module nokia-types-application-assurance {

    yang-version "1.1";

    namespace "urn:nokia.com:sros:ns:yang:sr:types-aa";

    prefix "types-aa";

    import nokia-sros-yang-extensions     { prefix "sros-ext"; }
    import nokia-types-sros               { prefix "types-sros"; }


    sros-ext:sros-major-release "rel20";

    organization "Nokia";

    contact
        "Nokia SR OS Support
         Web: <http://www.nokia.com>";

    description
        "Common application assurance data types used in the SR OS management system.

         Copyright 2016 Nokia. All rights reserved. Reproduction of this document
         is authorized on the condition that the foregoing copyright notice is included.

         This nokia-types-application-assurance YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-11";

    typedef isa-aa-grp-id {
        type uint32 {
            range "1..255";
        }
        description "isa-aa-grp-id is a group of ISA MDAs Identifier.";
    }

    typedef aa-grp-part-id {
        type uint32 {
            range "0..65535";
        }
        description "AA partition within an AA group.";
    }

    typedef aa-bit-rate-limit {
        type union {
            type int32 {
                range "1..40000";
            }
            type enumeration {
                enum "max"                          { value -1; }
            }
        }
        description "A bit rate limit expressed in megabits per second.";
    }

    typedef custom-protocol-name {
        type string {
            length "9";
            pattern "custom_(0[1-9]|10)" {
                error-message "The supported custom protocols are custom_[01-10].";
            }
        }
        description "custom protocol name";
    }

    typedef policer-start-time {
        type string {
            length "3..5";
            pattern "(([0-9]|0[0-9]|1[0-9]|2[0-3]):(00|15|30|45))" {
                error-message "The time format is [hh:mm], where hh is 00 to 23, and mm is 00, 15, 30, or 45.";
            }
        }
        description "The time format is [hh:mm], where hh is 00 to 23, and mm is 00, 15, 30, or 45.";
    }

    typedef policer-end-time {
        type string {
            length "3..5";
            pattern "(((([0-9]|0[0-9]|1[0-9]|2[0-3]):(00|15|30|45)))|(24:00))" {
                error-message "The time format is [hh:mm]. The range of hours is 00 to 24. The minutes are 00, 15, 30, or 45. If the hours is 24, the minutes must be 00.";
            }
        }
        description "The time format is [hh:mm], where hh is 00 to 24, and mm is 00, 15, 30, or 45.";
    }

    typedef day-of-week {
        type enumeration {
            enum "sunday"                       { value 1; }
            enum "monday"                       { value 2; }
            enum "tuesday"                      { value 3; }
            enum "wednesday"                    { value 4; }
            enum "thursday"                     { value 5; }
            enum "friday"                       { value 6; }
            enum "saturday"                     { value 7; }
        }
        description "The day of the week.";
    }

    typedef aa-grp-cflowd-template-select {
        type enumeration {
            enum "legacy"                       { value 0; }
            enum "dynamic"                      { value 1; }
        }
        description "Specifies the size limit of the AA URL list.";
    }

    typedef aa-datapath-cpu-limit {
        type union {
            type int32 {
                range "0..100";
            }
            type enumeration {
                enum "max"                          { value -1; }
            }
        }
        description "Datapath CPU traps limit as a percentage. max = disabled";
    }

    typedef aa-flow-setup-limit {
        type union {
            type int32 {
                range "1..800000";
            }
            type enumeration {
                enum "max"                          { value -1; }
            }
        }
        description "Limit for flow setup rate traps. max = disabled.";
    }

    typedef aa-packet-rate-limit {
        type union {
            type int32 {
                range "1..59523808";
            }
            type enumeration {
                enum "max"                          { value -1; }
            }
        }
        description "Limit for packet rate traps. max = disabled.";
    }

    typedef ipv4-address-or-ipv6-address-and-mask {
        type union {
            type types-sros:ipv4-address;
            type types-sros:ipv6-address-and-mask;
        }
        description "An IP address and mask.";
    }

    typedef permit-deny-action {
        type enumeration {
            enum "deny"                         { value 1; }
            enum "permit"                       { value 2; }
        }
        description "AA permit or deny action of an operation.";
    }

    typedef event-log-action {
        type enumeration {
            enum "deny"                         { value 0; }
            enum "permit"                       { value 1; }
            enum "all"                          { value 2; }
        }
        description "AA action on which an event log is raised.";
    }

    typedef stats-export-method {
        type enumeration {
            enum "accounting-policy"            { value 0; }
            enum "radius-accounting-policy"     { value 1; }
        }
        description "AA statistics export method.";
    }

    typedef http-redir-flow-type {
        type enumeration {
            enum "dropped-flows"                { value 1; }
            enum "admitted-flows"               { value 2; }
        }
        description "represents the types flows that can be redirected.";
    }

    typedef match-operator {
        type enumeration {
            enum "eq"                           { value 1; }
            enum "neq"                          { value 2; }
        }
        description "represents matching operator of charactersitics in application-qos-policy entry.";
    }

    typedef policer-type {
        type enumeration {
            enum "single-bucket-policer"        { value 1; }
            enum "dual-bucket-policer"          { value 2; }
            enum "flow-rate-policer"            { value 3; }
            enum "flow-count-policer"           { value 4; }
        }
        description "AA policer type.";
    }

    typedef policer-granulariy {
        type enumeration {
            enum "system"                       { value 1; }
            enum "subscriber"                   { value 2; }
        }
        description "AA policer granularity.";
    }

    typedef dual-policer-granulariy {
        type enumeration {
            enum "subscriber"                   { value 2; }
        }
        description "AA policer granularity.";
    }

    typedef policer-action {
        type enumeration {
            enum "permit-deny"                  { value 0; }
            enum "priority-mark"                { value 1; }
        }
        default "permit-deny";
        description "AA policer action to premit/deny or mark in/out of profile.";
    }

    typedef policer-cir {
        type union {
            type int32 {
                range "0..100000000";
            }
            type enumeration {
                enum "max"                          { value -1; }
            }
        }
        units "kbps";
        default "0";
        description "AA policer CIR in kbps. The value -1 means maximum rate.";
    }

    typedef policer-ir {
        type union {
            type int32 {
                range "1..100000000";
            }
            type enumeration {
                enum "max"                          { value -1; }
            }
        }
        units "kbps";
        default "max";
        description "AA policer information rate in kbps. The value -1 means maximum rate.";
    }

    typedef policer-burst-size {
        type int32 {
            range "0..131071";
        }
        units "KB";
        default "0";
        description "The amount of burst capacity assigned to a policer in kilo bytes.";
    }

    typedef policer-flow-rate {
        type union {
            type int32 {
                range "1..100000000";
            }
            type enumeration {
                enum "max"                          { value -1; }
            }
        }
        units "flows per second";
        default "max";
        description "AA policer flow rate in flows per seconds. The value -1 means maximum rate.";
    }

    typedef policer-flow-burst-size {
        type int32 {
            range "0..131071";
        }
        units "flows";
        default "0";
        description "The amount of flow burst capacity assigned to a policer.";
    }

    typedef policer-flow-count-limit {
        type union {
            type int32 {
                range "0..100000000";
            }
            type enumeration {
                enum "max"                          { value -1; }
            }
        }
        units "flows per second";
        default "max";
        description "AA policer flow count in flows per second. The value -1 means maximum rate while 0 means block flows.";
    }

    typedef cflowd-sample-rate {
        type uint32 {
            range "1..1000";
        }
        units "flows per second";
        description "AA cflowd per flow sampling rate";
    }

    typedef cflowd-export-type {
        type enumeration {
            enum "volume"                       { value 1; }
            enum "tcp-performance"              { value 2; }
            enum "rtp-performance"              { value 3; }
            enum "comprehensive"                { value 4; }
        }
        description "AA exported cflowd record type.";
    }

    typedef cflowd-measure-type {
        type enumeration {
            enum "tcp-performance"              { value 1; }
            enum "rtp-performance"              { value 2; }
            enum "comprehensive"                { value 3; }
        }
        description "AA cflowd flow based measurement type.";
    }

    typedef cflowd-packet-sample-type {
        type enumeration {
            enum "volume"                       { value 1; }
        }
        description "AA cflowd flow packet-based sampling type.";
    }

    typedef cflowd-export-override-type {
        type enumeration {
            enum "mobile"                       { value 1; }
        }
        description "AA cflowd export override type.";
    }

    typedef buffer-pool-reserved-percentage {
        type int32 {
            range "0..100";
        }
        description
            "configure the percentage of the buffer pool reserved for high priority traffic.
             A value of -1 (default) implies reserved CBS should be computed as the sum
             of the CBS requested by the entities using this pool.";
    }

    typedef http-field-encoding {
        type enumeration {
            enum "md5"                          { value 1; }
            enum "rc4"                          { value 2; }
            enum "crc4-md5-base64"              { value 3; }
        }
        description
            "AA HTTP enrichment field encoding types. It specifies the type of encoding that will be used
             on the field. Only the field value is encoded, not the field name.";
    }

    typedef http-tls-field-encoding {
        type enumeration {
            enum "md5"                          { value 1; }
            enum "rc4"                          { value 2; }
        }
        description "AA HTTP enrichment sub-type TLS encoding types.";
    }

    typedef certificate-file {
        type string {
            length "1..95";
        }
        description "A certificate file name without slashes or colon.";
    }

    typedef wa-shared-buffer-utilization-high {
        type union {
            type int32 {
                range "1..100";
            }
            type enumeration {
                enum "max"                          { value -1; }
            }
        }
        units "percent";
        description "Configure weighted average shared buffer utilization high watermark.";
    }

    typedef wa-shared-buffer-utilization-low {
        type types-sros:percent {
            range "0..99";
        }
        description "Configure weighted average shared buffer utilization low watermark.";
    }

    typedef truth-value {
        type enumeration {
            enum "true"                         { value 1; }
            enum "false"                        { value 2; }
        }
        description "Represents a truth value.";
    }

    typedef http-notif-interval {
        type union {
            type int32 {
                range "1..1440";
            }
            type enumeration {
                enum "one-time"                     { value 0; }
            }
        }
        units "minutes";
        default "one-time";
        description
            "specifies the minimum time to wait before re-inserting script URL into the
             HTTP response for a specific subscriber. A value of 0 specifies the insertion
             of the script URL is to occur one-time.";
    }

    typedef isa-aa-group-subscale {
        type enumeration {
            enum "residential"                  { value 0; }
            enum "vpn"                          { value 1; }
            enum "mobile-gateway"               { value 2; }
            enum "lightweight-internet"         { value 3; }
            enum "residential-8k"               { value 4; }
            enum "residential-16k"              { value 5; }
            enum "residential-32k"              { value 6; }
            enum "residential-64k"              { value 7; }
            enum "vpn-1k"                       { value 8; }
            enum "vpn-2k"                       { value 9; }
            enum "vpn-4k"                       { value 10; }
            enum "vpn-8k"                       { value 11; }
            enum "mobile-gateway-1m"            { value 12; }
            enum "mobile-gateway-2m"            { value 13; }
        }
        description
            "The various kinds of aa-sub-scale that are supported. This impacts the maximum number
             of AA subscribers and the corresponding policies that can be specified.";
    }

    typedef isa-generation-for-aa-grp {
        type uint32 {
            range "1..2";
        }
        description
            "The value specifies the minimum ISA Generation allowed in this group.
             On any HSR platform, the minimum ISA Generation has a value of 2.";
    }

    typedef isa-fail-to-mode {
        type enumeration {
            enum "fail-to-open"                 { value 1; }
        }
        description "specifies how the traffic is handled when there is no available ISA-AA cards.";
    }

    typedef isa-group-stats-category {
        type enumeration {
            enum "performance"                  { value 1; }
        }
        description "The ISA AA group statistics category names.";
    }

    typedef isa-mda-role {
        type enumeration {
            enum "primary"                      { value 0; }
            enum "backup"                       { value 1; }
        }
        description "The AA ISA mda role.";
    }

    typedef stat-type {
        type enumeration {
            enum "unknown"                      { value 0; }
            enum "protocol"                     { value 1; }
            enum "application"                  { value 2; }
            enum "app-group"                    { value 3; }
            enum "charging-group"               { value 4; }
        }
        description "The various kinds of statistics objects used in Application Assurance.";
    }

    typedef fragment-drop-scope {
        type enumeration {
            enum "all"                          { value 1; }
            enum "out-of-order"                 { value 2; }
        }
        description "specifies which fragments if any must be dropped as policy.";
    }

    typedef tcp-segment-size {
        type int32 {
            range "160..10240";
        }
        description "TCP MSS adjust size.";
    }

    typedef transit-ip-policy-sub-address {
        type union {
            type types-sros:ipv4-unicast-address;
            type types-sros:ipv6-prefix;
        }
        description "Sepcifies an AA static subscriber address in a transit-ip-policy.";
    }

    typedef traffic-direction {
        type enumeration {
            enum "subscriber-to-network"        { value 0; }
            enum "network-to-subscriber"        { value 1; }
            enum "both"                         { value 2; }
        }
        description "AA traffic direction.";
    }

    typedef flow-direction {
        type enumeration {
            enum "from-sub"                     { value 1; }
            enum "to-sub"                       { value 2; }
        }
        description "AA flow direction.";
    }

    typedef web-serv-classifier-id {
        type enumeration {
            enum "web-service-1"                { value 1; }
        }
        description "AA web service classifier Id.";
    }

    typedef partition-stats-category {
        type enumeration {
            enum "protocol"                     { value 1; }
            enum "application"                  { value 2; }
            enum "app-group"                    { value 3; }
            enum "aa-sub"                       { value 4; }
            enum "aa-sub-study-protocol"        { value 5; }
            enum "aa-sub-study-application"     { value 6; }
            enum "aa-partition"                 { value 7; }
            enum "aa-admit-deny"                { value 8; }
        }
        description "AA partition statistics categories.";
    }

    typedef tca-criteria {
        type enumeration {
            enum "error-drop"                   { value 1; }
            enum "fragment-drop-out-of-order"   { value 2; }
            enum "fragment-drop-all"            { value 3; }
            enum "overload-drop"                { value 4; }
            enum "gtp-sanity-drop"              { value 5; }
        }
        description "AA statistics threshold crosssing alert criteria based on Application QoS POlicy action.";
    }

    typedef tca-gtp-criteria {
        type enumeration {
            enum "max-payload-length"           { value 1; }
            enum "message-type-default-action"  { value 2; }
            enum "header-sanity"                { value 3; }
            enum "message-type-gtpv2-default-action" { value 4; }
            enum "imsi-apn-filter-default-action" { value 5; }
            enum "validate-gtp-tunnels"         { value 6; }
            enum "validate-sequence-number"     { value 7; }
            enum "validate-src-ip-addr"         { value 8; }
            enum "missing-mandatory-ie"         { value 9; }
            enum "gtp-in-gtp"                   { value 10; }
        }
        description "AA GTP filter statistics threshold crosssing alert criteria.";
    }

    typedef tca-sctp-criteria {
        type enumeration {
            enum "ppid-default-action"          { value 1; }
            enum "packet-sanity"                { value 2; }
            enum "ppid-range"                   { value 3; }
        }
        description "AA SCTP filter statistics threshold crosssing alert criteria.";
    }

    typedef tca-session-criteria {
        type enumeration {
            enum "default-action"               { value 1; }
        }
        description "AA session filter statistics threshold crosssing alert criteria.";
    }

    typedef ts-url-aa-string {
        type union {
            type types-sros:cflash-url {
                length "1..180";
            }
            type string {
                length "1..180";
            }
        }
        description
            "URL specifies a url in the following format:
             local-url    - [<cflash-id>/][<file-path>]
             remote-url   - [{ftp://|tftp://}<login>:<pswd>@<remote-locn>/][<file-path>] 180 chars max
             remote-locn  - [ <hostname> | <ipv4-address> | <ipv6-address> ]
             ipv4-address - a.b.c.d
             ipv6-address - x:x:x:x:x:x:x:x[-interface]
                            x:x:x:x:x:x:d.d.d.d[-interface]
                            x - [0..FFFF]H
                            d - [0..255]D
                            interface - 32 chars max, for link
                            local addresses
             cflash-id    - cf1:|cf1-A:|cf1-B:|cf2:|cf2-A:|cf2-B:|cf3:|cf3-A:|cf3-B:";
    }

    typedef fc-name {
        type enumeration {
            enum "be"                           { value 0; }
            enum "l2"                           { value 1; }
            enum "af"                           { value 2; }
            enum "l1"                           { value 3; }
            enum "h2"                           { value 4; }
            enum "ef"                           { value 5; }
            enum "h1"                           { value 6; }
            enum "nc"                           { value 7; }
        }
        description "Specifies different Forwarding Classes (FC).";
    }

    typedef expr-sub-string {
        type enumeration {
            enum "http-host"                    { value 1; }
            enum "http-uri"                     { value 2; }
            enum "http-referer"                 { value 3; }
            enum "sip-ua"                       { value 4; }
            enum "sip-uri"                      { value 5; }
            enum "sip-mt"                       { value 6; }
            enum "citrix-app"                   { value 7; }
            enum "http-user-agent"              { value 8; }
            enum "h323-product-id"              { value 9; }
            enum "tls-cert-subj-org-name"       { value 10; }
            enum "tls-cert-subj-common-name"    { value 11; }
            enum "rtsp-host"                    { value 12; }
            enum "rtsp-uri"                     { value 13; }
            enum "rtsp-ua"                      { value 14; }
            enum "rtmp-page-host"               { value 15; }
            enum "rtmp-page-uri"                { value 16; }
            enum "rtmp-swf-host"                { value 17; }
            enum "rtmp-swf-uri"                 { value 18; }
            enum "rtmp-tc-uri"                  { value 19; }
        }
        description "AA expression substring type. ";
    }

    typedef aa-ppid-value {
        type union {
            type uint32 {
                range "0..4294967295";
            }
            type enumeration {
                enum "iua"                          { value 1; }
                enum "m2ua"                         { value 2; }
                enum "m3ua"                         { value 3; }
                enum "sua"                          { value 4; }
                enum "m2pa"                         { value 5; }
                enum "v5ua"                         { value 6; }
                enum "h.248"                        { value 7; }
                enum "bicc/q.2150.3"                { value 8; }
                enum "tali"                         { value 9; }
                enum "dua"                          { value 10; }
                enum "asap"                         { value 11; }
                enum "enrp"                         { value 12; }
                enum "h.323"                        { value 13; }
                enum "q.ipc/q.2150.3"               { value 14; }
                enum "simco"                        { value 15; }
                enum "ddp-segment-chunk"            { value 16; }
                enum "ddp-stream-session-control"   { value 17; }
                enum "s1-application-protocol"      { value 18; }
                enum "rua"                          { value 19; }
                enum "hnbap"                        { value 20; }
                enum "forces-hp"                    { value 21; }
                enum "forces-mp"                    { value 22; }
                enum "forces-lp"                    { value 23; }
                enum "sbc-ap"                       { value 24; }
                enum "nbap"                         { value 25; }
                enum "x2ap"                         { value 27; }
                enum "ircp"                         { value 28; }
                enum "lcs-ap"                       { value 29; }
                enum "mpich2"                       { value 30; }
                enum "service-area-broadcast-protocol" { value 31; }
                enum "fractal-generator-protocol"   { value 32; }
                enum "ping-pong-protocol"           { value 33; }
                enum "calcapp-protocol"             { value 34; }
                enum "scripting-service-protocol"   { value 35; }
                enum "netperfmeter-protocol-control-channel" { value 36; }
                enum "netperfmeter-protocol-data-channel" { value 37; }
                enum "echo"                         { value 38; }
                enum "discard"                      { value 39; }
                enum "daytime"                      { value 40; }
                enum "character-generator"          { value 41; }
                enum "3gpp-rna"                     { value 42; }
                enum "3gpp-m2ap"                    { value 43; }
                enum "3gpp-m3ap"                    { value 44; }
                enum "ssh-over-sctp"                { value 45; }
                enum "diameter-in-a-sctp-data-chunk" { value 46; }
                enum "diameter-in-a-dtls/sctp-data-chunk" { value 47; }
                enum "r14p.-ber-encoded-asn.1-over-sctp" { value 48; }
                enum "webrtc-control"               { value 50; }
                enum "domstring-last"               { value 51; }
                enum "binary-data-partial"          { value 52; }
                enum "binary-data-last"             { value 53; }
                enum "domstring-partial"            { value 54; }
                enum "3gpp-pua"                     { value 55; }
                enum "webrtc-string-empty"          { value 56; }
                enum "webrtc-binary-empty"          { value 57; }
            }
        }
        description "Protocol Payload Identifier (PPID) value from IANA, 'SCTP Payload Protocol Identifiers'";
    }

    typedef aa-gtp-fltr-msg-value {
        type union {
            type int32 {
                range "0..255";
            }
            type enumeration {
                enum "echo-request"                 { value 1; }
                enum "echo-response"                { value 2; }
                enum "version-not-supported"        { value 3; }
                enum "node-alive-request"           { value 4; }
                enum "node-alive-response"          { value 5; }
                enum "redirection-request"          { value 6; }
                enum "redirection-response"         { value 7; }
                enum "create-pdp-context-request"   { value 16; }
                enum "create-pdp-context-response"  { value 17; }
                enum "update-pdp-context-request"   { value 18; }
                enum "update-pdp-context-response"  { value 19; }
                enum "delete-pdp-context-request"   { value 20; }
                enum "delete-pdp-context-response"  { value 21; }
                enum "initiate-pdp-context-activation-request" { value 22; }
                enum "initiate-pdp-context-activation-response" { value 23; }
                enum "error-indication"             { value 26; }
                enum "pdu-notification-request"     { value 27; }
                enum "pdu-notification-response"    { value 28; }
                enum "pdu-notification-reject-request" { value 29; }
                enum "pdu-notification-reject-response" { value 30; }
                enum "supported-extension-headers-notification" { value 31; }
                enum "send-routing-information-for-gprs-request" { value 32; }
                enum "send-routing-information-for-gprs-response" { value 33; }
                enum "failure-report-request"       { value 34; }
                enum "failure-report-response"      { value 35; }
                enum "note-ms-gprs-present-request" { value 36; }
                enum "note-ms-gprs-present-response" { value 37; }
                enum "identification-request"       { value 48; }
                enum "identification-response"      { value 49; }
                enum "sgsn-context-request"         { value 50; }
                enum "sgsn-context-response"        { value 51; }
                enum "sgsn-context-acknowledge"     { value 52; }
                enum "forward-relocation-request"   { value 53; }
                enum "forward-relocation-response"  { value 54; }
                enum "forward-relocation-complete"  { value 55; }
                enum "relocation-cancel-request"    { value 56; }
                enum "relocation-cancel-response"   { value 57; }
                enum "forward-srns-context"         { value 58; }
                enum "forward-relocation-complete-acknowledge" { value 59; }
                enum "forward-srns-context-acknowledge" { value 60; }
                enum "ran-information-relay"        { value 70; }
                enum "mbms-notification-request"    { value 96; }
                enum "mbms-notification-response"   { value 97; }
                enum "mbms-notification-reject-request" { value 98; }
                enum "mbms-notification-reject-response" { value 99; }
                enum "create-mbms-context-request"  { value 100; }
                enum "create-mbms-context-response" { value 101; }
                enum "update-mbms-context-request"  { value 102; }
                enum "update-mbms-context-response" { value 103; }
                enum "delete-mbms-context-request"  { value 104; }
                enum "delete-mbms-context-response" { value 105; }
                enum "mbms-registration-request"    { value 112; }
                enum "mbms-registration-response"   { value 113; }
                enum "mbms-de-registration-request" { value 114; }
                enum "mbms-de-registration-response" { value 115; }
                enum "mbms-session-start-request"   { value 116; }
                enum "mbms-session-start-response"  { value 117; }
                enum "mbms-session-stop-request"    { value 118; }
                enum "mbms-session-stop-response"   { value 119; }
                enum "mbms-session-update-request"  { value 120; }
                enum "mbms-session-update-response" { value 121; }
                enum "ms-info-change-notification-request" { value 128; }
                enum "ms-info-change-notification-response" { value 129; }
                enum "data-record-transfer-request" { value 240; }
                enum "data-record-transfer-response" { value 241; }
                enum "end-marker"                   { value 254; }
                enum "g-pdu"                        { value 255; }
            }
        }
        description "GPRS Tunneling Protocol (GTP) message value, defined in '3GPP, TS 29.060. V7.9.0'";
    }

    typedef aarp-state {
        type enumeration {
            enum "stand-alone"                  { value 0; }
            enum "remote"                       { value 1; }
            enum "master"                       { value 2; }
            enum "backup"                       { value 3; }
        }
        description
            "The state of an Application Assurance Redundancy Protocol (AARP) instance performing asymmetry removal.
             Asymmetry refers to a situation where the two directions of traffic for a specific flow
             take different paths through the network.
             Asymmetry removal ensures that packets for each flow and all flows for each subscriber are processed
             by the same ISA-AA.";
    }

    typedef aarp-oper-flags {
        type bits {
            bit admin-down                     { position 0; }
            bit no-sub-configd                 { position 1; }
            bit peer-down                      { position 2; }
            bit peer-aarp-down                 { position 3; }
            bit sub-type-mismatch              { position 4; }
            bit sub-down                       { position 5; }
            bit shunts-down                    { position 6; }
            bit divert-cap-down                { position 7; }
            bit app-prof-no-divert             { position 8; }
            bit sub-side-pipe-mismatch         { position 9; }
            bit sub-side-if-mismatch           { position 10; }
            bit net-side-pipe-mismatch         { position 11; }
            bit net-side-if-mismatch           { position 12; }
            bit unsupported-ioms               { position 13; }
            bit config-mismatch                { position 14; }
            bit no-secondary-eps               { position 15; }
        }
        description
            "Represents the different conditions that
             affect the operating status of an AARP instance.

             The bit values are:
                admin-down(0)                - AARP instance is administratively
                                               down.
                no-sub-configd(1)            - no 'dualHomed(2)' subscriber reference
                                               configured against the AARP instance.
                peer-down(2)                 - no communication with peer AARP
                                               instance.
                peer-aarp-down(3)            - MC-CTL link is up, but AARP layer
                                               protocol interaction with peer AARP
                                               instance is not established.
                sub-type-mismatch(4)         - mismatch detected in the subscriber
                                               types between peer AARP instances.
                sub-down(5)                  - 'dualHomed(2)' subscriber reference
                                               is operationally down.
                shunts-down(6)               - one of the shunts referenced by the
                                               AARP instance is down.
                divert-cap-down(7)           - divert to AA not possible - divert
                                               capability is down.
                app-prof-no-divert(8)        - app-profile used by the 'dualHomed(2)'
                                               subscriber reference has 'no divert'
                                               set.
                sub-side-pipe-mismatch(9)    - mismatch detected in the
                                               subscriber-side pipe between AARP
                                               instances.
                sub-side-if-mismatch(10)     - mismatch detected in the
                                               subscriber-side interface between
                                               peer AARP instances.
                net-side-pipe-mistmatch(11)  - mismatch detected in the network-side
                                               pipe between AARP instances.
                net-side-if-mismatch(12)     - mismatch detected in in the network-
                                               side interface between peer AARP
                                               instances.
                unsupported-ioms(13)         - IOMs which do not support AARP have
                                               been detected.
                config-mismatch(14)          - indicates that AARP is down because
                                               of a configuration mismatch between
                                               peer AARP instances.
                no-secondary-eps(15)         - indicates that single-node AARP is
                                               down because no secondary endpoints
                                               exist for that AARP instance.";
    }

    typedef aarp-svc-point-role {
        type enumeration {
            enum "none"                         { value 0; }
            enum "dual-homed"                   { value 1; }
            enum "pipe-shunt-sub"               { value 2; }
            enum "pipe-shunt-net"               { value 3; }
            enum "interface-shunt-sub"          { value 4; }
            enum "interface-shunt-net"          { value 5; }
            enum "dual-homed-secondary"         { value 6; }
        }
        description
            "Represents the different roles that an
             AARP instance service point can assume.

             The roles of service points are:
                    none                 (0) - no role.
                    dual-homed           (1) - a service point into the dual homed
                                               network being protected by AARP.
                    pipe-shunt-sub       (2) - subscriber side pipe shunt.
                    pipe-shunt-net       (3) - network side pipe shunt.
                    interface-shunt-sub  (4) - subscriber side interface shunt.
                    interface-shunt-net  (5) - network side interface shunt.
                    dual-homed-secondary (6) - a secondary service point into the
                                               dual homed network being protected by AARP.";
    }

    typedef url-list-flags {
        type bits {
            bit admin-down                     { position 0; }
            bit file-does-not-exist            { position 1; }
            bit invalid-file-format            { position 2; }
            bit too-many-urls                  { position 3; }
            bit switch-over-error              { position 4; }
            bit too-many-chars                 { position 5; }
        }
        description
            "Represents the different conditions that affect the status of
             a URL list.

             The bit values are:
                admin-down(0)              - URL list is administratively down
                file-does-not-exist(1)     - file at configured URL does not exist
                invalid-file-format(2)     - invalid format in file at configured URL
                too-many-urls(3)           - number of URLs in file exceeds limit
                switch-over-error(4)       - CPM activity switch has occurred during
                                             a URL list upgrade
                too-many-chars(5)          - number of characters in file exceeds limit";
    }

    typedef tca-state {
        type enumeration {
            enum "cleared"                      { value 1; }
            enum "raised"                       { value 2; }
        }
        description
            "Specifies the Threshold Crossing Alert (TCA) state.
             Valid values are:
                   cleared (1) - the state at TCA creation or when the utilization
                                 is less than the low watermark and for every
                                 subsequent utilization that is less than the high
                                 watermark
                   raised  (2) - the state when the utilization is greater than the
                                 high watermark and for every subsequent utilization
                                 that is greater than the low watermark.";
    }

    typedef trigger-type {
        type enumeration {
            enum "denied-traffic"               { value 1; }
            enum "admitted-traffic"             { value 2; }
        }
        description
            "Specifies the type of traffic used in triggering the Threshold Crossing Alert (TCA) utilization.
             Valid values are:
                 deniedTraffic   (1) - the utilization is triggered based on the amount of denied traffic
                 admittedTraffic (2) - the utilization is triggered based on the amount of admitted traffic.";
    }

    typedef trans-sub-orig {
        type bits {
            bit static                         { position 0; }
            bit dhcp                           { position 1; }
            bit radius                         { position 2; }
            bit auto-seen-ip                   { position 3; }
            bit diameter                       { position 4; }
        }
        description
            "Specifies the possible ways in which the transit AA subscriber was created.
             The various origins of a transit subscriber are:

               static       - statically provisioned
               dhcp         - dynamically learned via DHCP
               radius       - dynamically learned via RADIUS
               auto-seen-ip - automatically created via Seen IP
               diameter     - dynamically learned via Diameter

             A transit subscriber may have more than one origin.
             The absence of any bits indicates a subscriber of unknown origin.";
    }

    typedef centipercent {
        type uint32 {
            range "0..10000";
        }
        units "centipercent";
        description "A percentage defined to two decimal places.";
    }

    typedef mda-activity-state {
        type enumeration {
            enum "unavailable"                  { value 0; }
            enum "active"                       { value 1; }
            enum "standby"                      { value 2; }
        }
        description
            "Specifies the working state of an ISA-AA MDA in a group. The Activity state may be one of:
                   unavailable (0) - is not available to provide service
                   active      (1) - is online and providing service
                   standby     (2) - is online, but not providing service.";
    }

    typedef balance-state {
        type enumeration {
            enum "balancing"                    { value 0; }
            enum "complete"                     { value 1; }
        }
        description
            "Specifies the working state of an ISA-AA MDA in a group. The Activity state may be one of:
                   unavailable (0) - is not available to provide service
                   active      (1) - is online and providing service
                   standby     (2) - is online, but not providing service.";
    }

    typedef aso-val-derived-from {
        type enumeration {
            enum "unknown"                      { value 0; }
            enum "default"                      { value 1; }
            enum "app-profile"                  { value 2; }
            enum "override"                     { value 3; }
            enum "dyn-override"                 { value 4; }
        }
        description
            "Specifies from where the characteristic value is being derived from for the Application Assurance subscriber.
             The characteristic value can be derived from Application Service Option (ASO) defaults, application profiles, or policy-overrides.";
    }

    typedef statistics-type {
        type enumeration {
            enum "protocol"                     { value 1; }
            enum "application"                  { value 2; }
            enum "app-group"                    { value 3; }
            enum "charging-group"               { value 4; }
        }
        description "Specifies the various kinds of statistics used in Application Assurance.";
    }

    typedef um-oper-state {
        type enumeration {
            enum "admin-disabled"               { value 0; }
            enum "inactive"                     { value 1; }
            enum "active"                       { value 2; }
        }
        description
            "Specifies the status of a usage monitor.
             Valid values are:
                 admin-disabled (0)   - rule has been shutdown on the policy server
                 inactive       (1)   - rule received and either no credits granted
                                        from the policy server or credits have been
                                        exceeded
                 active         (2)   - rule and credits received from the policy
                                       server and credits have not been exceeded.";
    }

    typedef um-grant-state {
        type enumeration {
            enum "invalid"                      { value 0; }
            enum "valid"                        { value 1; }
            enum "exceeded"                     { value 2; }
        }
        description
            "Specifies the status of a grant within a usage monitor.
             Valid values are:
                 invalid  (0)   - the grant is inactive as no credits have been
                                  received from policy server
                 valid    (1)   - usage monitoring is in use and there are credits
                                  remaining
                 exceeded (2)   - the granted credits have been exceeded, and a
                                  report is sent back to the policy server.";
    }

}
