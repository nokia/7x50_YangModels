submodule nokia-conf-cflowd {

    yang-version "1.1";

    belongs-to nokia-conf { prefix "conf"; }

    import nokia-sros-yang-extensions     { prefix "sros-ext"; }
    import nokia-types-cflowd             { prefix "types-cflowd"; }
    import nokia-types-qos                { prefix "types-qos"; }
    import nokia-types-sros               { prefix "types-sros"; }

    include nokia-conf-groups;
    include nokia-conf-router;
    include nokia-conf-service;
    include nokia-conf-svc-ies;
    include nokia-conf-svc-ies-sub-if;
    include nokia-conf-svc-vprn;
    include nokia-conf-svc-vprn-sub-if;

    sros-ext:sros-major-release "rel20";

    organization "Nokia";

    contact
        "Nokia SR OS Support
         Web: <http://www.nokia.com>";

    description
        "Nokia YANG Data model to configure Cflowd configuration on SR OS based routers.

         Copyright 2016 Nokia. All rights reserved. Reproduction of this document
         is authorized on the condition that the foregoing copyright notice is included.

         This nokia-conf-cflowd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-17";

    grouping conf-cflowd {
        container cflowd {
            presence "cflowd";
            description "Enter the cflowd context";

            leaf admin-state {
                type types-sros:admin-state;
                default "enable";
                description "Administrative state of Cflowd sampling";
            }

            leaf analyze-gre-payload {
                type boolean;
                default "false";
                description "Perform Cflowd analysis on the inner IP packet within a GRE packet";
            }

            leaf analyze-l2tp-traffic {
                type boolean;
                default "false";
                description "Perform Cflowd analysis on the inner header within an L2TP packet.";
            }

            leaf analyze-v4overv6-traffic {
                type boolean;
                default "false";
                description "Perform Cflowd analysis on the inner IPv4 packet within an IPv6 packet.";
            }

            leaf cache-size {
                type uint32 {
                    range "1000..1500000";
                }
                units "flows";
                description "Maximum number of active flows in the flow cache table";
            }

            leaf enhanced-distribution {
                type boolean;
                default "false";
                description "Include ingress port ID in the hashing algorithm used to distribute Cflowd sample traffic";
            }

            leaf export-mode {
                type enumeration {
                    enum "automatic"                    { value 1; }
                    enum "manual"                       { value 2; }
                }
                default "automatic";
                description "Export mode for flow data";
            }

            leaf inband-collector-export-only {
                type boolean;
                default "false";
                description "Export the traffic to all collectors only via in-band interfaces";
            }

            leaf overflow {
                type uint32 {
                    range "1..50";
                }
                units "percent";
                default "1";
                description "Percentage of entries to remove from Cflowd cache when the maximum number of entries is exceeded";
            }

            leaf template-retransmit {
                type uint32 {
                    range "10..600";
                }
                units "seconds";
                default "600";
                description "Time to resend template information";
            }

            leaf use-vrtr-if-index {
                type boolean;
                default "false";
                description "Export flow data using virtual router interface indexes";
            }

            leaf active-flow-timeout {
                type uint32 {
                    range "60..36000";
                }
                units "seconds";
                default "1800";
                description "Specifies the maximum amount of time, in seconds, before an active flow will be exported. If an individual flow is active for this amount of time, the flow is exported and a new flow is created.";
            }

            leaf inactive-flow-timeout {
                type uint32 {
                    range "10..600";
                }
                units "seconds";
                default "15";
                description "Specifies the amount of time, in seconds, that must elapse without a packet matching a flow before the flow is considered inactive.";
            }

            leaf-list apply-groups {
                type leafref {
                    path "../../groups/group/name";
                }
                max-elements 8;
                ordered-by user;
                description "Apply a configuration group at this level";
            }

            leaf active-timeout {
                status obsolete;
                type uint32 {
                    range "1..600";
                }
                units "minutes";
                default "30";
                description "Maximum time before an active flow is exported";
            }

            leaf inactive-timeout {
                status obsolete;
                type uint32 {
                    range "10..600";
                }
                units "seconds";
                default "15";
                description "Time before the flow is considered inactive";
            }

            leaf rate {
                status obsolete;
                type uint32 {
                    range "1..10000";
                }
                units "packets";
                default "1000";
                description "Rate at which traffic is sampled and sent for Cflowd analysis";
            }

            list sample-profile {
                key "profile-id";
                max-elements 5;
                description "Enter the sample-profile list instance";

                leaf profile-id {
                    type uint32 {
                        range "1..5";
                    }
                    description "The unique specifier of this sample-profile";
                }

                leaf sample-rate {
                    type uint32 {
                        range "1..10000";
                    }
                    default "1000";
                    description "The cflowd sampling rate for this profile";
                }

                leaf-list apply-groups {
                    type leafref {
                        path "../../../groups/group/name";
                    }
                    max-elements 8;
                    ordered-by user;
                    description "Apply a configuration group at this level";
                }

            } // list sample-profile

            list collector {
                key "ip-address port";
                max-elements 8;
                description "Enter the collector list instance";

                leaf ip-address {
                    type types-sros:ip-unicast-address;
                    description "IP address of a remote Cflowd collector host to receive the exported Cflowd data";
                }

                leaf port {
                    type types-qos:tcp-udp-match-port {
                        range "1..65535";
                    }
                    description "UDP port number on the remote Cflowd collector host to receive the exported Cflowd data";
                }

                leaf admin-state {
                    type types-sros:admin-state;
                    default "enable";
                    description "Administrative state of this Cflowd collector";
                }

                leaf autonomous-system-type {
                    type enumeration {
                        enum "origin"                       { value 1; }
                        enum "peer"                         { value 2; }
                    }
                    default "origin";
                    description "Basis of the AS information included in flow data";
                }

                leaf description {
                    type types-sros:description;
                    description "Text description";
                }

                leaf router-instance {
                    type string;
                    default "management";
                    description "Router context for the flow data for this Cflowd collector";
                }

                leaf template-set {
                    type enumeration {
                        enum "not-applicable"               { value 0; }
                        enum "basic"                        { value 1; }
                        enum "mpls-ip"                      { value 2; }
                        enum "l2-ip"                        { value 3; }
                        enum "mpls-transport"               { value 4; }
                    }
                    description "Template set for this Cflowd collector";
                }

                leaf version {
                    type types-cflowd:collector-version;
                    sros-ext:immutable;
                    mandatory true;
                    description "Flow data collector version";
                }

                leaf-list apply-groups {
                    type leafref {
                        path "../../../groups/group/name";
                    }
                    max-elements 8;
                    ordered-by user;
                    description "Apply a configuration group at this level";
                }

                container aggregation {
                    description "Enter the aggregation context";

                    leaf as-matrix {
                        type boolean;
                        default "false";
                        description "Base aggregation data on autonomous system (AS) information";
                    }

                    leaf protocol-port {
                        type boolean;
                        default "false";
                        description "Aggregate flows based on the IP protocol, source port number, and destination port number";
                    }

                    leaf source-prefix {
                        type boolean;
                        default "false";
                        description "Aggregate flows based on the source prefix information";
                    }

                    leaf destination-prefix {
                        type boolean;
                        default "false";
                        description "Aggregate data based on the destination prefix information";
                    }

                    leaf source-destination-prefix {
                        type boolean;
                        default "false";
                        description "Aggregate data based on the source and destination prefix information";
                    }

                    leaf raw {
                        type boolean;
                        default "false";
                        description "Export flow data without aggregation";
                    }

                } // container aggregation

                container export-filter {
                    when "../version = 9 or ../version = 10";
                    description "Enter the export-filter context";

                    container family {
                        description "Enter the family context";

                        leaf ipv4 {
                            type boolean;
                            default "false";
                            description "Filter IPv4 flow data from being sent to the associated collector";
                        }

                        leaf ipv6 {
                            type boolean;
                            default "false";
                            description "Filter IPv6 flow data from being sent to the associated collector";
                        }

                        leaf mcast-ipv4 {
                            type boolean;
                            default "false";
                            description "Filter multicast IPv4 flow data from being sent to the associated collector";
                        }

                        leaf mcast-ipv6 {
                            type boolean;
                            default "false";
                            description "Filter multicast IPv6 flow data from being sent to the associated collector";
                        }

                        leaf l2-ip {
                            type boolean;
                            default "false";
                            description "Filter Layer 2 IP flow data from being sent to the associated collector";
                        }

                        leaf mpls {
                            type boolean;
                            default "false";
                            description "Filter MPLS flow data from being sent to the associated collector";
                        }

                    } // container family

                    list router {
                        key "router-instance";
                        description "Add a list entry for router";

                        leaf router-instance {
                            type string;
                            description "Router instance ID";
                        }

                    } // list router

                    container interface-list {
                        description "Enter the interface-list context";

                        list router {
                            key "router-name interface-name";
                            description "Add a list entry for router";

                            leaf router-name {
                                type leafref {
                                    path "../../../../../../router/router-name";
                                }
                                description "Name of router associated with the interface";
                            }

                            leaf interface-name {
                                type leafref {
                                    path "../../../../../../router[router-name=current()/../router-name]/interface/interface-name";
                                }
                                description "Interface name";
                            }

                        } // list router

                        container service {
                            description "Enter the service context";

                            list ies-interface {
                                key "service-name interface-name";
                                description "Add a list entry for ies-interface";

                                leaf service-name {
                                    type leafref {
                                        path "../../../../../../../service/ies/service-name";
                                    }
                                    description "IES service name";
                                }

                                leaf interface-name {
                                    type leafref {
                                        path "../../../../../../../service/ies[service-name=current()/../service-name]/interface/interface-name";
                                    }
                                    description "ies interface name";
                                }

                            } // list ies-interface

                            list ies-group-interface {
                                key "service-name subscriber-interface-name group-interface-name";
                                description "Add a list entry for ies-group-interface";

                                leaf service-name {
                                    type leafref {
                                        path "../../../../../../../service/ies/service-name";
                                    }
                                    description "IES service name";
                                }

                                leaf subscriber-interface-name {
                                    type leafref {
                                        path "../../../../../../../service/ies[service-name=current()/../service-name]/subscriber-interface/interface-name";
                                    }
                                    description "IES subscriber-interface name";
                                }

                                leaf group-interface-name {
                                    type leafref {
                                        path "../../../../../../../service/ies[service-name=current()/../service-name]/subscriber-interface[interface-name=current()/../subscriber-interface-name]/group-interface/group-interface-name";
                                    }
                                    description "IES group-interface name";
                                }

                            } // list ies-group-interface

                            list vprn-interface {
                                key "service-name interface-name";
                                description "Add a list entry for vprn-interface";

                                leaf service-name {
                                    type leafref {
                                        path "../../../../../../../service/vprn/service-name";
                                    }
                                    description "VPRN service name";
                                }

                                leaf interface-name {
                                    type leafref {
                                        path "../../../../../../../service/vprn[service-name=current()/../service-name]/interface/interface-name";
                                    }
                                    description "vprn interface name";
                                }

                            } // list vprn-interface

                            list vprn-network-interface {
                                key "service-name network-interface-name";
                                description "Add a list entry for vprn-network-interface";

                                leaf service-name {
                                    type leafref {
                                        path "../../../../../../../service/vprn/service-name";
                                    }
                                    description "VPRN service name";
                                }

                                leaf network-interface-name {
                                    type leafref {
                                        path "../../../../../../../service/vprn[service-name=current()/../service-name]/network-interface/interface-name";
                                    }
                                    description "VPRN network-interface name";
                                }

                            } // list vprn-network-interface

                            list vprn-group-interface {
                                key "service-name subscriber-interface-name group-interface-name";
                                description "Add a list entry for vprn-group-interface";

                                leaf service-name {
                                    type leafref {
                                        path "../../../../../../../service/vprn/service-name";
                                    }
                                    description "VPRN service name";
                                }

                                leaf subscriber-interface-name {
                                    type leafref {
                                        path "../../../../../../../service/vprn[service-name=current()/../service-name]/subscriber-interface/interface-name";
                                    }
                                    description "VPRN subscriber-interface name";
                                }

                                leaf group-interface-name {
                                    type leafref {
                                        path "../../../../../../../service/vprn[service-name=current()/../service-name]/subscriber-interface[interface-name=current()/../subscriber-interface-name]/group-interface/group-interface-name";
                                    }
                                    description "vprn group-interface name";
                                }

                            } // list vprn-group-interface

                        } // container service

                    } // container interface-list

                } // container export-filter

            } // list collector

        } // container cflowd

    } // grouping conf-cflowd

}
