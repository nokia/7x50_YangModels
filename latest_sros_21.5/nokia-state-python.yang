submodule nokia-state-python {

    yang-version "1.1";

    belongs-to nokia-state { prefix "state"; }

    import ietf-yang-types                { prefix "yang"; }
    import nokia-sros-yang-extensions     { prefix "sros-ext"; }
    import nokia-types-esa                { prefix "types-esa"; }
    import nokia-types-isa                { prefix "types-isa"; }
    import nokia-types-sros               { prefix "types-sros"; }


    sros-ext:sros-major-release "rel21";

    organization "Nokia";

    contact
        "Nokia SR OS Support
         Web: <http://www.nokia.com>";

    description
        "Nokia YANG Data model with operational state for Python scripts on SR OS based routers.

         Copyright 2016 Nokia. All rights reserved. Reproduction of this document
         is authorized on the condition that the foregoing copyright notice is included.

         This nokia-state-python YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-26";

    grouping state-python {
        container python {
            description "Enter the python context";

            list python-script {
                key "name";
                description "Enter the python-script list instance";

                leaf name {
                    type types-sros:named-item;
                    description "Python script policy name";
                }

                leaf oper-state {
                    type types-sros:oper-state;
                    description "the operational state of the Python script.";
                }

                leaf oper-state-distributed {
                    type types-sros:oper-state;
                    description "the operational state of the distributed deployment of the Python script.";
                }

                leaf code-size {
                    type uint32;
                    units "bytes";
                    description "the bytecode size of the Python script.";
                }

                leaf active-url {
                    type enumeration {
                        enum "none"                         { value 0; }
                        enum "primary"                      { value 1; }
                        enum "secondary"                    { value 2; }
                        enum "tertiary"                     { value 3; }
                    }
                    description
                        "which URL the script has been loaded.

                         A value of 'primary (1)' indicates the URL in primary-url
                         has been used.
                         A value of 'secondary (2)' indicates the URL in
                         secondary-url has been used.
                         A value of 'tertiary (3)' indicates the URL in tertiary-url
                         has been used.

                         A value of 'none (0)' indicates no script has been
                         loaded.";
                }

                leaf reload-action {
                    type types-sros:action-type;
                    description
                        "whether to reload the Python script file specified by this
                         Python script.

                         When SET to the value of 'do-action' the system will load
                         and parse the file specified in the primary, secondary or
                         tertiary URL.

                         A request on this object returns 'not-applicable'.";
                }

                list statistics {
                    key "isa-group-id isa";
                    description "Enter the statistics list instance";

                    leaf isa-group-id {
                        type uint32 {
                            range "1..4";
                        }
                        description "NAT or WLAN-GW Integrated Service Adaptor (ISA) group ID";
                    }

                    leaf isa {
                        type types-isa:slot-mda;
                        description "Location of the ISA";
                    }

                    leaf success {
                        type yang:counter32;
                        description "The number of times the Python script ran successfully";
                    }

                    leaf failure {
                        type yang:counter32;
                        description "The number of times the Python script ran unsuccessfully";
                    }

                    leaf timeout {
                        type yang:counter32;
                        description "The number of times the Python script timed out while running";
                    }

                    leaf abort {
                        type yang:counter32;
                        description
                            "The number of times the Python script was aborted due to
                             rate limitation while running";
                    }

                } // list statistics

                list esa-vm-statistics {
                    key "isa-group-id esa vm";
                    description "Enter the esa-vm-statistics list instance";

                    leaf isa-group-id {
                        type uint32 {
                            range "1..4";
                        }
                        description "NAT or WLAN-GW Integrated Service Adaptor (ISA) group ID";
                    }

                    leaf esa {
                        type types-esa:esa-id;
                        description "Location of the ESA";
                    }

                    leaf vm {
                        type types-esa:vm-id;
                        description "Location of the ESA-VM";
                    }

                    leaf success {
                        type yang:counter32;
                        description "The number of times the Python script ran successfully";
                    }

                    leaf failure {
                        type yang:counter32;
                        description "The number of times the Python script ran unsuccessfully";
                    }

                    leaf timeout {
                        type yang:counter32;
                        description "The number of times the Python script timed out while running";
                    }

                    leaf abort {
                        type yang:counter32;
                        description
                            "The number of times the Python script was aborted due to
                             rate limitation while running";
                    }

                } // list esa-vm-statistics

            } // list python-script

            list python-policy {
                key "name";
                description "Enter the python-policy list instance";

                leaf name {
                    type types-sros:named-item;
                    description "Python policy name";
                }

                container cache {
                    description "Enter the cache context";

                    leaf number-of-entries {
                        type yang:gauge32;
                        description "Current number of Python cache entries.";
                    }

                } // container cache

            } // list python-policy

        } // container python

    } // grouping state-python

}
