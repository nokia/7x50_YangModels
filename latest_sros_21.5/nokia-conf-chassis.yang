submodule nokia-conf-chassis {

    yang-version "1.1";

    belongs-to nokia-conf { prefix "conf"; }

    import nokia-features                 { prefix "nokia-features"; }
    import nokia-sros-yang-extensions     { prefix "sros-ext"; }
    import nokia-types-chassis            { prefix "types-chassis"; }
    import nokia-types-sros               { prefix "types-sros"; }
    import nokia-types-system             { prefix "types-system"; }

    include nokia-conf-groups;


    sros-ext:sros-major-release "rel21";

    organization "Nokia";

    contact
        "Nokia SR OS Support
         Web: <http://www.nokia.com>";

    description
        "Nokia YANG Data model to configure Physical Chassis related parameters on SR OS based routers.

         Copyright 2016 Nokia. All rights reserved. Reproduction of this document
         is authorized on the condition that the foregoing copyright notice is included.

         This nokia-conf-chassis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-02-02";

    grouping conf-chassis {
        list chassis {
            key "chassis-class chassis-number";
            description "Enter the chassis list instance";

            leaf chassis-class {
                type types-chassis:chassis-class;
                description "Functional use of the physical chassis";
            }

            leaf chassis-number {
                type uint32 {
                    range "1..100";
                }
                description "Unique index to identify this physical chassis";
            }

            leaf monitor-filter-door {
                if-feature nokia-features:sros-filter-door-monitoring;
                type boolean;
                default "false";
                description "Allow filter door monitoring";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list power-supply {
                key "power-supply-id";
                description "Enter the power-supply list instance";

                leaf power-supply-id {
                    type uint32 {
                        range "1..31";
                    }
                    description "Unique identifier index for a power supply tray in the chassis";
                }

                leaf power-supply-type {
                    type enumeration {
                        enum "none"                         { value 0; }
                        enum "dc-single"                    { value 1; }
                        enum "ac-single"                    { value 2; }
                        enum "ac-multiple"                  { value 3; }
                        enum "auto"                         { value 4; }
                        enum "dc-multiple"                  { value 5; }
                    }
                    default "auto";
                    description "Power supply type";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list power-supply

            list peq {
                key "peq-slot";
                description "Enter the peq list instance";

                leaf peq-slot {
                    type uint32 {
                        range "1..31";
                    }
                    description "Unique identifier index for a power supply tray in the chassis";
                }

                leaf input-power-mode {
                    type uint32 {
                        range "60|80";
                    }
                    units "amperes";
                    description "Input power mode of the PEQ";
                }

                leaf peq-type {
                    type types-system:peq-type;
                    sros-ext:immutable;
                    description "APEQ type";
                }

                leaf admin-state {
                    type types-sros:admin-state;
                    default "enable";
                    description "Administrative state of the PEQ";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list peq

            list power-connection-module {
                key "pcm-slot";
                description "Enter the power-connection-module list instance";

                leaf pcm-slot {
                    type uint32 {
                        range "1..12";
                    }
                    description "Unique identifier index for a power control module in the chassis";
                }

                leaf pcm-type {
                    type types-chassis:pcm-type;
                    sros-ext:immutable;
                    description "PCM type";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list power-connection-module

            list power-module {
                key "power-module-id";
                description "Enter the power-module list instance";

                leaf power-module-id {
                    type uint32 {
                        range "1..12";
                    }
                    description "Unique identifier for a power module in chassis";
                }

                leaf power-module-type {
                    type types-chassis:power-module-type;
                    sros-ext:immutable;
                    description "Power module type";
                }

                leaf admin-state {
                    type types-sros:admin-state;
                    default "enable";
                    description "Administrative state of the power module";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list power-module

            list power-shelf {
                if-feature nokia-features:sros-power-shelf;
                key "power-shelf-id";
                description "Enter the power-shelf list instance";

                leaf power-shelf-id {
                    type uint32 {
                        range "1..2";
                    }
                    description "Unique identifier index for a power shelf in chassis";
                }

                leaf power-shelf-type {
                    type types-chassis:power-shelf-type;
                    sros-ext:immutable;
                    description "Power shelf type";
                }

                leaf admin-state {
                    type types-sros:admin-state;
                    default "enable";
                    description "Administrative state of the power shelf";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list power-module {
                    key "power-module-id";
                    description "Enter the power-module list instance";

                    leaf power-module-id {
                        type uint32 {
                            range "1..12";
                        }
                        description "Unique identifier for a power module in chassis";
                    }

                    leaf power-module-type {
                        type types-chassis:power-module-type;
                        sros-ext:immutable;
                        description "Power module type";
                    }

                    leaf admin-state {
                        type types-sros:admin-state;
                        default "enable";
                        description "Administrative state of the power module";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list power-module

            } // list power-shelf

        } // list chassis

    } // grouping conf-chassis

}
