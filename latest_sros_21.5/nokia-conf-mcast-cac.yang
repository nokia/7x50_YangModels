submodule nokia-conf-mcast-cac {

    yang-version "1.1";

    belongs-to nokia-conf { prefix "conf"; }

    import nokia-sros-yang-extensions     { prefix "sros-ext"; }
    import nokia-types-mcast-cac          { prefix "types-mcast-cac"; }
    import nokia-types-sros               { prefix "types-sros"; }

    include nokia-conf-groups;


    sros-ext:sros-major-release "rel21";

    organization "Nokia";

    contact
        "Nokia SR OS Support
         Web: <http://www.nokia.com>";

    description
        "Nokia YANG Data model to configure mcast cac on SR OS based routers.

         Copyright 2016 Nokia. All rights reserved. Reproduction of this document
         is authorized on the condition that the foregoing copyright notice is included.

         This nokia-conf-mcast-cac YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-16";

    grouping conf-mcast-cac-mcac {
        container mcac {
            description "Enter the mcac context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list interface-policy {
                key "policy-name";
                description "Enter the interface-policy list instance";

                leaf policy-name {
                    type string {
                        length "1..32";
                    }
                    description "Policy name for multicast CAC interface";
                }

                leaf description {
                    type types-sros:description;
                    description "Text description";
                }

                leaf admin-state {
                    type types-sros:admin-state;
                    default "enable";
                    description "Administrative state of the multicast CAC interface policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container bandwidth {
                    description "Enter the bandwidth context";

                    leaf total {
                        type types-mcast-cac:bandwidth-limit;
                        description "Maximum allowed bandwidth";
                    }

                    leaf mandatory {
                        type types-mcast-cac:bandwidth-limit;
                        description "Pre-reserved bandwidth for all mandatory channels";
                    }

                } // container bandwidth

            } // list interface-policy

            list policy {
                key "policy-name";
                description "Enter the policy list instance";

                leaf policy-name {
                    type string {
                        length "1..32";
                    }
                    description "Multicast CAC policy name";
                }

                leaf description {
                    type types-sros:description;
                    description "Text description";
                }

                leaf default-action {
                    type types-mcast-cac:policy-action;
                    default "discard";
                    description "Default action for this MCAC policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list bundle {
                    key "bundle-name";
                    max-elements 64;
                    description "Enter the bundle list instance";

                    leaf bundle-name {
                        type string {
                            length "1..32";
                        }
                        description "Name for the Multicast CAC policy bundle";
                    }

                    leaf admin-state {
                        type types-sros:admin-state;
                        default "disable";
                        description "Administrative state of the bundle";
                    }

                    leaf description {
                        type types-sros:description;
                        description "Text description";
                    }

                    leaf bandwidth {
                        type types-mcast-cac:bandwidth {
                            range "1..4294967295";
                        }
                        default "100";
                        description "Maximum bandwidth for this bundle";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list channel {
                        key "start end source";
                        description "Enter the channel list instance";

                        leaf start {
                            type types-sros:ip-address;
                            description "Beginning multicast IP address";
                        }

                        leaf end {
                            type types-sros:ip-address;
                            description "Ending multicast IP address";
                        }

                        leaf source {
                            type types-sros:ip-prefix;
                            description "Source prefix";
                        }

                        leaf bandwidth {
                            type types-mcast-cac:bandwidth {
                                range "10..10000000";
                            }
                            default "10";
                            description "Bandwidth required by this channel";
                        }

                        leaf priority-class {
                            type enumeration {
                                enum "low"                          { value 1; }
                                enum "high"                         { value 2; }
                            }
                            default "low";
                            description "Classification of channels used in the algorithm when LAG ports change state";
                        }

                        leaf type {
                            type types-mcast-cac:channel-type;
                            default "optional";
                            description "Channel type to be either mandatory or optional";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list channel

                    container mc-constraints {
                        description "Enter the mc-constraints context";

                        leaf use-lag-port-weight {
                            type boolean;
                            default "false";
                            description "Use LAG port weight in calculating MCAC constraints";
                        }

                        list level {
                            key "level-id";
                            description "Enter the level list instance";

                            leaf level-id {
                                type types-mcast-cac:constraints-level;
                                description "Bandwidth level ID for a multicast CAC constraint";
                            }

                            leaf bandwidth {
                                type types-mcast-cac:bandwidth {
                                    range "0..2147483647";
                                }
                                mandatory true;
                                description "Bandwidth available for this level";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list level

                        list lag-port-down {
                            key "lag-name number-down";
                            description "Enter the lag-port-down list instance";

                            leaf lag-name {
                                type types-sros:lag-interface;
                                description "LAG name";
                            }

                            leaf number-down {
                                type uint32 {
                                    range "1..64";
                                }
                                description "Number of lag ports that are down.";
                            }

                            leaf level {
                                type types-mcast-cac:constraints-level;
                                mandatory true;
                                description "Level ID to associate with number of down LAG ports";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list lag-port-down

                    } // container mc-constraints

                } // list bundle

            } // list policy

        } // container mcac

    } // grouping conf-mcast-cac-mcac

}
