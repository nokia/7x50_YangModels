submodule nokia-conf-router-segment-routing {

    yang-version "1.1";

    belongs-to nokia-conf { prefix "conf"; }

    import nokia-sros-yang-extensions     { prefix "sros-ext"; }
    import nokia-types-sros               { prefix "types-sros"; }

    include nokia-conf-bfd;
    include nokia-conf-groups;
    include nokia-conf-pxc;
    include nokia-conf-router;


    sros-ext:sros-major-release "rel21";

    organization "Nokia";

    contact
        "Nokia SR OS Support
         Web: <http://www.nokia.com>";

    description
        "Nokia YANG Data model to configure segment routing management on SR OS based routers.

         Copyright 2016 Nokia. All rights reserved. Reproduction of this document
         is authorized on the condition that the foregoing copyright notice is included.

         This nokia-conf-router-segment-routing YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-07";

    grouping conf-router-segment-routing {
        container segment-routing {
            when "../router-name = 'Base'";
            description "Enter the segment-routing context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list maintenance-policy {
                key "policy-name";
                description "Enter the maintenance-policy list instance";

                leaf policy-name {
                    type types-sros:named-item;
                    description "Maintenance policy name";
                }

                leaf admin-state {
                    type types-sros:admin-state;
                    default "disable";
                    description "Administrative state of the maintenance policy";
                }

                leaf bfd-liveness {
                    type boolean;
                    default "false";
                    description "Enable seamless BFD for segment lists of candidate path";
                }

                leaf bfd-template {
                    type leafref {
                        path "../../../../bfd/bfd-template/name";
                    }
                    description "BFD template to be used by seamless BFD";
                }

                leaf mode {
                    type enumeration {
                        enum "none"                         { value 0; }
                        enum "ecmp-protected"               { value 1; }
                        enum "linear"                       { value 2; }
                    }
                    sros-ext:auto-restart-to-modify;
                    default "none";
                    description "Protection mode for SR policy candidate paths";
                }

                leaf threshold {
                    type uint32 {
                        range "1..32";
                    }
                    default "1";
                    description "Minimum number of up S-BFD sessions for up path status";
                }

                leaf hold-down-timer {
                    type uint32 {
                        range "0..5000";
                    }
                    units "deciseconds";
                    default "0";
                    description "Hold down timer for SR policy candidate paths";
                }

                leaf revert-timer {
                    type uint32 {
                        range "0..4320";
                    }
                    units "minutes";
                    default "0";
                    description "Revert timer for SR policy candidate paths";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list maintenance-policy

            container sr-policies {
                description "Enter the sr-policies context";

                leaf admin-state {
                    type types-sros:admin-state;
                    default "disable";
                    description "Administrative state of segment routing policies";
                }

                leaf reserved-label-block {
                    type leafref {
                        path "../../../mpls-labels/reserved-label-block/label-block-name";
                    }
                    sros-ext:auto-restart-to-modify;
                    description "Reserved local block for segment routing policies";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ingress-statistics {
                    presence "Enable the ingress-statistics context";
                    description "Enable the ingress-statistics context";

                    leaf admin-state {
                        type types-sros:admin-state;
                        default "disable";
                        description "Administrative state of the traffic statistics";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ingress-statistics

                container egress-statistics {
                    presence "Enable the egress-statistics context";
                    description "Enable the egress-statistics context";

                    leaf admin-state {
                        type types-sros:admin-state;
                        default "disable";
                        description "Administrative state of the traffic statistics";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container egress-statistics

                list static-policy {
                    key "name";
                    max-elements 8192;
                    description "Enter the static-policy list instance";

                    leaf name {
                        type types-sros:named-item-64;
                        description "Name for the segment routing static policy";
                    }

                    leaf admin-state {
                        type types-sros:admin-state;
                        default "disable";
                        description "Administrative state of segment routing static policy";
                    }

                    leaf color {
                        type int64 {
                            range "0..4294967295";
                        }
                        sros-ext:auto-restart-to-modify;
                        description "Traffic flows to be steered by this policy";
                    }

                    leaf endpoint {
                        type types-sros:ip-address;
                        sros-ext:auto-restart-to-modify;
                        description "Destination of the source-routed path";
                    }

                    leaf preference {
                        type uint32;
                        sros-ext:auto-restart-to-modify;
                        default "100";
                        description "Preference value of this static policy";
                    }

                    leaf head-end {
                        type union {
                            type types-sros:ip-address;
                            type enumeration {
                                enum "local"                        { value 1; }
                            }
                        }
                        sros-ext:auto-restart-to-modify;
                        description "Head end address for this static policy";
                    }

                    leaf binding-sid {
                        type types-sros:mpls-label-or-zero;
                        description "Segment ID that opaquely represents an SR policy to upstream routers";
                    }

                    leaf distinguisher {
                        type uint32 {
                            range "1..max";
                        }
                        sros-ext:auto-restart-to-modify;
                        description "Unique value for a policy";
                    }

                    leaf maintenance-policy {
                        type leafref {
                            path "../../../maintenance-policy/policy-name";
                        }
                        description "Policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list segment-list {
                        key "seg-list-index";
                        max-elements 32;
                        description "Enter the segment-list list instance";

                        leaf seg-list-index {
                            type uint32 {
                                range "1..32";
                            }
                            description "Index for identifying a particular segment list";
                        }

                        leaf admin-state {
                            type types-sros:admin-state;
                            sros-ext:auto-restart-to-modify;
                            default "disable";
                            description "Administrative state of segment list for static policy";
                        }

                        leaf weight {
                            type uint32;
                            sros-ext:auto-restart-to-modify;
                            default "1";
                            description "Weight of this segment list";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        list segment {
                            key "segment-index";
                            max-elements 11;
                            sros-ext:auto-restart-to-modify;
                            description "Enter the segment list instance";

                            leaf segment-index {
                                type uint32 {
                                    range "1..11";
                                }
                                description "Index for identifying a particular segment list";
                            }

                            leaf mpls-label {
                                type uint32 {
                                    range "0..1048575";
                                }
                                sros-ext:auto-restart-to-modify;
                                description "Value for the MPLS label";
                            }

                            leaf-list apply-groups {
                                type leafref {
                                    path "../../../../../../../groups/group/name";
                                }
                                max-elements 8;
                                ordered-by user;
                                sros-ext:auto-restart-to-modify;
                                description "Apply a configuration group at this level";
                            }

                            leaf-list apply-groups-exclude {
                                type leafref {
                                    path "../../../../../../../groups/group/name";
                                }
                                max-elements 8;
                                ordered-by user;
                                sros-ext:auto-restart-to-modify;
                                description "Exclude a configuration group at this level";
                            }

                        } // list segment

                    } // list segment-list

                } // list static-policy

            } // container sr-policies

            container segment-routing-v6 {
                presence "Enable the segment-routing-v6 context";
                description "Enable the segment-routing-v6 context";

                leaf-list origination-fpe {
                    type leafref {
                        path "../../../../fwd-path-ext/fpe/fpe-id";
                    }
                    max-elements 1;
                    description "List of the SRv6 origination FPEs";
                }

                leaf source-address {
                    type types-sros:ipv6-unicast-address;
                    description "Source address used in the SRv6 packet";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list locator {
                    key "locator-name";
                    max-elements 16;
                    description "Enter the locator list instance";

                    leaf locator-name {
                        type types-sros:named-item-64 {
                            pattern "[^@]*" {
                                error-message "locator name cannot contain @";
                            }
                        }
                        description "SRv6 locator name";
                    }

                    leaf block-length {
                        type types-sros:prefix-length {
                            range "0..96";
                        }
                        sros-ext:auto-restart-to-modify;
                        default "0";
                        description "SRv6 locator block address length";
                    }

                    leaf function-length {
                        type types-sros:prefix-length {
                            range "20..96";
                        }
                        sros-ext:auto-restart-to-modify;
                        default "20";
                        description "Function length";
                    }

                    leaf admin-state {
                        type types-sros:admin-state;
                        default "disable";
                        description "Administrative state of the SRv6 locator";
                    }

                    leaf-list termination-fpe {
                        type leafref {
                            path "../../../../../fwd-path-ext/fpe/fpe-id";
                        }
                        max-elements 1;
                        description "List of the SRv6 termination FPE";
                    }

                    leaf algorithm {
                        type uint32 {
                            range "128..255";
                        }
                        sros-ext:auto-restart-to-modify;
                        description "Algorithm ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container prefix {
                        description "Enter the prefix context";

                        leaf ip-prefix {
                            type types-sros:ipv6-unicast-prefix;
                            sros-ext:auto-restart-to-modify;
                            description "SRv6 locator prefix";
                        }

                    } // container prefix

                    container static-function {
                        description "Enter the static-function context";

                        leaf max-entries {
                            type uint32 {
                                range "1..1048575";
                            }
                            default "1";
                            description "Maximum number of static SID functions";
                        }

                        leaf label-block {
                            type leafref {
                                path "../../../../../mpls-labels/reserved-label-block/label-block-name";
                            }
                            sros-ext:auto-restart-to-modify;
                            description "Label block for the service SIDs of the SRv6 locator";
                        }

                    } // container static-function

                } // list locator

                container base-routing-instance {
                    description "Enter the base-routing-instance context";

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list locator {
                        key "locator-name";
                        description "Enter the locator list instance";

                        leaf locator-name {
                            type leafref {
                                path "../../../locator/locator-name";
                            }
                            description "SRv6 locator name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container function {
                            description "Enter the function context";

                            list end {
                                key "value";
                                max-elements 8;
                                description "Enter the end list instance";

                                leaf value {
                                    type uint32 {
                                        range "1..1048575";
                                    }
                                    description "SRv6 End SID function value";
                                }

                                leaf srh-mode {
                                    type enumeration {
                                        enum "psp"                          { value 1; }
                                        enum "usp"                          { value 2; }
                                    }
                                    default "psp";
                                    description "Segment Routing Header (SRH) mode";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list end

                            list end-x {
                                key "value";
                                description "Enter the end-x list instance";

                                leaf value {
                                    type uint32 {
                                        range "1..1048575";
                                    }
                                    description "SRv6 End SID function value";
                                }

                                leaf srh-mode {
                                    type enumeration {
                                        enum "psp"                          { value 1; }
                                        enum "usp"                          { value 2; }
                                    }
                                    default "psp";
                                    description "Segment Routing Header (SRH) mode";
                                }

                                leaf protection {
                                    type enumeration {
                                        enum "unprotected"                  { value 0; }
                                        enum "protected"                    { value 1; }
                                    }
                                    default "protected";
                                    description "Adjacency protection for static End.x SID function";
                                }

                                leaf interface-name {
                                    type leafref {
                                        path "../../../../../../../interface/interface-name";
                                    }
                                    description "Interface name";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list end-x

                            list end-x-auto-allocate {
                                key "srh-mode protection";
                                max-elements 2;
                                description "Add a list entry for end-x-auto-allocate";

                                leaf srh-mode {
                                    type enumeration {
                                        enum "psp"                          { value 1; }
                                        enum "usp"                          { value 2; }
                                    }
                                    description "Segment Routing Header (SRH) mode";
                                }

                                leaf protection {
                                    type enumeration {
                                        enum "unprotected"                  { value 0; }
                                        enum "protected"                    { value 1; }
                                    }
                                    description "Adjacency protection for automatic End.x SID function";
                                }

                            } // list end-x-auto-allocate

                            container end-dt4 {
                                presence "Enable the end-dt4 context";
                                description "Enable the end-dt4 context";

                                leaf value {
                                    type uint32 {
                                        range "1..1048575";
                                    }
                                    description "Service SID value for base router routes";
                                }

                            } // container end-dt4

                            container end-dt6 {
                                presence "Enable the end-dt6 context";
                                description "Enable the end-dt6 context";

                                leaf value {
                                    type uint32 {
                                        range "1..1048575";
                                    }
                                    description "Service SID value for base router routes";
                                }

                            } // container end-dt6

                            container end-dt46 {
                                presence "Enable the end-dt46 context";
                                description "Enable the end-dt46 context";

                                leaf value {
                                    type uint32 {
                                        range "1..1048575";
                                    }
                                    description "Service SID value for base router routes";
                                }

                            } // container end-dt46

                        } // container function

                    } // list locator

                } // container base-routing-instance

            } // container segment-routing-v6

        } // container segment-routing

    } // grouping conf-router-segment-routing

}
