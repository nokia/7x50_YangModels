module nokia-conf {

    yang-version "1.1";

    namespace "urn:nokia.com:sros:ns:yang:sr:conf";

    prefix "conf";

    import nokia-sros-yang-extensions     { prefix "sros-ext"; }

    include nokia-conf-aaa;
    include nokia-conf-aps;
    include nokia-conf-bfd;
    include nokia-conf-bmp;
    include nokia-conf-call-trace;
    include nokia-conf-card;
    include nokia-conf-card-fp;
    include nokia-conf-cflowd;
    include nokia-conf-chassis;
    include nokia-conf-conn-prof;
    include nokia-conf-esa;
    include nokia-conf-eth-cfm;
    include nokia-conf-filter;
    include nokia-conf-filter-dhcp;
    include nokia-conf-filter-ip-exception;
    include nokia-conf-groups;
    include nokia-conf-ipsec;
    include nokia-conf-isa;
    include nokia-conf-isa-video-group;
    include nokia-conf-lag;
    include nokia-conf-log;
    include nokia-conf-macsec;
    include nokia-conf-mcast-cac;
    include nokia-conf-mcast-mgmt;
    include nokia-conf-mirror;
    include nokia-conf-multilink-bundle;
    include nokia-conf-oam-pm;
    include nokia-conf-openflow;
    include nokia-conf-policy-options;
    include nokia-conf-port;
    include nokia-conf-port-access;
    include nokia-conf-port-connector;
    include nokia-conf-port-dwdm;
    include nokia-conf-port-dwdm-coherent;
    include nokia-conf-port-eth-access;
    include nokia-conf-port-eth-dot1x;
    include nokia-conf-port-eth-efm-oam;
    include nokia-conf-port-eth-egress;
    include nokia-conf-port-eth-lldp;
    include nokia-conf-port-eth-network;
    include nokia-conf-port-ethernet;
    include nokia-conf-port-gnss;
    include nokia-conf-port-network;
    include nokia-conf-port-otu;
    include nokia-conf-port-policy;
    include nokia-conf-port-sonet;
    include nokia-conf-port-tdm;
    include nokia-conf-pw-port;
    include nokia-conf-pxc;
    include nokia-conf-python;
    include nokia-conf-qos;
    include nokia-conf-redundancy;
    include nokia-conf-router;
    include nokia-conf-router-bgp;
    include nokia-conf-router-bier;
    include nokia-conf-router-dhcp-server;
    include nokia-conf-router-firewall;
    include nokia-conf-router-gtm;
    include nokia-conf-router-igmp;
    include nokia-conf-router-isis;
    include nokia-conf-router-l2tp;
    include nokia-conf-router-ldp;
    include nokia-conf-router-mld;
    include nokia-conf-router-mpls;
    include nokia-conf-router-msdp;
    include nokia-conf-router-nat;
    include nokia-conf-router-origin-validation;
    include nokia-conf-router-ospf;
    include nokia-conf-router-ospf3;
    include nokia-conf-router-p2mp-sr-tree;
    include nokia-conf-router-pcep;
    include nokia-conf-router-pim;
    include nokia-conf-router-radius;
    include nokia-conf-router-rib-api;
    include nokia-conf-router-rip;
    include nokia-conf-router-ripng;
    include nokia-conf-router-rsvp;
    include nokia-conf-router-segment-routing;
    include nokia-conf-router-static-route;
    include nokia-conf-router-twamp-light;
    include nokia-conf-router-wpp;
    include nokia-conf-routing-options;
    include nokia-conf-saa;
    include nokia-conf-satellite;
    include nokia-conf-service;
    include nokia-conf-sfm;
    include nokia-conf-submgt-ancp;
    include nokia-conf-submgt-gtp;
    include nokia-conf-submgt-isa-filter;
    include nokia-conf-submgt-isa-policer;
    include nokia-conf-submgt-local-user-db;
    include nokia-conf-submgt-service-chaining;
    include nokia-conf-submgt-vrgw;
    include nokia-conf-submgt-wlangw;
    include nokia-conf-subscriber-mgmt;
    include nokia-conf-svc-cpipe;
    include nokia-conf-svc-epipe;
    include nokia-conf-svc-ies;
    include nokia-conf-svc-ies-grp-if-wlangw;
    include nokia-conf-svc-ies-sub-if;
    include nokia-conf-svc-ies-sub-if-wlangw;
    include nokia-conf-svc-ies-vdo-if;
    include nokia-conf-svc-ipfix;
    include nokia-conf-svc-ipipe;
    include nokia-conf-svc-nat;
    include nokia-conf-svc-sdp;
    include nokia-conf-svc-vpls;
    include nokia-conf-svc-vprn;
    include nokia-conf-svc-vprn-dhcp-server;
    include nokia-conf-svc-vprn-grp-if-wlangw;
    include nokia-conf-svc-vprn-isis;
    include nokia-conf-svc-vprn-msdp;
    include nokia-conf-svc-vprn-ospf;
    include nokia-conf-svc-vprn-ospf3;
    include nokia-conf-svc-vprn-radius;
    include nokia-conf-svc-vprn-rip;
    include nokia-conf-svc-vprn-ripng;
    include nokia-conf-svc-vprn-sub-if;
    include nokia-conf-svc-vprn-sub-if-wlangw;
    include nokia-conf-svc-vprn-twamp-light;
    include nokia-conf-svc-vprn-vdo-if;
    include nokia-conf-system;
    include nokia-conf-system-bluetooth;
    include nokia-conf-system-central-frequency-clock;
    include nokia-conf-system-cron;
    include nokia-conf-system-login-control;
    include nokia-conf-system-ned;
    include nokia-conf-system-persistence;
    include nokia-conf-system-script-control;
    include nokia-conf-system-security;
    include nokia-conf-system-security-aaa;
    include nokia-conf-system-security-cli-script;
    include nokia-conf-system-security-cpm;
    include nokia-conf-system-security-management-access-filter;
    include nokia-conf-system-security-pki;
    include nokia-conf-system-security-snmp;
    include nokia-conf-system-security-ssh;
    include nokia-conf-system-security-tls;
    include nokia-conf-system-security-user-parameters;
    include nokia-conf-system-telemetry;
    include nokia-conf-system-time;
    include nokia-conf-test-oam;
    include nokia-conf-vrrp;

    sros-ext:sros-major-release "rel21";

    organization "Nokia";

    contact
        "Nokia SR OS Support
         Web: <http://www.nokia.com>";

    description
        "Nokia YANG Data model to configure all data on SR OS based routers.

         Copyright 2016 Nokia. All rights reserved. Reproduction of this document
         is authorized on the condition that the foregoing copyright notice is included.

         This nokia-conf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-12-03";

    container configure {
        description "Enter the configure context";

        leaf-list apply-groups {
            type leafref {
                path "../groups/group/name";
            }
            max-elements 8;
            ordered-by user;
            description "Apply a configuration group at this level";
        }

        uses conf-aaa;
        uses conf-aps;
        uses conf-bfd;
        uses conf-bmp;
        uses conf-call-trace;
        uses conf-card;
        uses conf-cflowd;
        uses conf-chassis;
        uses conf-conn-prof-connection-profile;
        uses conf-esa;
        uses conf-eth-cfm;
        uses conf-filter;
        uses conf-pxc-fwd-path-ext;
        uses conf-groups;
        uses conf-ipsec;
        uses conf-isa;
        uses conf-lag;
        uses conf-log;
        uses conf-macsec;
        uses conf-mcast-cac-mcac;
        uses conf-mirror;
        uses conf-mcast-mgmt-multicast-management;
        uses conf-multilink-bundle;
        uses conf-oam-pm;
        uses conf-openflow;
        uses conf-policy-options;
        uses conf-port;
        uses conf-port-policy;
        uses conf-pxc-port-xc;
        uses conf-pw-port;
        uses conf-python;
        uses conf-qos;
        uses conf-redundancy;
        uses conf-router;
        uses conf-routing-options;
        uses conf-saa;
        uses conf-satellite;
        uses conf-service;
        uses conf-sfm;
        uses conf-subscriber-mgmt;
        uses conf-system;
        uses conf-test-oam;
        uses conf-vrrp;
    } // container configure

}
