module nokia-datastores {

  yang-version 1.1;

  namespace "urn:nokia.com:sros:ns:yang:sr:datastores";

  prefix nokia-ds;

  import ietf-datastores { prefix ds; }

  description "This YANG module defines a set of identities for proprietary Nokia SR OS datastores.";

  revision "2020-12-04" {
    description "Initial nokia revision.";
    reference
      "Proprietary Nokia SR OS datastores";

  }

  identity configure-region {
    base ds:datastore;
  }

  identity configure-running {
    base configure-region;
    description
      "The configure-running configuration datastore.";
  }

  identity configure-candidate {
    base configure-region;
    description
      "The configure-candidate configuration datastore.";
  }

  identity configure-startup {
    base configure-region;
    description
      "The configure-startup configuration datastore.";
  }

  identity configure-intended {
    base configure-region;
    description
      "The configure-intended configuration datastore.";
  }

  identity li-region {
    base ds:datastore;
  }

  identity li-running {
    base li-region;
    description
      "The li-running configuration datastore.";
  }

  identity li-candidate {
    base li-region;
    description
      "The li-candidate configuration datastore.";
  }

  identity li-startup {
    base li-region;
    description
      "The li-startup configuration datastore.";
  }

  identity li-intended {
    base li-region;
    description
      "The li-intended configuration datastore.";
  }

  identity bof-region {
    base ds:datastore;
  }

  identity bof-running {
    base bof-region;
    description
      "The bof-running configuration datastore.";
  }

  identity bof-candidate {
    base bof-region;
    description
      "The bof-candidate configuration datastore.";
  }

  identity bof-startup {
    base bof-region;
    description
      "The bof-startup configuration datastore.";
  }

  identity bof-intended {
    base bof-region;
    description
      "The bof-intended configuration datastore.";
  }

}  // module nokia-datastores
