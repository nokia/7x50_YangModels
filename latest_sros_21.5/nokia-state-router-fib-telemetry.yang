submodule nokia-state-router-fib-telemetry {

    yang-version "1.1";

    belongs-to nokia-state { prefix "state"; }

    import ietf-yang-types                { prefix "yang"; }
    import nokia-sros-yang-extensions     { prefix "sros-ext"; }
    import nokia-types-mpls               { prefix "types-mpls"; }
    import nokia-types-router             { prefix "types-router"; }
    import nokia-types-sros               { prefix "types-sros"; }


    sros-ext:sros-major-release "rel21";

    organization "Nokia";

    contact
        "Nokia SR OS Support
         Web: <http://www.nokia.com>";

    description
        "Nokia YANG Data model with operational state for FIB Telemetry state models on SR OS based routers.

         Copyright 2016 Nokia. All rights reserved. Reproduction of this document
         is authorized on the condition that the foregoing copyright notice is included.

         This nokia-state-router-fib-telemetry YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-01-27";

    grouping state-router-fib-telemetry-route-fib {
        container route-fib {
            description "Enter the route-fib context";

            container ipv4 {
                description "Enter the ipv4 context";

                list route {
                    key "prefix";
                    description "Enter the route list instance";

                    leaf prefix {
                        type types-sros:ipv4-prefix;
                        description "Indicates the IPv4 prefix for this route FIB entry.";
                    }

                    leaf last-updated {
                        type yang:date-and-time;
                        description "Time when route acknowledged as programmed on the line-cards.";
                    }

                    leaf protocol {
                        type types-router:protocol-type;
                        description "Identifies the routing protocol.";
                    }

                    list next-hop-group {
                        key "index";
                        description "Enter the next-hop-group list instance";

                        leaf index {
                            type uint32;
                            description "Index of next-hop group.";
                        }

                        container primary-next-hop {
                            description "Enter the primary-next-hop context";

                            leaf is-indirect {
                                type boolean;
                                description
                                    "If true, this indicates the next-hop is an indirect next-hop IP.
                                     An additional route lookup will have to be made to map the indirect
                                     IP address to the resolving IP address. The 'if-index' leaf will be
                                     not be provided in this case.";
                            }

                            leaf is-tunnel {
                                type boolean;
                                description
                                    "If true, this indicates indicates the next-hop is a tunnel destination
                                     (the 'address' leaf is a far-end tunnel destination). The 'if-index'
                                     leaf will be not be provided in this case.";
                            }

                            leaf is-backup {
                                type boolean;
                                description
                                    "If true, this indicates the next-hop is a BGP backup next-hop. The BGP
                                     backup next-hop is used only if all the primary next-hops are down.";
                            }

                            leaf if-index {
                                type uint32;
                                description
                                    "This is the index of the egress interface where the
                                     next-hop resides. If this is not provided, is it not
                                     valid for the type of next-hop.

                                     If the next-hop is not an indirect or tunneled next-hop
                                     and both the 'if-index' and the 'address' leafs are not
                                     present, the next-hop is a blackhole next-hop.";
                            }

                            leaf address {
                                type types-sros:ip-address;
                                description
                                    "Indicates the next-hop IP address of the route entry.

                                     The 'address' is a tunnel or SDP far-end IP if the 'is-tunnel'
                                     leaf is true.

                                     The 'address' is an indirect IP if the 'is-indirect' leaf
                                     is true.

                                     If the next-hop is not an indirect or tunneled next-hop
                                     and both the 'if-index' and the 'address' leafs are not
                                     present, the next-hop is a blackhole next-hop.";
                            }

                            leaf tunnel-id {
                                type uint32;
                                description
                                    "This is provided if the 'is-tunnel' leaf is true and the
                                     tunnel is not an LDP/BGP/UDP/GRE/SR tunnel.

                                     This indicates the next-hop tunnel ID or SDP ID
                                     associated with the tunnel.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container primary-next-hop

                        container backup-next-hop {
                            description "Enter the backup-next-hop context";

                            leaf is-indirect {
                                type boolean;
                                description
                                    "If true, this indicates the next-hop is an indirect next-hop IP.
                                     An additional route lookup will have to be made to map the indirect
                                     IP address to the resolving IP address. The 'if-index' leaf will be
                                     not be provided in this case.";
                            }

                            leaf is-tunnel {
                                type boolean;
                                description
                                    "If true, this indicates indicates the next-hop is a tunnel destination
                                     (the 'address' leaf is a far-end tunnel destination). The 'if-index'
                                     leaf will be not be provided in this case.";
                            }

                            leaf is-backup {
                                type boolean;
                                description
                                    "If true, this indicates the next-hop is a BGP backup next-hop. The BGP
                                     backup next-hop is used only if all the primary next-hops are down.";
                            }

                            leaf if-index {
                                type uint32;
                                description
                                    "This is the index of the egress interface where the
                                     next-hop resides. If this is not provided, is it not
                                     valid for the type of next-hop.

                                     If the next-hop is not an indirect or tunneled next-hop
                                     and both the 'if-index' and the 'address' leafs are not
                                     present, the next-hop is a blackhole next-hop.";
                            }

                            leaf address {
                                type types-sros:ip-address;
                                description
                                    "Indicates the next-hop IP address of the route entry.

                                     The 'address' is a tunnel or SDP far-end IP if the 'is-tunnel'
                                     leaf is true.

                                     The 'address' is an indirect IP if the 'is-indirect' leaf
                                     is true.

                                     If the next-hop is not an indirect or tunneled next-hop
                                     and both the 'if-index' and the 'address' leafs are not
                                     present, the next-hop is a blackhole next-hop.";
                            }

                            leaf tunnel-id {
                                type uint32;
                                description
                                    "This is provided if the 'is-tunnel' leaf is true and the
                                     tunnel is not an LDP/BGP/UDP/GRE/SR tunnel.

                                     This indicates the next-hop tunnel ID or SDP ID
                                     associated with the tunnel.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container backup-next-hop

                    } // list next-hop-group

                } // list route

            } // container ipv4

            container ipv6 {
                description "Enter the ipv6 context";

                list route {
                    key "prefix";
                    description "Enter the route list instance";

                    leaf prefix {
                        type types-sros:ipv6-prefix;
                        description "Indicates the IPv6 prefix for this route FIB entry.";
                    }

                    leaf last-updated {
                        type yang:date-and-time;
                        description "Time when route acknowledged as programmed on the line-cards.";
                    }

                    leaf protocol {
                        type types-router:protocol-type;
                        description "Identifies the routing protocol.";
                    }

                    list next-hop-group {
                        key "index";
                        description "Enter the next-hop-group list instance";

                        leaf index {
                            type uint32;
                            description "Index of next-hop group.";
                        }

                        container primary-next-hop {
                            description "Enter the primary-next-hop context";

                            leaf is-indirect {
                                type boolean;
                                description
                                    "If true, this indicates the next-hop is an indirect next-hop IP.
                                     An additional route lookup will have to be made to map the indirect
                                     IP address to the resolving IP address. The 'if-index' leaf will be
                                     not be provided in this case.";
                            }

                            leaf is-tunnel {
                                type boolean;
                                description
                                    "If true, this indicates indicates the next-hop is a tunnel destination
                                     (the 'address' leaf is a far-end tunnel destination). The 'if-index'
                                     leaf will be not be provided in this case.";
                            }

                            leaf is-backup {
                                type boolean;
                                description
                                    "If true, this indicates the next-hop is a BGP backup next-hop. The BGP
                                     backup next-hop is used only if all the primary next-hops are down.";
                            }

                            leaf if-index {
                                type uint32;
                                description
                                    "This is the index of the egress interface where the
                                     next-hop resides. If this is not provided, is it not
                                     valid for the type of next-hop.

                                     If the next-hop is not an indirect or tunneled next-hop
                                     and both the 'if-index' and the 'address' leafs are not
                                     present, the next-hop is a blackhole next-hop.";
                            }

                            leaf address {
                                type types-sros:ip-address;
                                description
                                    "Indicates the next-hop IP address of the route entry.

                                     The 'address' is a tunnel or SDP far-end IP if the 'is-tunnel'
                                     leaf is true.

                                     The 'address' is an indirect IP if the 'is-indirect' leaf
                                     is true.

                                     If the next-hop is not an indirect or tunneled next-hop
                                     and both the 'if-index' and the 'address' leafs are not
                                     present, the next-hop is a blackhole next-hop.";
                            }

                            leaf tunnel-id {
                                type uint32;
                                description
                                    "This is provided if the 'is-tunnel' leaf is true and the
                                     tunnel is not an LDP/BGP/UDP/GRE/SR tunnel.

                                     This indicates the next-hop tunnel ID or SDP ID
                                     associated with the tunnel.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container primary-next-hop

                        container backup-next-hop {
                            description "Enter the backup-next-hop context";

                            leaf is-indirect {
                                type boolean;
                                description
                                    "If true, this indicates the next-hop is an indirect next-hop IP.
                                     An additional route lookup will have to be made to map the indirect
                                     IP address to the resolving IP address. The 'if-index' leaf will be
                                     not be provided in this case.";
                            }

                            leaf is-tunnel {
                                type boolean;
                                description
                                    "If true, this indicates indicates the next-hop is a tunnel destination
                                     (the 'address' leaf is a far-end tunnel destination). The 'if-index'
                                     leaf will be not be provided in this case.";
                            }

                            leaf is-backup {
                                type boolean;
                                description
                                    "If true, this indicates the next-hop is a BGP backup next-hop. The BGP
                                     backup next-hop is used only if all the primary next-hops are down.";
                            }

                            leaf if-index {
                                type uint32;
                                description
                                    "This is the index of the egress interface where the
                                     next-hop resides. If this is not provided, is it not
                                     valid for the type of next-hop.

                                     If the next-hop is not an indirect or tunneled next-hop
                                     and both the 'if-index' and the 'address' leafs are not
                                     present, the next-hop is a blackhole next-hop.";
                            }

                            leaf address {
                                type types-sros:ip-address;
                                description
                                    "Indicates the next-hop IP address of the route entry.

                                     The 'address' is a tunnel or SDP far-end IP if the 'is-tunnel'
                                     leaf is true.

                                     The 'address' is an indirect IP if the 'is-indirect' leaf
                                     is true.

                                     If the next-hop is not an indirect or tunneled next-hop
                                     and both the 'if-index' and the 'address' leafs are not
                                     present, the next-hop is a blackhole next-hop.";
                            }

                            leaf tunnel-id {
                                type uint32;
                                description
                                    "This is provided if the 'is-tunnel' leaf is true and the
                                     tunnel is not an LDP/BGP/UDP/GRE/SR tunnel.

                                     This indicates the next-hop tunnel ID or SDP ID
                                     associated with the tunnel.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container backup-next-hop

                    } // list next-hop-group

                } // list route

            } // container ipv6

        } // container route-fib

    } // grouping state-router-fib-telemetry-route-fib

    grouping state-router-fib-telemetry-tunnel-fib {
        container tunnel-fib {
            description "Enter the tunnel-fib context";

            container ipv4 {
                description "Enter the ipv4 context";

                list tunnel {
                    key "prefix index";
                    description "Enter the tunnel list instance";

                    leaf prefix {
                        type types-sros:ipv4-prefix;
                        description "The value of this object specifies the IPv4 prefix.";
                    }

                    leaf index {
                        type uint64;
                        description "This is the index of the next tunnel to the same destination";
                    }

                    leaf preference {
                        type uint8;
                        description
                            "Indicates the priority of this tunnel versus the other tunnels
                             from different sources.

                             Lowest value signifies the most preferred entry in the table.";
                    }

                    leaf protocol {
                        type types-router:protocol-type;
                        description "Indicates the owner of this tunnel.";
                    }

                    leaf instance {
                        type uint32;
                        description "Indicates an instance of the tunnel of the type indicated by protocol.";
                    }

                    leaf tunnel-id {
                        type types-sros:tunnel-id;
                        description "Indicates the global tunnel ID that represents a particular tunnel.";
                    }

                    leaf last-updated {
                        type yang:date-and-time;
                        description "Indicates when this entry was last updated";
                    }

                    list next-hop-group {
                        key "index";
                        description "Enter the next-hop-group list instance";

                        leaf index {
                            type uint32;
                            description "Index of next-hop group.";
                        }

                        leaf group-id {
                            type uint32;
                            description
                                "Present only for RIB-API provided next-hop groups and is the ID
                                 provided for the next-hop group in the RIB-API call.";
                        }

                        leaf primary-active {
                            type boolean;
                            description
                                "Flag indicating if the primary next-hop is currently active (used for
                                 forwarding traffic). If the primary is not active, then the backup
                                 is active. This flag is useful only if a backup next-hop is present.";
                        }

                        leaf weight {
                            type uint32;
                            description "This is the normalized weight associated with this next-hop.";
                        }

                        container primary-next-hop {
                            description "Enter the primary-next-hop context";

                            leaf is-tunnel {
                                type boolean;
                                description
                                    "If true, this indicates indicates the next-hop is a tunnel destination
                                     (the 'address' leaf is a far-end tunnel destination). The 'if-index'
                                     leaf will be not be provided in this case.";
                            }

                            leaf if-index {
                                type uint32;
                                description
                                    "This is the index of the egress interface where the
                                     next-hop resides. If this is not provided, is it not
                                     valid for the type of next-hop.";
                            }

                            leaf address {
                                type types-sros:ip-address;
                                description
                                    "Indicates the next-hop IP address of the route entry.
                                     This may be a tunnel far-end IP if the tunnel has an
                                     underlying tunnel. Whether this is a tunnel far-end IP
                                     is indicated by the 'is-tunnel' flag.";
                            }

                            leaf tunnel-id {
                                type uint32;
                                description
                                    "This is provided if the 'is-tunnel' leaf is true and the
                                     tunnel is not an LDP/BGP/UDP/GRE/SR tunnel.

                                     This indicates the next-hop tunnel ID associated with the tunnel.";
                            }

                            leaf is-backup {
                                type boolean;
                                description
                                    "If true, this indicates the next-hop is a BGP backup next-hop. The BGP
                                     backup next-hop is used only if all the primary next-hops are down.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container primary-next-hop

                        container backup-next-hop {
                            description "Enter the backup-next-hop context";

                            leaf is-tunnel {
                                type boolean;
                                description
                                    "If true, this indicates indicates the next-hop is a tunnel destination
                                     (the 'address' leaf is a far-end tunnel destination). The 'if-index'
                                     leaf will be not be provided in this case.";
                            }

                            leaf if-index {
                                type uint32;
                                description
                                    "This is the index of the egress interface where the
                                     next-hop resides. If this is not provided, is it not
                                     valid for the type of next-hop.";
                            }

                            leaf address {
                                type types-sros:ip-address;
                                description
                                    "Indicates the next-hop IP address of the route entry.
                                     This may be a tunnel far-end IP if the tunnel has an
                                     underlying tunnel. Whether this is a tunnel far-end IP
                                     is indicated by the 'is-tunnel' flag.";
                            }

                            leaf tunnel-id {
                                type uint32;
                                description
                                    "This is provided if the 'is-tunnel' leaf is true and the
                                     tunnel is not an LDP/BGP/UDP/GRE/SR tunnel.

                                     This indicates the next-hop tunnel ID associated with the tunnel.";
                            }

                            leaf is-backup {
                                type boolean;
                                description
                                    "If true, this indicates the next-hop is a BGP backup next-hop. The BGP
                                     backup next-hop is used only if all the primary next-hops are down.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container backup-next-hop

                    } // list next-hop-group

                } // list tunnel

            } // container ipv4

            container ipv6 {
                description "Enter the ipv6 context";

                list tunnel {
                    key "prefix index";
                    description "Enter the tunnel list instance";

                    leaf prefix {
                        type types-sros:ipv6-prefix;
                        description "The value of this object specifies the IPv6 prefix.";
                    }

                    leaf index {
                        type uint64;
                        description "This is the index of the next tunnel to the same destination";
                    }

                    leaf preference {
                        type uint8;
                        description
                            "Indicates the priority of this tunnel versus the other tunnels
                             from different sources.

                             Lowest value signifies the most preferred entry in the table.";
                    }

                    leaf protocol {
                        type types-router:protocol-type;
                        description "Indicates the owner of this tunnel.";
                    }

                    leaf instance {
                        type uint32;
                        description "Indicates an instance of the tunnel of the type indicated by protocol.";
                    }

                    leaf tunnel-id {
                        type types-sros:tunnel-id;
                        description "Indicates the global tunnel ID that represents a particular tunnel.";
                    }

                    leaf last-updated {
                        type yang:date-and-time;
                        description "Indicates when this entry was last updated";
                    }

                    list next-hop-group {
                        key "index";
                        description "Enter the next-hop-group list instance";

                        leaf index {
                            type uint32;
                            description "Index of next-hop group.";
                        }

                        leaf group-id {
                            type uint32;
                            description
                                "Present only for RIB-API provided next-hop groups and is the ID
                                 provided for the next-hop group in the RIB-API call.";
                        }

                        leaf primary-active {
                            type boolean;
                            description
                                "Flag indicating if the primary next-hop is currently active (used for
                                 forwarding traffic). If the primary is not active, then the backup
                                 is active. This flag is useful only if a backup next-hop is present.";
                        }

                        leaf weight {
                            type uint32;
                            description "This is the normalized weight associated with this next-hop.";
                        }

                        container primary-next-hop {
                            description "Enter the primary-next-hop context";

                            leaf is-tunnel {
                                type boolean;
                                description
                                    "If true, this indicates indicates the next-hop is a tunnel destination
                                     (the 'address' leaf is a far-end tunnel destination). The 'if-index'
                                     leaf will be not be provided in this case.";
                            }

                            leaf if-index {
                                type uint32;
                                description
                                    "This is the index of the egress interface where the
                                     next-hop resides. If this is not provided, is it not
                                     valid for the type of next-hop.";
                            }

                            leaf address {
                                type types-sros:ip-address;
                                description
                                    "Indicates the next-hop IP address of the route entry.
                                     This may be a tunnel far-end IP if the tunnel has an
                                     underlying tunnel. Whether this is a tunnel far-end IP
                                     is indicated by the 'is-tunnel' flag.";
                            }

                            leaf tunnel-id {
                                type uint32;
                                description
                                    "This is provided if the 'is-tunnel' leaf is true and the
                                     tunnel is not an LDP/BGP/UDP/GRE/SR tunnel.

                                     This indicates the next-hop tunnel ID associated with the tunnel.";
                            }

                            leaf is-backup {
                                type boolean;
                                description
                                    "If true, this indicates the next-hop is a BGP backup next-hop. The BGP
                                     backup next-hop is used only if all the primary next-hops are down.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container primary-next-hop

                        container backup-next-hop {
                            description "Enter the backup-next-hop context";

                            leaf is-tunnel {
                                type boolean;
                                description
                                    "If true, this indicates indicates the next-hop is a tunnel destination
                                     (the 'address' leaf is a far-end tunnel destination). The 'if-index'
                                     leaf will be not be provided in this case.";
                            }

                            leaf if-index {
                                type uint32;
                                description
                                    "This is the index of the egress interface where the
                                     next-hop resides. If this is not provided, is it not
                                     valid for the type of next-hop.";
                            }

                            leaf address {
                                type types-sros:ip-address;
                                description
                                    "Indicates the next-hop IP address of the route entry.
                                     This may be a tunnel far-end IP if the tunnel has an
                                     underlying tunnel. Whether this is a tunnel far-end IP
                                     is indicated by the 'is-tunnel' flag.";
                            }

                            leaf tunnel-id {
                                type uint32;
                                description
                                    "This is provided if the 'is-tunnel' leaf is true and the
                                     tunnel is not an LDP/BGP/UDP/GRE/SR tunnel.

                                     This indicates the next-hop tunnel ID associated with the tunnel.";
                            }

                            leaf is-backup {
                                type boolean;
                                description
                                    "If true, this indicates the next-hop is a BGP backup next-hop. The BGP
                                     backup next-hop is used only if all the primary next-hops are down.";
                            }

                            leaf tunnel-type {
                                type types-router:tunnel-type;
                                description "Indicates the tunnel owner if the next-hop is a tunnel far-end.";
                            }

                            leaf tunnel-instance {
                                type uint32;
                                description "Indicates the instance for SR type (ISIS/OSPF/OSPFv3) tunnels.";
                            }

                        } // container backup-next-hop

                    } // list next-hop-group

                } // list tunnel

            } // container ipv6

        } // container tunnel-fib

    } // grouping state-router-fib-telemetry-tunnel-fib

    grouping state-router-fib-telemetry-label-fib {
        container label-fib {
            description "Enter the label-fib context";

            list label {
                key "label";
                description "Enter the label list instance";

                leaf label {
                    type types-sros:mpls-label-full-range;
                    description "MPLS label.";
                }

                leaf protocol {
                    type types-mpls:ilm-owner-type;
                    description "Indicates the owner of this ilm entry.";
                }

                leaf statistics {
                    type boolean;
                    description "Indicates if stats is enabled in this ILM entry.";
                }

                leaf last-updated {
                    type yang:date-and-time;
                    description "Indicates when this entry was last updated";
                }

                list next-hop-group {
                    key "index";
                    description "Enter the next-hop-group list instance";

                    leaf index {
                        type uint32;
                        description "Index of next-hop group.";
                    }

                    leaf group-id {
                        type uint32;
                        description
                            "Present only for RIB-API provided next-hop groups and is the ID
                             provided for the next-hop group in the RIB-API call.";
                    }

                    leaf primary-active {
                        type boolean;
                        description
                            "Flag indicating if the primary next-hop is currently active (used for
                             forwarding traffic). If the primary is not active, then the backup
                             is active. This flag is useful only if a backup next-hop is present.";
                    }

                    leaf weight {
                        type uint32;
                        description "This is the normalized weight associated with this next-hop.";
                    }

                    container primary-next-hop {
                        description "Enter the primary-next-hop context";

                        leaf is-tunnel {
                            type boolean;
                            description
                                "If true, this indicates indicates the next-hop is a tunnel destination
                                 (the 'address' leaf is a far-end tunnel destination). The 'if-index'
                                 leaf will be not be provided in this case.";
                        }

                        leaf if-index {
                            type uint32;
                            description
                                "This is the index of the egress interface where the
                                 next-hop resides. If this is not provided, is it not
                                 valid for the type of next-hop.";
                        }

                        leaf address {
                            type types-sros:ip-address;
                            description
                                "Indicates the next-hop IP address of the route entry.
                                 This may be a tunnel far-end IP if the tunnel has an
                                 underlying tunnel. Whether this is a tunnel far-end IP
                                 is indicated by the 'is-tunnel' flag.";
                        }

                        leaf tunnel-id {
                            type uint32;
                            description
                                "This is provided if the 'is-tunnel' leaf is true and the
                                 tunnel is not an LDP/BGP/UDP/GRE/SR tunnel.

                                 This indicates the next-hop tunnel ID associated with the tunnel.";
                        }

                        list label-stack {
                            key "label-index";
                            description "Enter the label-stack list instance";

                            leaf label-index {
                                type uint32;
                                description "0 based label index; item 0 is the outermost label.";
                            }

                            leaf label {
                                type types-sros:mpls-label-full-range;
                                description "MPLS label.";
                            }

                        } // list label-stack

                    } // container primary-next-hop

                    container backup-next-hop {
                        description "Enter the backup-next-hop context";

                        leaf is-tunnel {
                            type boolean;
                            description
                                "If true, this indicates indicates the next-hop is a tunnel destination
                                 (the 'address' leaf is a far-end tunnel destination). The 'if-index'
                                 leaf will be not be provided in this case.";
                        }

                        leaf if-index {
                            type uint32;
                            description
                                "This is the index of the egress interface where the
                                 next-hop resides. If this is not provided, is it not
                                 valid for the type of next-hop.";
                        }

                        leaf address {
                            type types-sros:ip-address;
                            description
                                "Indicates the next-hop IP address of the route entry.
                                 This may be a tunnel far-end IP if the tunnel has an
                                 underlying tunnel. Whether this is a tunnel far-end IP
                                 is indicated by the 'is-tunnel' flag.";
                        }

                        leaf tunnel-id {
                            type uint32;
                            description
                                "This is provided if the 'is-tunnel' leaf is true and the
                                 tunnel is not an LDP/BGP/UDP/GRE/SR tunnel.

                                 This indicates the next-hop tunnel ID associated with the tunnel.";
                        }

                        list label-stack {
                            key "label-index";
                            description "Enter the label-stack list instance";

                            leaf label-index {
                                type uint32;
                                description "0 based label index; item 0 is the outermost label.";
                            }

                            leaf label {
                                type types-sros:mpls-label-full-range;
                                description "MPLS label.";
                            }

                        } // list label-stack

                    } // container backup-next-hop

                } // list next-hop-group

            } // list label

        } // container label-fib

    } // grouping state-router-fib-telemetry-label-fib

}
