module nokia-sr-openconfig-network-instance-deviations {

    namespace "urn:nokia.com:sros:ns:yang:sr:openconfig_network_instance_deviations";

    prefix "nokia-sr-oc-netinst-devs";

    import nokia-sros-yang-extensions     { prefix "sros-ext"; }
    import openconfig-aft                 { prefix "oc-aft"; }
    import openconfig-bgp                 { prefix "oc-bgp"; }
    import openconfig-extensions          { prefix "oc-ext"; }
    import openconfig-igmp                { prefix "oc-igmp"; }
    import openconfig-interfaces          { prefix "oc-if"; }
    import openconfig-isis                { prefix "oc-isis"; }
    import openconfig-local-routing       { prefix "oc-loc-rt"; }
    import openconfig-mpls                { prefix "oc-mpls"; }
    import openconfig-network-instance    { prefix "oc-netinst"; }
    import openconfig-network-instance-l3 { prefix "oc-ni-l3"; }
    import openconfig-network-instance-types { prefix "oc-ni-types"; }
    import openconfig-ospfv2              { prefix "oc-ospfv2"; }
    import openconfig-policy-forwarding   { prefix "oc-pf"; }
    import openconfig-policy-types        { prefix "oc-pol-types"; }
    import openconfig-routing-policy      { prefix "oc-rpol"; }
    import openconfig-types               { prefix "oc-types"; }

    sros-ext:sros-major-release "rel21";

    organization "Nokia";

    contact
        "Nokia SR OS Support
         Web: <http://www.nokia.com>";

    description
        "This module contains the list of deviations against the openconfig-network-instance
          module for the Nokia SR OS based routers.

         Copyright 2016 Nokia. All rights reserved. Reproduction of this document
         is authorized on the condition that the foregoing copyright notice is included.

         This nokia-sr-openconfig-network-instance-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-02-28";

    deviation /oc-netinst:network-instances/oc-netinst:network-instance/oc-netinst:fdb {
        deviate not-supported;
    }

    deviation /oc-netinst:network-instances/oc-netinst:network-instance/oc-netinst:config/oc-netinst:enabled {
        deviate not-supported;
    }

    deviation /oc-netinst:network-instances/oc-netinst:network-instance/oc-netinst:config/oc-netinst:description {
        deviate replace {
            type string {
                length 1..80;
            }
        }
    }

    deviation /oc-netinst:network-instances/oc-netinst:network-instance/oc-netinst:config/oc-netinst:route-distinguisher {
        deviate not-supported;
    }

    deviation /oc-netinst:network-instances/oc-netinst:network-instance/oc-netinst:config/oc-netinst:enabled-address-families {
        deviate not-supported;
    }

    deviation /oc-netinst:network-instances/oc-netinst:network-instance/oc-netinst:config/oc-netinst:mtu {
        deviate not-supported;
    }

    deviation /oc-netinst:network-instances/oc-netinst:network-instance/oc-netinst:state/oc-netinst:enabled {
        deviate not-supported;
    }

    deviation /oc-netinst:network-instances/oc-netinst:network-instance/oc-netinst:state/oc-netinst:description {
        deviate replace {
            type string {
                length 1..80;
            }
        }
    }

    deviation /oc-netinst:network-instances/oc-netinst:network-instance/oc-netinst:state/oc-netinst:route-distinguisher {
        deviate not-supported;
    }

    deviation /oc-netinst:network-instances/oc-netinst:network-instance/oc-netinst:state/oc-netinst:enabled-address-families {
        deviate not-supported;
    }

    deviation /oc-netinst:network-instances/oc-netinst:network-instance/oc-netinst:state/oc-netinst:mtu {
        deviate not-supported;
    }

    deviation /oc-netinst:network-instances/oc-netinst:network-instance/oc-netinst:encapsulation {
        deviate not-supported;
    }

    deviation /oc-netinst:network-instances/oc-netinst:network-instance/oc-netinst:inter-instance-policies {
        deviate not-supported;
    }

    deviation /oc-netinst:network-instances/oc-netinst:network-instance/oc-netinst:table-connections {
        deviate not-supported;
    }

    deviation /oc-netinst:network-instances/oc-netinst:network-instance/oc-netinst:interfaces/oc-netinst:interface/oc-netinst:config/oc-netinst:interface {
        deviate add {
            mandatory true;
        }
    }

    deviation /oc-netinst:network-instances/oc-netinst:network-instance/oc-netinst:interfaces/oc-netinst:interface/oc-netinst:config/oc-netinst:subinterface {
        deviate add {
            mandatory true;
        }
    }

    deviation /oc-netinst:network-instances/oc-netinst:network-instance/oc-netinst:interfaces/oc-netinst:interface/oc-netinst:state/oc-netinst:interface {
        deviate add {
            mandatory true;
        }
    }

    deviation /oc-netinst:network-instances/oc-netinst:network-instance/oc-netinst:interfaces/oc-netinst:interface/oc-netinst:state/oc-netinst:subinterface {
        deviate add {
            mandatory true;
        }
    }

    deviation /oc-netinst:network-instances/oc-netinst:network-instance/oc-netinst:tables {
        deviate not-supported;
    }

    deviation /oc-netinst:network-instances/oc-netinst:network-instance/oc-netinst:connection-points {
        deviate not-supported;
    }

    deviation /oc-netinst:network-instances/oc-netinst:network-instance/oc-netinst:segment-routing {
        deviate not-supported;
    }

    deviation /oc-netinst:network-instances/oc-netinst:network-instance/oc-netinst:vlans {
        deviate not-supported;
    }

    deviation /oc-netinst:network-instances/oc-netinst:network-instance/oc-netinst:policy-forwarding {
        deviate not-supported;
    }

    deviation /oc-netinst:network-instances/oc-netinst:network-instance/oc-netinst:afts {
        deviate not-supported;
    }

    deviation /oc-netinst:network-instances/oc-netinst:network-instance/oc-netinst:protocols/oc-netinst:protocol/oc-netinst:config/oc-netinst:default-metric {
        deviate not-supported;
    }

    deviation /oc-netinst:network-instances/oc-netinst:network-instance/oc-netinst:protocols/oc-netinst:protocol/oc-netinst:state/oc-netinst:default-metric {
        deviate not-supported;
    }

    deviation /oc-netinst:network-instances/oc-netinst:network-instance/oc-netinst:protocols/oc-netinst:protocol/oc-netinst:ospfv2 {
        deviate not-supported;
    }

}
