submodule nokia-conf-router-igmp {

    yang-version "1.1";

    belongs-to nokia-conf { prefix "conf"; }

    import nokia-sros-yang-extensions     { prefix "sros-ext"; }
    import nokia-types-igmp               { prefix "types-igmp"; }
    import nokia-types-mcast-cac          { prefix "types-mcast-cac"; }
    import nokia-types-services           { prefix "types-services"; }
    import nokia-types-sros               { prefix "types-sros"; }

    include nokia-conf-groups;
    include nokia-conf-mcast-cac;
    include nokia-conf-policy-options;
    include nokia-conf-router;
    include nokia-conf-service;
    include nokia-conf-svc-ies;
    include nokia-conf-svc-ies-sub-if;
    include nokia-conf-svc-vprn;
    include nokia-conf-svc-vprn-sub-if;


    sros-ext:sros-major-release "rel21";

    organization "Nokia";

    contact
        "Nokia SR OS Support
         Web: <http://www.nokia.com>";

    description
        "Nokia YANG Data model to configure igmp protocol on SR OS based routers.

         Copyright 2016 Nokia. All rights reserved. Reproduction of this document
         is authorized on the condition that the foregoing copyright notice is included.

         This nokia-conf-router-igmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-02-02";

    grouping conf-router-igmp {
        container igmp {
            presence "Enable the igmp context";
            description "Enable the igmp context";

            leaf group-if-query-source-address {
                type types-sros:ipv4-unicast-address;
                description "Default query-source address for all group interfaces";
            }

            leaf query-interval {
                type uint32 {
                    range "2..1024";
                }
                units "seconds";
                default "125";
                description "Time between two consecutive host-query messages";
            }

            leaf query-last-member-interval {
                type uint32 {
                    range "1..1023";
                }
                units "seconds";
                default "1";
                description "Time between group-specific query messages";
            }

            leaf query-response-interval {
                type uint32 {
                    range "1..1023";
                }
                units "seconds";
                default "10";
                description "Time to wait for a response to the host-query messages";
            }

            leaf robust-count {
                type uint32 {
                    range "2..10";
                }
                default "2";
                description "Number of retries after message loss";
            }

            leaf admin-state {
                type types-sros:admin-state;
                default "enable";
                description "Administrative state of IGMP";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container ssm-translate {
                description "Enter the ssm-translate context";

                list group-range {
                    key "start end";
                    description "Enter the group-range list instance";

                    leaf start {
                        type types-sros:ipv4-multicast-address;
                        description "IP address that specifies the start of the group range";
                    }

                    leaf end {
                        type types-sros:ipv4-multicast-address;
                        description "IP address that specifies the end of the group range";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list source {
                        key "source-address";
                        min-elements 1;
                        description "Add a list entry for source";

                        leaf source-address {
                            type types-sros:ipv4-unicast-address;
                            description "Source IP address of multicast channel sending data";
                        }

                    } // list source

                } // list group-range

            } // container ssm-translate

            list interface {
                key "ip-interface-name";
                description "Enter the interface list instance";

                leaf ip-interface-name {
                    type types-sros:interface-name;
                    description "IP interface name";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf admin-state {
                    type types-sros:admin-state;
                    default "enable";
                    description "Administrative state of IGMP";
                }

                leaf import-policy {
                    type leafref {
                        path "../../../../policy-options/policy-statement/name";
                    }
                    description "Import policy that filters IGMP packets";
                }

                leaf subnet-check {
                    type boolean;
                    default "true";
                    description "Allow subnet checking";
                }

                leaf version {
                    type types-igmp:igmp-version;
                    default "3";
                    description "IGMP protocol version";
                }

                leaf redundant-mcast {
                    type boolean;
                    default "false";
                    description "Use interface as a redundant-pair member for multicast";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container mcac {
                    description "Enter the mcac context";

                    leaf interface-policy {
                        type leafref {
                            path "../../../../../mcac/interface-policy/policy-name";
                        }
                        description "Name of multicast CAC interface policy";
                    }

                    leaf policy {
                        type leafref {
                            path "../../../../../mcac/policy/policy-name";
                        }
                        description "Multicast CAC policy name";
                    }

                    container mc-constraints {
                        description "Enter the mc-constraints context";

                        leaf use-lag-port-weight {
                            type boolean;
                            default "false";
                            description "Use LAG port weight in calculating MCAC constraints";
                        }

                        list level {
                            key "level-id";
                            description "Enter the level list instance";

                            leaf level-id {
                                type types-mcast-cac:constraints-level;
                                description "Bandwidth level ID for a multicast CAC constraint";
                            }

                            leaf bandwidth {
                                type types-mcast-cac:bandwidth {
                                    range "0..2147483647";
                                }
                                mandatory true;
                                description "Bandwidth available for this level";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list level

                        list number-down {
                            key "number-lag-port-down";
                            description "Enter the number-down list instance";

                            leaf number-lag-port-down {
                                type uint32 {
                                    range "1..64";
                                }
                                description "Number of ports that are down in this LAG link";
                            }

                            leaf level {
                                type types-mcast-cac:constraints-level;
                                mandatory true;
                                description "Level ID to associate with number of down LAG ports";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list number-down

                    } // container mc-constraints

                    container bandwidth {
                        description "Enter the bandwidth context";

                        leaf total {
                            type types-mcast-cac:bandwidth-limit;
                            description "Maximum allowed bandwidth";
                        }

                        leaf mandatory {
                            type types-mcast-cac:bandwidth-limit;
                            description "Pre-reserved bandwidth for all mandatory channels";
                        }

                    } // container bandwidth

                } // container mcac

                container ssm-translate {
                    description "Enter the ssm-translate context";

                    list group-range {
                        key "start end";
                        description "Enter the group-range list instance";

                        leaf start {
                            type types-sros:ipv4-multicast-address;
                            description "IP address that specifies the start of the group range";
                        }

                        leaf end {
                            type types-sros:ipv4-multicast-address;
                            description "IP address that specifies the end of the group range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list source {
                            key "source-address";
                            min-elements 1;
                            description "Add a list entry for source";

                            leaf source-address {
                                type types-sros:ipv4-unicast-address;
                                description "Source IP address of multicast channel sending data";
                            }

                        } // list source

                    } // list group-range

                } // container ssm-translate

                container static {
                    description "Enter the static context";

                    list group {
                        key "group-address";
                        description "Enter the group list instance";

                        leaf group-address {
                            type types-sros:ipv4-multicast-address;
                            description "Group address of static IGMP multicast channel";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        choice source-or-starg {
                            mandatory true;
                            case source {

                                list source {
                                    key "source-address";
                                    description "Add a list entry for source";

                                    leaf source-address {
                                        type types-sros:ipv4-unicast-address;
                                        description "Source IP address of multicast channel sending data";
                                    }

                                } // list source

                            }
                            case starg {

                                leaf starg {
                                    type empty;
                                    description "Add a starg (*,G) address entry for the group range";
                                }

                            }
                        }
                    } // list group

                    list group-range {
                        key "start end step";
                        description "Enter the group-range list instance";

                        leaf start {
                            type types-sros:ipv4-multicast-address;
                            description "IP address for the start of the static group range";
                        }

                        leaf end {
                            type types-sros:ipv4-multicast-address;
                            description "IP address for the end of the static group range";
                        }

                        leaf step {
                            type types-sros:ipv4-address;
                            description "Step interval in the group-range address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        choice source-or-starg {
                            mandatory true;
                            case source {

                                list source {
                                    key "source-address";
                                    description "Add a list entry for source";

                                    leaf source-address {
                                        type types-sros:ipv4-unicast-address;
                                        description "Source IP address of multicast channel sending data";
                                    }

                                } // list source

                            }
                            case starg {

                                leaf starg {
                                    type empty;
                                    description "Add a starg (*,G) address entry for the group range";
                                }

                            }
                        }
                    } // list group-range

                } // container static

            } // list interface

            list group-interface {
                key "group-interface-name";
                description "Enter the group-interface list instance";

                leaf group-interface-name {
                    type leafref {
                        path "../../../../service/ies/subscriber-interface/group-interface/group-interface-name";
                    }
                    description "Group interface name";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf admin-state {
                    type types-sros:admin-state;
                    default "enable";
                    description "Administrative state of IGMP";
                }

                leaf import-policy {
                    type leafref {
                        path "../../../../policy-options/policy-statement/name";
                    }
                    description "Import policy that filters IGMP packets";
                }

                leaf subnet-check {
                    type boolean;
                    default "true";
                    description "Allow subnet checking";
                }

                leaf version {
                    type types-igmp:igmp-version;
                    default "3";
                    description "IGMP protocol version";
                }

                leaf sub-hosts-only {
                    type boolean;
                    default "true";
                    description "Allow IGMP traffic from known hosts only";
                }

                leaf query-source-address {
                    type types-sros:ipv4-unicast-address;
                    description "Source address for IGMP queries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container mcac {
                    description "Enter the mcac context";

                    leaf interface-policy {
                        type leafref {
                            path "../../../../../mcac/interface-policy/policy-name";
                        }
                        description "Name of multicast CAC interface policy";
                    }

                    leaf policy {
                        type leafref {
                            path "../../../../../mcac/policy/policy-name";
                        }
                        description "Multicast CAC policy name";
                    }

                    container bandwidth {
                        description "Enter the bandwidth context";

                        leaf total {
                            type types-mcast-cac:bandwidth-limit;
                            description "Maximum allowed bandwidth";
                        }

                        leaf mandatory {
                            type types-mcast-cac:bandwidth-limit;
                            description "Pre-reserved bandwidth for all mandatory channels";
                        }

                    } // container bandwidth

                } // container mcac

            } // list group-interface

            container tunnel-interface {
                description "Enter the tunnel-interface context";

                list rsvp-p2mp-root {
                    key "lsp-name";
                    description "Enter the rsvp-p2mp-root list instance";

                    leaf lsp-name {
                        type leafref {
                            path "../../../../tunnel-interface/rsvp-p2mp-root/lsp-name";
                        }
                        description "LSP name for the RSVP P2MP LSP";
                    }

                    leaf admin-state {
                        type types-sros:admin-state;
                        default "enable";
                        description "Administrative state of IGMP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "Add a starg (*,G) address entry for the group range";
                                    }

                                }
                            }
                        } // list group

                    } // container static

                } // list rsvp-p2mp-root

                list ldp-p2mp-root {
                    key "p2mp-id sender-address";
                    description "Enter the ldp-p2mp-root list instance";

                    leaf p2mp-id {
                        type leafref {
                            path "../../../../tunnel-interface/ldp-p2mp-root[sender-address=current()/../sender-address]/p2mp-id";
                        }
                        description "The identifier of the RSVP P2MP LSP";
                    }

                    leaf sender-address {
                        type leafref {
                            path "../../../../tunnel-interface/ldp-p2mp-root[p2mp-id=current()/../p2mp-id]/sender-address";
                        }
                        description "System address of the ingress LER for the P2MP RSVP LSP";
                    }

                    leaf admin-state {
                        type types-sros:admin-state;
                        default "enable";
                        description "Administrative state of IGMP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "Add a starg (*,G) address entry for the group range";
                                    }

                                }
                            }
                        } // list group

                    } // container static

                } // list ldp-p2mp-root

            } // container tunnel-interface

        } // container igmp

    } // grouping conf-router-igmp

}
