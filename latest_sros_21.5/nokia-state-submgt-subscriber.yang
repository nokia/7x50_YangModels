submodule nokia-state-submgt-subscriber {

    yang-version "1.1";

    belongs-to nokia-state { prefix "state"; }

    import ietf-yang-types                { prefix "yang"; }
    import nokia-sros-yang-extensions     { prefix "sros-ext"; }
    import nokia-types-cellular           { prefix "types-cellular"; }
    import nokia-types-dhcp               { prefix "types-dhcp"; }
    import nokia-types-l2tp               { prefix "types-l2tp"; }
    import nokia-types-nat                { prefix "types-nat"; }
    import nokia-types-pcc-rule           { prefix "types-pcc-rule"; }
    import nokia-types-ppp                { prefix "types-ppp"; }
    import nokia-types-qos                { prefix "types-qos"; }
    import nokia-types-services           { prefix "types-services"; }
    import nokia-types-sros               { prefix "types-sros"; }
    import nokia-types-subscriber-mgmt    { prefix "types-submgt"; }


    sros-ext:sros-major-release "rel21";

    organization "Nokia";

    contact
        "Nokia SR OS Support
         Web: <http://www.nokia.com>";

    description
        "Nokia YANG Data model with operational state for subscriber management subscriber on SR OS based routers.

         Copyright 2016 Nokia. All rights reserved. Reproduction of this document
         is authorized on the condition that the foregoing copyright notice is included.

         This nokia-state-submgt-subscriber YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-03-18";

    grouping state-submgt-subscriber {
        list subscriber {
            key "subscriber-id";
            description "Enter the subscriber list instance";

            leaf subscriber-id {
                type types-submgt:subscriber-id;
                description "Subscriber Identification string";
            }

            leaf port {
                type types-sros:port;
                description "Port.";
            }

            leaf sub-profile {
                type types-sros:named-item;
                description "The subscriber profile of this subscriber.";
            }

            leaf sub-profile-changes {
                type uint32;
                description "The number of times the sub-profile of this subscriber has changed.";
            }

            leaf ancp-string {
                type types-sros:display-string {
                    length "1..64";
                }
                description "The ancp string of this subscriber.";
            }

            leaf int-dest-id {
                type types-submgt:int-dest-id;
                description "The Int-dest-id corresponding to this subscriber.";
            }

            container mcac {
                description "Enter the mcac context";

                leaf sub-mcac-policy {
                    type types-sros:named-item;
                    description "The sub-mcac-policy (based on the sub-profile)";
                }

                leaf in-use-mandatory-bandwidth {
                    type uint32;
                    units "kilobps";
                    description
                        "The in-use bandwidth for the mandatory channels for this
                         subscriber.";
                }

                leaf in-use-optional-bandwidth {
                    type uint32;
                    units "kilobps";
                    description
                        "The in-use bandwidth for the optional channels for this
                         subscriber.";
                }

                leaf available-mandatory-bandwidth {
                    type uint32;
                    units "kilobps";
                    description
                        "The pre-reserved bandwidth for the mandatory channels for
                         this subscriber.";
                }

                leaf available-optional-bandwidth {
                    type uint32;
                    units "kilobps";
                    description "The available bandwidth for this subscriber.";
                }

            } // container mcac

            container igmp-host-tracking {
                description "Enter the igmp-host-tracking context";

                leaf host-tracking-policy {
                    type types-sros:named-item;
                    description "The host-tracking-policy (based on the sub-profile)";
                }

                leaf egress-rate-reduction {
                    type yang:gauge32;
                    description
                        "The egress rate reduction to be applied for this subscriber
                         in order to account for its multicast membership.";
                }

            } // container igmp-host-tracking

            container ingress {
                description "Enter the ingress context";

                container qos {
                    description "Enter the qos context";

                    list scheduler {
                        key "scheduler-name";
                        description "Enter the scheduler list instance";

                        leaf scheduler-name {
                            type types-sros:named-item;
                            description "Scheduler name";
                        }

                        container statistics {
                            description "Enter the statistics context";

                            leaf forwarded-packets {
                                type yang:counter64;
                                description "The number of forwarded packets.";
                            }

                            leaf forwarded-octets {
                                type yang:counter64;
                                description "The number of forwarded octets.";
                            }

                        } // container statistics

                        container overrides {
                            description "Enter the overrides context";

                            leaf pir {
                                type types-qos:scheduler-cir-rate;
                                units "kilobps";
                                description "PIR rate";
                            }

                            leaf cir {
                                type types-qos:scheduler-cir-rate-override;
                                units "kilobps";
                                description "CIR rate";
                            }

                        } // container overrides

                    } // list scheduler

                    list arbiter {
                        key "arbiter-name";
                        description "Enter the arbiter list instance";

                        leaf arbiter-name {
                            type types-sros:named-item;
                            description "Arbiter name";
                        }

                        container statistics {
                            description "Enter the statistics context";

                            leaf forwarded-packets {
                                type yang:counter64;
                                description "The number of forwarded packets.";
                            }

                            leaf forwarded-octets {
                                type yang:counter64;
                                description "The number of forwarded octets.";
                            }

                        } // container statistics

                        container overrides {
                            description "Enter the overrides context";

                            leaf pir {
                                type types-qos:policer-pir-rate-override;
                                units "kilobps";
                                description "PIR rate";
                            }

                        } // container overrides

                    } // list arbiter

                    container accumulated-statistics {
                        description "Enter the accumulated-statistics context";

                        list queue {
                            key "id";
                            description "Enter the queue list instance";

                            leaf id {
                                type types-qos:ingress-queue-id;
                                description "The id identifies the queue.";
                            }

                            container statistics {
                                description "Enter the statistics context";

                                leaf in-profile-forwarded-packets {
                                    type yang:counter64;
                                    description
                                        "The total number of in-profile packets
                                         (rate below CIR) forwarded by the ingress packet processor.";
                                }

                                leaf in-profile-forwarded-octets {
                                    type yang:counter64;
                                    description
                                        "The total number of in-profile octets
                                         (rate below CIR) forwarded by the ingress packet processor.";
                                }

                                leaf out-profile-forwarded-packets {
                                    type yang:counter64;
                                    description
                                        "The total number of out-profile packets
                                         (rate above CIR) forwarded by the ingress packet processor.";
                                }

                                leaf out-profile-forwarded-octets {
                                    type yang:counter64;
                                    description
                                        "The total number of out-profile octets
                                         (rate above CIR) forwarded by the ingress packet processor.";
                                }

                                leaf high-priority-dropped-packets {
                                    type yang:counter64;
                                    description
                                        "The total number of high-priority packets dropped by the traffic manager
                                         for this subscriber.";
                                }

                                leaf high-priority-dropped-octets {
                                    type yang:counter64;
                                    description
                                        "The total number of high-priority octets, as determined by the
                                         SLA profile ingress QoS policy, dropped by the packet processor for this subscriber.";
                                }

                                leaf low-priority-dropped-packets {
                                    type yang:counter64;
                                    description
                                        "The total number of low-priority packets  dropped by the
                                         packet processor for this subscriber.";
                                }

                                leaf low-priority-dropped-octets {
                                    type yang:counter64;
                                    description
                                        "The total number of low-priority octets as determined by the SLA profile
                                         ingress QoS policy, dropped by the packet processor to the traffic manager for this subscriber.";
                                }

                                leaf high-priority-offered-packets {
                                    type yang:counter64;
                                    description
                                        "The total number of high-priority packets offered by the
                                         packet processor to the traffic manager for this subscriber.";
                                }

                                leaf high-priority-offered-octets {
                                    type yang:counter64;
                                    description
                                        "The total number of high-priority octets offered by the
                                         packet processor to the traffic manager for this subscriber.";
                                }

                                leaf low-priority-offered-packets {
                                    type yang:counter64;
                                    description
                                        "The total number of low-priority packets offered by the
                                         packet processor to the traffic manager for this subscriber.";
                                }

                                leaf low-priority-offered-octets {
                                    type yang:counter64;
                                    description
                                        "The total number of low-priority octets offered by the
                                         packet processor to the traffic manager for this subscriber.";
                                }

                            } // container statistics

                        } // list queue

                        list policer {
                            key "id";
                            description "Enter the policer list instance";

                            leaf id {
                                type types-qos:ingress-policer-id;
                                description "The id identifies the policer.";
                            }

                            container statistics {
                                description "Enter the statistics context";

                                leaf in-profile-forwarded-packets {
                                    type yang:counter64;
                                    description
                                        "The total number of in-profile packets
                                         (rate below CIR) forwarded by the ingress packet processor.";
                                }

                                leaf in-profile-forwarded-octets {
                                    type yang:counter64;
                                    description
                                        "The total number of in-profile octets
                                         (rate below CIR) forwarded by the ingress packet processor.";
                                }

                                leaf out-profile-forwarded-packets {
                                    type yang:counter64;
                                    description
                                        "The total number of out-profile packets
                                         (rate above CIR) forwarded by the ingress packet processor.";
                                }

                                leaf out-profile-forwarded-octets {
                                    type yang:counter64;
                                    description
                                        "The total number of out-profile octets
                                         (rate above CIR) forwarded by the ingress packet processor.";
                                }

                                leaf high-priority-dropped-packets {
                                    type yang:counter64;
                                    description
                                        "The total number of high-priority packets dropped by the traffic manager
                                         for this subscriber.";
                                }

                                leaf high-priority-dropped-octets {
                                    type yang:counter64;
                                    description
                                        "The total number of high-priority octets, as determined by the
                                         SLA profile ingress QoS policy, dropped by the packet processor for this subscriber.";
                                }

                                leaf low-priority-dropped-packets {
                                    type yang:counter64;
                                    description
                                        "The total number of low-priority packets  dropped by the
                                         packet processor for this subscriber.";
                                }

                                leaf low-priority-dropped-octets {
                                    type yang:counter64;
                                    description
                                        "The total number of low-priority octets as determined by the SLA profile
                                         ingress QoS policy, dropped by the packet processor to the traffic manager for this subscriber.";
                                }

                                leaf high-priority-offered-packets {
                                    type yang:counter64;
                                    description
                                        "The total number of high-priority packets offered by the
                                         packet processor to the traffic manager for this subscriber.";
                                }

                                leaf high-priority-offered-octets {
                                    type yang:counter64;
                                    description
                                        "The total number of high-priority octets offered by the
                                         packet processor to the traffic manager for this subscriber.";
                                }

                                leaf low-priority-offered-packets {
                                    type yang:counter64;
                                    description
                                        "The total number of low-priority packets offered by the
                                         packet processor to the traffic manager for this subscriber.";
                                }

                                leaf low-priority-offered-octets {
                                    type yang:counter64;
                                    description
                                        "The total number of low-priority octets offered by the
                                         packet processor to the traffic manager for this subscriber.";
                                }

                                leaf stat-mode {
                                    type types-submgt:subscriber-ingress-policer-stat-mode-type;
                                    description "The stat mode format of this policer.";
                                }

                            } // container statistics

                        } // list policer

                    } // container accumulated-statistics

                } // container qos

            } // container ingress

            container egress {
                description "Enter the egress context";

                container qos {
                    description "Enter the qos context";

                    leaf hardware-type {
                        type enumeration {
                            enum "unknown"                      { value 0; }
                            enum "fp"                           { value 1; }
                            enum "hsmda2"                       { value 3; }
                            enum "hs"                           { value 4; }
                        }
                        description "The Quality of Service model (based on the MDA and/or IOM)";
                    }

                    leaf queue-group {
                        type string;
                        description "Queue group for policer output";
                    }

                    leaf virtual-port {
                        type string;
                        description "Virtual port";
                    }

                    leaf secondary-shaper {
                        type enumeration {
                            enum "unused"                       { value 0; }
                            enum "default"                      { value 1; }
                            enum "int-dest-id"                  { value 2; }
                        }
                        description
                            "'unused'      no secondary shaper is used.
                             'default'     the default secondary shaper is used.
                             'int-dest-id' the value of int-dest-id is used as secondary shaper.";
                    }

                    leaf aggregate-rate-limit-override {
                        type types-qos:rate-limit;
                        description "The egress aggregate rate limit override received by RADIUS/AAA/... .";
                    }

                    leaf aggregate-rate-limit {
                        type types-qos:rate-limit;
                        description "The intended egress aggregate rate limit, regardless of its origin.";
                    }

                    leaf aggregate-rate-limit-below-min {
                        type boolean;
                        description "True if the egress aggregate rate limit was below min-resv-bw and has been set to min-resv-bw.";
                    }

                    list scheduler {
                        key "scheduler-name";
                        description "Enter the scheduler list instance";

                        leaf scheduler-name {
                            type types-sros:named-item;
                            description "Scheduler name";
                        }

                        container statistics {
                            description "Enter the statistics context";

                            leaf forwarded-packets {
                                type yang:counter64;
                                description "The number of forwarded packets.";
                            }

                            leaf forwarded-octets {
                                type yang:counter64;
                                description "The number of forwarded octets.";
                            }

                        } // container statistics

                        container overrides {
                            description "Enter the overrides context";

                            leaf pir {
                                type types-qos:scheduler-cir-rate;
                                units "kilobps";
                                description "PIR rate";
                            }

                            leaf cir {
                                type types-qos:scheduler-cir-rate-override;
                                units "kilobps";
                                description "CIR rate";
                            }

                        } // container overrides

                    } // list scheduler

                    list arbiter {
                        key "arbiter-name";
                        description "Enter the arbiter list instance";

                        leaf arbiter-name {
                            type types-sros:named-item;
                            description "Arbiter name";
                        }

                        container statistics {
                            description "Enter the statistics context";

                            leaf forwarded-packets {
                                type yang:counter64;
                                description "The number of forwarded packets.";
                            }

                            leaf forwarded-octets {
                                type yang:counter64;
                                description "The number of forwarded octets.";
                            }

                        } // container statistics

                        container overrides {
                            description "Enter the overrides context";

                            leaf pir {
                                type types-qos:policer-pir-rate-override;
                                units "kilobps";
                                description "PIR rate";
                            }

                        } // container overrides

                    } // list arbiter

                    container accumulated-statistics {
                        description "Enter the accumulated-statistics context";

                        list policer {
                            key "id";
                            description "Enter the policer list instance";

                            leaf id {
                                type types-qos:sap-egress-policer-id;
                                description "The id identifies the policer.";
                            }

                            container statistics {
                                description "Enter the statistics context";

                                leaf in-profile-forwarded-packets {
                                    type yang:counter64;
                                    description
                                        "The total number of in-profile packets forwarded
                                         for this subscriber.";
                                }

                                leaf in-profile-forwarded-octets {
                                    type yang:counter64;
                                    description
                                        "The total number of in-profile octets forwarded
                                         for this subscriber.";
                                }

                                leaf out-profile-forwarded-packets {
                                    type yang:counter64;
                                    description
                                        "The total number of out-profile packets forwarded
                                         for this subscriber.";
                                }

                                leaf out-profile-forwarded-octets {
                                    type yang:counter64;
                                    description
                                        "The total number of out-profile octets forwarded
                                         for this subscriber.";
                                }

                                leaf in-profile-dropped-packets {
                                    type yang:counter64;
                                    description
                                        "The total number of in-profile packets discarded
                                         for this subscriber.";
                                }

                                leaf in-profile-dropped-octets {
                                    type yang:counter64;
                                    description
                                        "The total number of in-profile octets discarded
                                         for this subscriber.";
                                }

                                leaf out-profile-dropped-packets {
                                    type yang:counter64;
                                    description
                                        "The total number of out-profile packets discarded
                                         for this subscriber.";
                                }

                                leaf out-profile-dropped-octets {
                                    type yang:counter64;
                                    description
                                        "The total number of out-profile octets discarded
                                         for this subscriber.";
                                }

                                leaf in-profile-offered-packets {
                                    type yang:counter64;
                                    description
                                        "The total number of in-profile packets offered
                                         for this subscriber.";
                                }

                                leaf in-profile-offered-octets {
                                    type yang:counter64;
                                    description
                                        "The total number of in-profile octets offered
                                         for this subscriber.";
                                }

                                leaf out-profile-offered-packets {
                                    type yang:counter64;
                                    description
                                        "The total number of out-profile packets offered
                                         for this subscriber.";
                                }

                                leaf out-profile-offered-octets {
                                    type yang:counter64;
                                    description
                                        "The total number of out-profile octets offered
                                         for this subscriber.";
                                }

                                leaf stat-mode {
                                    type types-submgt:subscriber-egress-policer-stat-mode-2-type;
                                    description "The stat mode format of this egress policer.";
                                }

                            } // container statistics

                        } // list policer

                        list queue {
                            key "id";
                            description "Enter the queue list instance";

                            leaf id {
                                type types-qos:egress-queue-id;
                                description "The id identifies the queue.";
                            }

                            container statistics {
                                description "Enter the statistics context";

                                leaf in-profile-forwarded-packets {
                                    type yang:counter64;
                                    description
                                        "The total number of in-profile packets forwarded
                                         for this subscriber.";
                                }

                                leaf in-profile-forwarded-octets {
                                    type yang:counter64;
                                    description
                                        "The total number of in-profile octets forwarded
                                         for this subscriber.";
                                }

                                leaf out-profile-forwarded-packets {
                                    type yang:counter64;
                                    description
                                        "The total number of out-profile packets forwarded
                                         for this subscriber.";
                                }

                                leaf out-profile-forwarded-octets {
                                    type yang:counter64;
                                    description
                                        "The total number of out-profile octets forwarded
                                         for this subscriber.";
                                }

                                leaf in-profile-dropped-packets {
                                    type yang:counter64;
                                    description
                                        "The total number of in-profile packets discarded
                                         for this subscriber.";
                                }

                                leaf in-profile-dropped-octets {
                                    type yang:counter64;
                                    description
                                        "The total number of in-profile octets discarded
                                         for this subscriber.";
                                }

                                leaf out-profile-dropped-packets {
                                    type yang:counter64;
                                    description
                                        "The total number of out-profile packets discarded
                                         for this subscriber.";
                                }

                                leaf out-profile-dropped-octets {
                                    type yang:counter64;
                                    description
                                        "The total number of out-profile octets discarded
                                         for this subscriber.";
                                }

                            } // container statistics

                        } // list queue

                    } // container accumulated-statistics

                } // container qos

            } // container egress

            list sla-profile-instance {
                key "id";
                description "Enter the sla-profile-instance list instance";

                leaf id {
                    type types-submgt:sla-profile-instance-id;
                    description "The id identifies sla profile instance.";
                }

                leaf sla-profile {
                    type types-sros:named-item;
                    description "SLA profile name.";
                }

                leaf sharing-type {
                    type types-submgt:sla-profile-instance-sharing-type;
                    description "Sharing type.";
                }

                leaf sharing-id {
                    type uint32;
                    description "Sharing id.";
                }

                leaf bonded {
                    type boolean;
                    description "Bonded SLA profile instance.";
                }

                leaf category-map {
                    type types-sros:named-item;
                    description "Name of the category map used.";
                }

                leaf radius-accounting-session-id {
                    type types-submgt:accounting-session-id;
                    description "The id of the RADIUS accounting session.";
                }

                container diameter {
                    description "Enter the diameter context";

                    leaf gy-session-id {
                        type string;
                        description "Diameter Gy session id.";
                    }

                    leaf gx-session-id {
                        type string;
                        description "Diameter Gx session id of the Gx diameter session owning the usage monitoring.";
                    }

                    container extended-failure-handling {
                        description "Enter the extended-failure-handling context";

                        leaf action {
                            type enumeration {
                                enum "terminate"                    { value 1; }
                                enum "continue"                     { value 2; }
                                enum "retry-and-terminate"          { value 3; }
                            }
                            description "The action taken in case of a credit-control session failure.";
                        }

                        leaf active-count {
                            type uint32;
                            description "Number of times the credit-control session has been in EFH mode.";
                        }

                        leaf active-time {
                            type types-sros:time-interval;
                            units "centiseconds";
                            description "The total time the diameter session has been in EFH mode.";
                        }

                        leaf attempts {
                            type uint32;
                            description "Number of times the diameter session has assigned interim quota.";
                        }

                        leaf max-attempts {
                            type uint32;
                            description
                                "Maximum number of times the diameter session can assign
                                 interim quota to the SLA profile instance.";
                        }

                        leaf state {
                            type enumeration {
                                enum "active"                       { value 1; }
                                enum "inactive"                     { value 2; }
                                enum "disabled"                     { value 3; }
                            }
                            description "Extended Failure Handling (EFH) state of the diameter session.";
                        }

                        leaf up-time {
                            type types-sros:time-interval;
                            units "centiseconds";
                            description "The time elapsed since this diameter session is active.";
                        }

                    } // container extended-failure-handling

                } // container diameter

                container service {
                    description "Enter the service context";

                    leaf service-name {
                        type types-services:service-name;
                        description "Service of the sla-profile-instance";
                    }

                    leaf subscriber-interface {
                        type types-sros:interface-name;
                        description "Subscriber interface of the sla-profile-instance";
                    }

                    leaf group-interface {
                        type types-sros:interface-name;
                        description "Group interface of the sla-profile-instance";
                    }

                    leaf sap {
                        type types-sros:sap;
                        description "SAP of the sla-profile-instance";
                    }

                } // container service

                container ingress {
                    description "Enter the ingress context";

                    container qos {
                        description "Enter the qos context";

                        leaf qos-policy-override {
                            type types-submgt:overrule-qos-policy-name;
                            description "The qos policy, overruling the one specified in the sla-profile";
                        }

                        list policer {
                            key "policer-id";
                            description "Enter the policer list instance";

                            leaf policer-id {
                                type types-qos:ingress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-priority-no-cir {

                                        container offered-priority-no-cir {
                                            description "Enter the offered-priority-no-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf high-priority-dropped-packets {
                                                type yang:counter64;
                                                description "The number of high-priority packets dropped by the packet processor to traffic manager";
                                            }

                                            leaf high-priority-dropped-octets {
                                                type yang:counter64;
                                                description "The number of high-priority octets dropped by the packet processor to traffic manager";
                                            }

                                            leaf low-priority-dropped-packets {
                                                type yang:counter64;
                                                description "The number of low-priority packets dropped by the packet processor to traffic manager";
                                            }

                                            leaf low-priority-dropped-octets {
                                                type yang:counter64;
                                                description "The number of low-priority octets dropped by the packet processor to traffic manager";
                                            }

                                            leaf high-priority-forwarded-packets {
                                                type yang:counter64;
                                                description "The number of high-priority packets forwarded by the packet processor to traffic manager";
                                            }

                                            leaf high-priority-forwarded-octets {
                                                type yang:counter64;
                                                description "The number of high-priority octets forwarded by the packet processor to traffic manager";
                                            }

                                            leaf low-priority-forwarded-packets {
                                                type yang:counter64;
                                                description "The number of low-priority packets forwarded by the packet processor to traffic manager";
                                            }

                                            leaf low-priority-forwarded-octets {
                                                type yang:counter64;
                                                description "The number of low-priority octets forwarded by the packet processor to traffic manager";
                                            }

                                        } // container offered-priority-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-priority-cir {

                                        container offered-priority-cir {
                                            description "Enter the offered-priority-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-priority-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-profile-cir {

                                        container offered-limited-profile-cir {
                                            description "Enter the offered-limited-profile-cir context";

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-limited-profile-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-profile-with-discards {

                                        container offered-profile-with-discards {
                                            description "Enter the offered-profile-with-discards context";

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-profile packets forwarded by the packet processor to traffic manager";
                                            }

                                            leaf out-profile-forwarded-octets {
                                                type yang:counter64;
                                                description "The number of out-profile octets forwarded by the packet processor to traffic manager";
                                            }

                                            leaf dropped-exceed-profile-packets {
                                                type yang:counter64;
                                                description "The number of dropped-exceed-profile packets by the packet processor to traffic manager";
                                            }

                                            leaf dropped-exceed-profile-octets {
                                                type yang:counter64;
                                                description "The number of dropped-exceed-profile octets by the packet processor to traffic manager";
                                            }

                                        } // container offered-profile-with-discards

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf uncolor-offered-packets {
                                                type yang:counter64;
                                                description "The number of out-of-rofile packets offered by the packet processor to traffic manager";
                                            }

                                            leaf uncolor-offered-octets {
                                                type yang:counter64;
                                                description "The number of out-of-profile octets offered by the packet processor to traffic manager";
                                            }

                                        } // container offered-limited-capped-cir

                                    }
                                    case v4-v6 {

                                        container v4-v6 {
                                            description "Enter the v4-v6 context";

                                            leaf ipv4-offered-packets {
                                                type yang:counter64;
                                                description "The number of ipv4 packets offered by the packet processor to traffic manager";
                                            }

                                            leaf ipv4-offered-octets {
                                                type yang:counter64;
                                                description "The number of ipv4 octets offered by the packet processor to traffic manager";
                                            }

                                            leaf ipv6-offered-packets {
                                                type yang:counter64;
                                                description "The number of ipv6 packets offered by the packet processor to traffic manager";
                                            }

                                            leaf ipv6-offered-octets {
                                                type yang:counter64;
                                                description "The number of ipv6 octets offered by the packet processor to traffic manager";
                                            }

                                            leaf ipv4-dropped-packets {
                                                type yang:counter64;
                                                description "The number of ipv4 packets dropped by the packet processor to traffic manager";
                                            }

                                            leaf ipv4-dropped-octets {
                                                type yang:counter64;
                                                description "The number of ipv4 octets dropped by the packet processor to traffic manager";
                                            }

                                            leaf ipv6-dropped-packets {
                                                type yang:counter64;
                                                description "The number of ipv6 packets dropped by the packet processor to traffic manager";
                                            }

                                            leaf ipv6-dropped-octets {
                                                type yang:counter64;
                                                description "The number of ipv6 octets dropped by the packet processor to traffic manager";
                                            }

                                            leaf ipv4-forwarded-packets {
                                                type yang:counter64;
                                                description "The number of ipv4 packets forwarded by the packet processor to traffic manager";
                                            }

                                            leaf ipv4-forwarded-octets {
                                                type yang:counter64;
                                                description "The number of ipv4 octets forwarded by the packet processor to traffic manager";
                                            }

                                            leaf ipv6-forwarded-packets {
                                                type yang:counter64;
                                                description "The number of ipv6 packets forwarded by the packet processor to traffic manager";
                                            }

                                            leaf ipv6-forwarded-octets {
                                                type yang:counter64;
                                                description "The number of ipv6 octets forwarded by the packet processor to traffic manager";
                                            }

                                        } // container v4-v6

                                    }
                                }
                            } // container statistics

                            container overrides {
                                description "Enter the overrides context";

                                leaf pir {
                                    type types-qos:policer-pir-rate-override;
                                    units "kilobps";
                                    description "PIR rate";
                                }

                                leaf cir {
                                    type types-qos:policer-cir-rate-override;
                                    units "kilobps";
                                    description "CIR rate";
                                }

                                leaf mbs {
                                    type types-qos:policer-burst-size-override;
                                    units "bytes";
                                    description "The maximum reserved buffer space";
                                }

                                leaf cbs {
                                    type types-qos:policer-burst-size-override;
                                    units "bytes";
                                    description "The committed buffer size";
                                }

                            } // container overrides

                        } // list policer

                        list queue {
                            key "queue-id";
                            description "Enter the queue list instance";

                            leaf queue-id {
                                type types-qos:ingress-queue-id;
                                description "The unique identifier for the queue.";
                            }

                            container statistics {
                                description "Enter the statistics context";

                                choice stat-mode {
                                    case unicast-priority {

                                        container unicast-priority {
                                            description "Enter the unicast-priority context";

                                            leaf high-priority-offered-packets {
                                                type yang:counter64;
                                                description "The number of high-priority packets offered by packet processor to traffic manager.";
                                            }

                                            leaf high-priority-offered-octets {
                                                type yang:counter64;
                                                description "The number of high-priority octets offered by packet processor to traffic manager.";
                                            }

                                            leaf low-priority-offered-packets {
                                                type yang:counter64;
                                                description "The number of low-priority packets offered by packet processor to traffic manager.";
                                            }

                                            leaf low-priority-offered-octets {
                                                type yang:counter64;
                                                description "The number of low-priority octets offered by packet processor to traffic manager.";
                                            }

                                            leaf high-priority-dropped-packets {
                                                type yang:counter64;
                                                description "The number of high-priority packets dropped by packet processor to traffic manager.";
                                            }

                                            leaf high-priority-dropped-octets {
                                                type yang:counter64;
                                                description "The number of high-priority octets dropped by packet processor to traffic manager.";
                                            }

                                            leaf low-priority-dropped-packets {
                                                type yang:counter64;
                                                description "The number of low-priority packets dropped by packet processor to traffic manager.";
                                            }

                                            leaf low-priority-dropped-octets {
                                                type yang:counter64;
                                                description "The number of low-priority octets dropped by packet processor to traffic manager.";
                                            }

                                            leaf in-profile-forwarded-packets {
                                                type yang:counter64;
                                                description "The number of in-profile packets (rate below CIR) forwarded.";
                                            }

                                            leaf in-profile-forwarded-octets {
                                                type yang:counter64;
                                                description "The number of in-profile octets (rate below CIR) forwarded.";
                                            }

                                            leaf out-profile-forwarded-packets {
                                                type yang:counter64;
                                                description "The number of out-of-profile packets (rate below CIR) forwarded.";
                                            }

                                            leaf out-profile-forwarded-octets {
                                                type yang:counter64;
                                                description "The number of out-of-profile octets (rate below CIR) forwarded.";
                                            }

                                        } // container unicast-priority

                                    }
                                    case unicast-profile {

                                        container unicast-profile {
                                            description "Enter the unicast-profile context";

                                            leaf color-in-offered-packets {
                                                type yang:counter64;
                                                description "The number of color-in packets offered to traffic manager.";
                                            }

                                            leaf color-in-offered-octets {
                                                type yang:counter64;
                                                description "The number of color-in octets offered to traffic manager.";
                                            }

                                            leaf color-out-offered-packets {
                                                type yang:counter64;
                                                description "The number of color-out packets offered to traffic manager.";
                                            }

                                            leaf color-out-offered-octets {
                                                type yang:counter64;
                                                description "The number of color-out octets offered to traffic manager.";
                                            }

                                            leaf color-offered-packets {
                                                type yang:counter64;
                                                description "The number of color packets offered to traffic manager.";
                                            }

                                            leaf color-offered-octets {
                                                type yang:counter64;
                                                description "The number of color octets offered to traffic manager.";
                                            }

                                            leaf uncolor-offered-packets {
                                                type yang:counter64;
                                                description "The number of uncolor packets offered to traffic manager.";
                                            }

                                            leaf uncolor-offered-octets {
                                                type yang:counter64;
                                                description "The number of uncolor octets offered to traffic manager.";
                                            }

                                            leaf color-out-dropped-packets {
                                                type yang:counter64;
                                                description "The number of color-out packets dropped.";
                                            }

                                            leaf color-out-dropped-octets {
                                                type yang:counter64;
                                                description "The number of color-out octets dropped.";
                                            }

                                            leaf color-in-uncolor-dropped-packets {
                                                type yang:counter64;
                                                description "The number of color-in/uncolor packets dropped.";
                                            }

                                            leaf color-in-uncolor-dropped-octets {
                                                type yang:counter64;
                                                description "The number of color-in/uncolor octets dropped.";
                                            }

                                            leaf in-profile-forwarded-packets {
                                                type yang:counter64;
                                                description "The number of in-profile packets (rate below CIR) forwarded.";
                                            }

                                            leaf in-profile-forwarded-octets {
                                                type yang:counter64;
                                                description "The number of in-profile octets (rate below CIR) forwarded.";
                                            }

                                            leaf out-profile-forwarded-packets {
                                                type yang:counter64;
                                                description "The number of out-of-profile packets (rate below CIR) forwarded.";
                                            }

                                            leaf out-profile-forwarded-octets {
                                                type yang:counter64;
                                                description "The number of out-of-profile octets (rate below CIR) forwarded.";
                                            }

                                        } // container unicast-profile

                                    }
                                    case multipoint-priority {

                                        container multipoint-priority {
                                            description "Enter the multipoint-priority context";

                                            leaf high-priority-offered-packets {
                                                type yang:counter64;
                                                description "The number of high-priority packets offered by packet processor to traffic manager.";
                                            }

                                            leaf high-priority-offered-octets {
                                                type yang:counter64;
                                                description "The number of high-priority octets offered by packet processor to traffic manager.";
                                            }

                                            leaf low-priority-offered-packets {
                                                type yang:counter64;
                                                description "The number of low-priority packets offered by packet processor to traffic manager.";
                                            }

                                            leaf low-priority-offered-octets {
                                                type yang:counter64;
                                                description "The number of low-priority octets offered by packet processor to traffic manager.";
                                            }

                                            leaf combined-offered-packets {
                                                type yang:counter64;
                                                description "The number of combined high and low priority packets offered by packet processor to traffic manager.";
                                            }

                                            leaf combined-offered-octets {
                                                type yang:counter64;
                                                description "The number of combined high and low priority octets offered by packet processor to traffic manager.";
                                            }

                                            leaf managed-offered-packets {
                                                type yang:counter64;
                                                description "The number of managed packets offered by packet processor to traffic manager.";
                                            }

                                            leaf managed-offered-octets {
                                                type yang:counter64;
                                                description "The number of managed octets offered by packet processor to traffic manager.";
                                            }

                                            leaf high-priority-dropped-packets {
                                                type yang:counter64;
                                                description "The number of high-priority packets dropped by packet processor to traffic manager.";
                                            }

                                            leaf high-priority-dropped-octets {
                                                type yang:counter64;
                                                description "The number of high-priority octets dropped by packet processor to traffic manager.";
                                            }

                                            leaf low-priority-dropped-packets {
                                                type yang:counter64;
                                                description "The number of low-priority packets dropped by packet processor to traffic manager.";
                                            }

                                            leaf low-priority-dropped-octets {
                                                type yang:counter64;
                                                description "The number of low-priority octets dropped by packet processor to traffic manager.";
                                            }

                                            leaf in-profile-forwarded-packets {
                                                type yang:counter64;
                                                description "The number of in-profile packets (rate below CIR) forwarded.";
                                            }

                                            leaf in-profile-forwarded-octets {
                                                type yang:counter64;
                                                description "The number of in-profile octets (rate below CIR) forwarded.";
                                            }

                                            leaf out-profile-forwarded-packets {
                                                type yang:counter64;
                                                description "The number of out-of-profile packets (rate below CIR) forwarded.";
                                            }

                                            leaf out-profile-forwarded-octets {
                                                type yang:counter64;
                                                description "The number of out-of-profile octets (rate below CIR) forwarded.";
                                            }

                                        } // container multipoint-priority

                                    }
                                    case multipoint-profile {

                                        container multipoint-profile {
                                            description "Enter the multipoint-profile context";

                                            leaf color-in-offered-packets {
                                                type yang:counter64;
                                                description "The number of color-in packets offered to traffic manager.";
                                            }

                                            leaf color-in-offered-octets {
                                                type yang:counter64;
                                                description "The number of color-in octets offered to traffic manager.";
                                            }

                                            leaf color-out-offered-packets {
                                                type yang:counter64;
                                                description "The number of color-out packets offered to traffic manager.";
                                            }

                                            leaf color-out-offered-octets {
                                                type yang:counter64;
                                                description "The number of color-out octets offered to traffic manager.";
                                            }

                                            leaf uncolor-offered-packets {
                                                type yang:counter64;
                                                description "The number of uncolor packets offered to traffic manager.";
                                            }

                                            leaf uncolor-offered-octets {
                                                type yang:counter64;
                                                description "The number of uncolor octets offered to traffic manager.";
                                            }

                                            leaf combined-offered-packets {
                                                type yang:counter64;
                                                description "The number of combined colored in, out and uncolored packets offered to traffic manager.";
                                            }

                                            leaf combined-offered-octets {
                                                type yang:counter64;
                                                description "The number of combined colored in, out and uncolored octets offered to traffic manager.";
                                            }

                                            leaf managed-offered-packets {
                                                type yang:counter64;
                                                description "The number of managed packets offered by packet processor to traffic manager.";
                                            }

                                            leaf managed-offered-octets {
                                                type yang:counter64;
                                                description "The number of managed octets offered by packet processor to traffic manager.";
                                            }

                                            leaf color-out-dropped-packets {
                                                type yang:counter64;
                                                description "The number of color-out packets dropped.";
                                            }

                                            leaf color-out-dropped-octets {
                                                type yang:counter64;
                                                description "The number of color-out octets dropped.";
                                            }

                                            leaf color-in-uncolor-dropped-packets {
                                                type yang:counter64;
                                                description "The number of color-in/uncolor packets dropped.";
                                            }

                                            leaf color-in-uncolor-dropped-octets {
                                                type yang:counter64;
                                                description "The number of color-in/uncolor octets dropped.";
                                            }

                                            leaf in-profile-forwarded-packets {
                                                type yang:counter64;
                                                description "The number of in-profile packets (rate below CIR) forwarded.";
                                            }

                                            leaf in-profile-forwarded-octets {
                                                type yang:counter64;
                                                description "The number of in-profile octets (rate below CIR) forwarded.";
                                            }

                                            leaf out-profile-forwarded-packets {
                                                type yang:counter64;
                                                description "The number of out-of-profile packets (rate below CIR) forwarded.";
                                            }

                                            leaf out-profile-forwarded-octets {
                                                type yang:counter64;
                                                description "The number of out-of-profile octets (rate below CIR) forwarded.";
                                            }

                                        } // container multipoint-profile

                                    }
                                    case v4-v6 {

                                        container v4-v6 {
                                            description "Enter the v4-v6 context";

                                            leaf ipv4-offered-packets {
                                                type yang:counter64;
                                                description "The number of ipv4 packets offered by packet processor to traffic manager.";
                                            }

                                            leaf ipv4-offered-octets {
                                                type yang:counter64;
                                                description "The number of ipv4 octets offered by packet processor to traffic manager.";
                                            }

                                            leaf ipv6-offered-packets {
                                                type yang:counter64;
                                                description "The number of ipv6 packets offered by packet processor to traffic manager.";
                                            }

                                            leaf ipv6-offered-octets {
                                                type yang:counter64;
                                                description "The number of ipv6 octets offered by packet processor to traffic manager.";
                                            }

                                            leaf ipv4-dropped-packets {
                                                type yang:counter64;
                                                description "The number of ipv4 packets dropped by packet processor to traffic manager.";
                                            }

                                            leaf ipv4-dropped-octets {
                                                type yang:counter64;
                                                description "The number of ipv4 octets dropped by packet processor to traffic manager.";
                                            }

                                            leaf ipv6-dropped-packets {
                                                type yang:counter64;
                                                description "The number of ipv6 packets dropped by packet processor to traffic manager.";
                                            }

                                            leaf ipv6-dropped-octets {
                                                type yang:counter64;
                                                description "The number of ipv6 octets dropped by packet processor to traffic manager.";
                                            }

                                            leaf ipv4-forwarded-packets {
                                                type yang:counter64;
                                                description "The number of ipv4 packets forwarded.";
                                            }

                                            leaf ipv4-forwarded-octets {
                                                type yang:counter64;
                                                description "The number of ipv4 octets forwarded.";
                                            }

                                            leaf ipv6-forwarded-packets {
                                                type yang:counter64;
                                                description "The number of ipv6 packets forwarded.";
                                            }

                                            leaf ipv6-forwarded-octets {
                                                type yang:counter64;
                                                description "The number of ipv6 octets forwarded.";
                                            }

                                        } // container v4-v6

                                    }
                                }
                            } // container statistics

                            container overrides {
                                description "Enter the overrides context";

                                leaf pir {
                                    type types-qos:queue-pir-rate-override;
                                    units "kilobps";
                                    description "PIR rate";
                                }

                                leaf cir {
                                    type types-qos:queue-cir-rate-override;
                                    units "kilobps";
                                    description "CIR rate";
                                }

                                leaf mbs {
                                    type types-qos:queue-burst-size-override;
                                    units "bytes";
                                    description "The maximum reserved buffer space";
                                }

                                leaf cbs {
                                    type types-qos:queue-burst-size-override;
                                    units "bytes";
                                    description "The committed buffer size";
                                }

                                leaf wrr-weight {
                                    type types-qos:hs-wrr-weight-override;
                                    description
                                        "The Weighted Round Robin (WRR) weight with which
                                         this queue should parent into the scheduler.";
                                }

                                leaf class-weight {
                                    type types-qos:hs-class-weight-override;
                                    description "The scheduling class weight.";
                                }

                            } // container overrides

                        } // list queue

                        container statistics {
                            description "Enter the statistics context";

                            leaf high-priority-offered-packets {
                                type yang:counter64;
                                description "The number of high-priority packets offered by packet processor to traffic manager.";
                            }

                            leaf high-priority-offered-octets {
                                type yang:counter64;
                                description "The number of high-priority octets offered by packet processor to traffic manager.";
                            }

                            leaf low-priority-offered-packets {
                                type yang:counter64;
                                description "The number of low-priority packets offered by packet processor to traffic manager.";
                            }

                            leaf low-priority-offered-octets {
                                type yang:counter64;
                                description "The number of low-priority octets offered by packet processor to traffic manager.";
                            }

                            leaf uncolor-offered-packets {
                                type yang:counter64;
                                description
                                    "Number of uncolored packets offered by the packet processor
                                     to the traffic manager";
                            }

                            leaf uncolor-offered-octets {
                                type yang:counter64;
                                description
                                    "Number of uncolored octets offered by the packet processor
                                     to the traffic manager";
                            }

                            leaf managed-offered-packets {
                                type yang:counter64;
                                description
                                    "Number of multicast managed packets offered by the packet processor
                                     to the traffic manager";
                            }

                            leaf managed-offered-octets {
                                type yang:counter64;
                                description
                                    "Number of multicast managed octets offered by the packet processor
                                     to the traffic manager";
                            }

                            leaf high-priority-dropped-packets {
                                type yang:counter64;
                                description "The number of high-priority packets dropped by packet processor to traffic manager.";
                            }

                            leaf high-priority-dropped-octets {
                                type yang:counter64;
                                description "The number of high-priority octets dropped by packet processor to traffic manager.";
                            }

                            leaf low-priority-dropped-packets {
                                type yang:counter64;
                                description "The number of low-priority packets dropped by packet processor to traffic manager.";
                            }

                            leaf low-priority-dropped-octets {
                                type yang:counter64;
                                description "The number of low-priority octets dropped by packet processor to traffic manager.";
                            }

                            leaf in-profile-forwarded-packets {
                                type yang:counter64;
                                description "The number of in-profile packets (rate below CIR) forwarded.";
                            }

                            leaf in-profile-forwarded-octets {
                                type yang:counter64;
                                description "The number of in-profile octets (rate below CIR) forwarded.";
                            }

                            leaf out-profile-forwarded-packets {
                                type yang:counter64;
                                description "The number of out-of-profile packets (rate below CIR) forwarded.";
                            }

                            leaf out-profile-forwarded-octets {
                                type yang:counter64;
                                description "The number of out-of-profile octets (rate below CIR) forwarded.";
                            }

                            leaf ipv4-offered-packets {
                                type yang:counter64;
                                description "The number of ipv4 packets offered by packet processor to traffic manager.";
                            }

                            leaf ipv4-offered-octets {
                                type yang:counter64;
                                description "The number of ipv4 octets offered by packet processor to traffic manager.";
                            }

                            leaf ipv6-offered-packets {
                                type yang:counter64;
                                description "The number of ipv6 packets offered by packet processor to traffic manager.";
                            }

                            leaf ipv6-offered-octets {
                                type yang:counter64;
                                description "The number of ipv6 octets offered by packet processor to traffic manager.";
                            }

                            leaf ipv4-dropped-packets {
                                type yang:counter64;
                                description "The number of ipv4 packets dropped by packet processor to traffic manager.";
                            }

                            leaf ipv4-dropped-octets {
                                type yang:counter64;
                                description "The number of ipv4 octets dropped by packet processor to traffic manager.";
                            }

                            leaf ipv6-dropped-packets {
                                type yang:counter64;
                                description "The number of ipv6 packets dropped by packet processor to traffic manager.";
                            }

                            leaf ipv6-dropped-octets {
                                type yang:counter64;
                                description "The number of ipv6 octets dropped by packet processor to traffic manager.";
                            }

                            leaf ipv4-forwarded-packets {
                                type yang:counter64;
                                description "The number of ipv4 packets forwarded.";
                            }

                            leaf ipv4-forwarded-octets {
                                type yang:counter64;
                                description "The number of ipv4 octets forwarded.";
                            }

                            leaf ipv6-forwarded-packets {
                                type yang:counter64;
                                description "The number of ipv6 packets forwarded.";
                            }

                            leaf ipv6-forwarded-octets {
                                type yang:counter64;
                                description "The number of ipv6 octets forwarded.";
                            }

                        } // container statistics

                    } // container qos

                } // container ingress

                container egress {
                    description "Enter the egress context";

                    container qos {
                        description "Enter the qos context";

                        leaf aggregate-rate-limit {
                            type types-qos:rate-limit;
                            description "Egress aggregate rate limit.";
                        }

                        leaf aggregate-rate-limit-override {
                            type types-qos:rate-limit;
                            description "The egress aggregate rate limit override received by RADIUS/AAA/... .";
                        }

                        leaf hqos-management-status {
                            type enumeration {
                                enum "disabled"                     { value 1; }
                                enum "enabled"                      { value 2; }
                                enum "mismatch"                     { value 3; }
                            }
                            description "Hierarchical QoS management state of egress policers.";
                        }

                        leaf qos-policy-override {
                            type types-submgt:overrule-qos-policy-name;
                            description "The qos policy, overruling the one specified in the sla-profile";
                        }

                        list policer {
                            key "policer-id";
                            description "Enter the policer list instance";

                            leaf policer-id {
                                type types-qos:sap-egress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf out-profile-offered-packets {
                                                type yang:counter64;
                                                description "The number of out-of-rofile packets offered by the packet processor to traffic manager";
                                            }

                                            leaf out-profile-offered-octets {
                                                type yang:counter64;
                                                description "The number of out-of-profile octets offered by the packet processor to traffic manager";
                                            }

                                        } // container offered-limited-capped-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-total-cir-exceed {

                                        container offered-total-cir-exceed {
                                            description "Enter the offered-total-cir-exceed context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf exceed-profile-dropped-packets {
                                                type yang:counter64;
                                                description "The number of exceed-profile packets dropped by the packet processor to traffic manager";
                                            }

                                            leaf exceed-profile-dropped-octets {
                                                type yang:counter64;
                                                description "The number of exceed-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf exceed-profile-forwarded-packets {
                                                type yang:counter64;
                                                description "The number of exceed-profile packets forwarded by the packet processor to traffic manager";
                                            }

                                            leaf exceed-profile-forwarded-octets {
                                                type yang:counter64;
                                                description "The number of exceed-profile octets forwarded by the packet processor to traffic manager";
                                            }

                                        } // container offered-total-cir-exceed

                                    }
                                    case offered-four-profile-no-cir {

                                        container offered-four-profile-no-cir {
                                            description "Enter the offered-four-profile-no-cir context";

                                            leaf inplus-profile-offered-packets {
                                                type yang:counter64;
                                                description "The number of inplus-profile packets offered by the packet processor to traffic manager";
                                            }

                                            leaf inplus-profile-offered-octets {
                                                type yang:counter64;
                                                description "The number of inplus-profile octets offered by the packet processor to traffic manager";
                                            }

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf exceed-profile-offered-packets {
                                                type yang:counter64;
                                                description "The number of exceed-profile packets offered by the packet processor to traffic manager";
                                            }

                                            leaf exceed-profile-offered-octets {
                                                type yang:counter64;
                                                description "The number of exceed-profile octets offered by the packet processor to traffic manager";
                                            }

                                            leaf inplus-profile-dropped-packets {
                                                type yang:counter64;
                                                description "The number of inplus-profile packets dropped by the packet processor to traffic manager";
                                            }

                                            leaf inplus-profile-dropped-octets {
                                                type yang:counter64;
                                                description "The number of inplus-profile octets dropped by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf exceed-profile-dropped-packets {
                                                type yang:counter64;
                                                description "The number of exceed-profile packets dropped by the packet processor to traffic manager";
                                            }

                                            leaf exceed-profile-dropped-octets {
                                                type yang:counter64;
                                                description "The number of exceed-profile octets dropped by the packet processor to traffic manager";
                                            }

                                            leaf inplus-profile-forwarded-packets {
                                                type yang:counter64;
                                                description "The number of inplus-profile packets forwarded by the packet processor to traffic manager";
                                            }

                                            leaf inplus-profile-forwarded-octets {
                                                type yang:counter64;
                                                description "The number of inplus-profile octets forwarded by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf exceed-profile-forwarded-packets {
                                                type yang:counter64;
                                                description "The number of exceed-profile packets forwarded by the packet processor to traffic manager";
                                            }

                                            leaf exceed-profile-forwarded-octets {
                                                type yang:counter64;
                                                description "The number of exceed-profile octets forwarded by the packet processor to traffic manager";
                                            }

                                        } // container offered-four-profile-no-cir

                                    }
                                    case offered-total-cir-four-profile {

                                        container offered-total-cir-four-profile {
                                            description "Enter the offered-total-cir-four-profile context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf inplus-profile-dropped-packets {
                                                type yang:counter64;
                                                description "The number of inplus-profile packets dropped by the packet processor to traffic manager";
                                            }

                                            leaf inplus-profile-dropped-octets {
                                                type yang:counter64;
                                                description "The number of inplus-profile octets dropped by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf exceed-profile-dropped-packets {
                                                type yang:counter64;
                                                description "The number of exceed-profile packets dropped by the packet processor to traffic manager";
                                            }

                                            leaf exceed-profile-dropped-octets {
                                                type yang:counter64;
                                                description "The number of exceed-profile octets dropped by the packet processor to traffic manager";
                                            }

                                            leaf inplus-profile-forwarded-packets {
                                                type yang:counter64;
                                                description "The number of inplus-profile packets forwarded by the packet processor to traffic manager";
                                            }

                                            leaf inplus-profile-forwarded-octets {
                                                type yang:counter64;
                                                description "The number of inplus-profile octets forwarded by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf exceed-profile-forwarded-packets {
                                                type yang:counter64;
                                                description "The number of exceed-profile packets forwarded by the packet processor to traffic manager";
                                            }

                                            leaf exceed-profile-forwarded-octets {
                                                type yang:counter64;
                                                description "The number of exceed-profile octets forwarded by the packet processor to traffic manager";
                                            }

                                        } // container offered-total-cir-four-profile

                                    }
                                    case v4-v6 {

                                        container v4-v6 {
                                            description "Enter the v4-v6 context";

                                            leaf ipv4-offered-packets {
                                                type yang:counter64;
                                                description "The number of ipv4 packets offered by the packet processor to traffic manager";
                                            }

                                            leaf ipv4-offered-octets {
                                                type yang:counter64;
                                                description "The number of ipv4 octets offered by the packet processor to traffic manager";
                                            }

                                            leaf ipv6-offered-packets {
                                                type yang:counter64;
                                                description "The number of ipv6 packets offered by the packet processor to traffic manager";
                                            }

                                            leaf ipv6-offered-octets {
                                                type yang:counter64;
                                                description "The number of ipv6 octets offered by the packet processor to traffic manager";
                                            }

                                            leaf ipv4-dropped-packets {
                                                type yang:counter64;
                                                description "The number of ipv4 packets dropped by the packet processor to traffic manager";
                                            }

                                            leaf ipv4-dropped-octets {
                                                type yang:counter64;
                                                description "The number of ipv4 octets dropped by the packet processor to traffic manager";
                                            }

                                            leaf ipv6-dropped-packets {
                                                type yang:counter64;
                                                description "The number of ipv6 packets dropped by the packet processor to traffic manager";
                                            }

                                            leaf ipv6-dropped-octets {
                                                type yang:counter64;
                                                description "The number of ipv6 octets dropped by the packet processor to traffic manager";
                                            }

                                            leaf ipv4-forwarded-packets {
                                                type yang:counter64;
                                                description "The number of ipv4 packets forwarded by the packet processor to traffic manager";
                                            }

                                            leaf ipv4-forwarded-octets {
                                                type yang:counter64;
                                                description "The number of ipv4 octets forwarded by the packet processor to traffic manager";
                                            }

                                            leaf ipv6-forwarded-packets {
                                                type yang:counter64;
                                                description "The number of ipv6 packets forwarded by the packet processor to traffic manager";
                                            }

                                            leaf ipv6-forwarded-octets {
                                                type yang:counter64;
                                                description "The number of ipv6 octets forwarded by the packet processor to traffic manager";
                                            }

                                        } // container v4-v6

                                    }
                                    case bonding {

                                        container bonding {
                                            description "Enter the bonding context";

                                            leaf connection-1-offered-packets {
                                                type yang:counter64;
                                                description "The number of connection-1 packets offered by the packet processor to traffic manager";
                                            }

                                            leaf connection-1-offered-octets {
                                                type yang:counter64;
                                                description "The number of connection-1 octets offered by the packet processor to traffic manager";
                                            }

                                            leaf connection-2-offered-packets {
                                                type yang:counter64;
                                                description "The number of connection-2 packets offered by the packet processor to traffic manager";
                                            }

                                            leaf connection-2-offered-octets {
                                                type yang:counter64;
                                                description "The number of connection-2 octets offered by the packet processor to traffic manager";
                                            }

                                            leaf connection-1-dropped-packets {
                                                type yang:counter64;
                                                description "The number of connection-1 packets dropped by the packet processor to traffic manager";
                                            }

                                            leaf connection-1-dropped-octets {
                                                type yang:counter64;
                                                description "The number of connection-1 octets dropped by the packet processor to traffic manager";
                                            }

                                            leaf connection-2-dropped-packets {
                                                type yang:counter64;
                                                description "The number of connection-2 packets dropped by the packet processor to traffic manager";
                                            }

                                            leaf connection-2-dropped-octets {
                                                type yang:counter64;
                                                description "The number of connection-2 octets dropped by the packet processor to traffic manager";
                                            }

                                            leaf connection-1-forwarded-packets {
                                                type yang:counter64;
                                                description "The number of connection-1 packets forwarded by the packet processor to traffic manager";
                                            }

                                            leaf connection-1-forwarded-octets {
                                                type yang:counter64;
                                                description "The number of connection-1 octets forwarded by the packet processor to traffic manager";
                                            }

                                            leaf connection-2-forwarded-packets {
                                                type yang:counter64;
                                                description "The number of connection-2 packets forwarded by the packet processor to traffic manager";
                                            }

                                            leaf connection-2-forwarded-octets {
                                                type yang:counter64;
                                                description "The number of connection-2 octets forwarded by the packet processor to traffic manager";
                                            }

                                        } // container bonding

                                    }
                                }
                            } // container statistics

                            container overrides {
                                description "Enter the overrides context";

                                leaf pir {
                                    type types-qos:policer-pir-rate-override;
                                    units "kilobps";
                                    description "PIR rate";
                                }

                                leaf cir {
                                    type types-qos:policer-cir-rate-override;
                                    units "kilobps";
                                    description "CIR rate";
                                }

                                leaf mbs {
                                    type types-qos:policer-burst-size-override;
                                    units "bytes";
                                    description "The maximum reserved buffer space";
                                }

                                leaf cbs {
                                    type types-qos:policer-burst-size-override;
                                    units "bytes";
                                    description "The committed buffer size";
                                }

                            } // container overrides

                        } // list policer

                        list queue {
                            key "queue-id";
                            description "Enter the queue list instance";

                            leaf queue-id {
                                type types-qos:egress-queue-id;
                                description "The unique identifier for the queue.";
                            }

                            container statistics {
                                description "Enter the statistics context";

                                choice stat-mode {
                                    case profile {

                                        container profile {
                                            description "Enter the profile context";

                                            leaf in-inplus-profile-forwarded-packets {
                                                type yang:counter64;
                                                description
                                                    "The number of in-profile/in-plus-profile packets
                                                     (rate below CIR) forwarded.";
                                            }

                                            leaf in-inplus-profile-forwarded-octets {
                                                type yang:counter64;
                                                description
                                                    "The number of in-profile/in-plus-profile octets
                                                     (rate below CIR) forwarded.";
                                            }

                                            leaf out-exceed-profile-forwarded-packets {
                                                type yang:counter64;
                                                description
                                                    "The number of out-profile/exceed-profile packets
                                                     (rate above CIR) forwarded.";
                                            }

                                            leaf out-exceed-profile-forwarded-octets {
                                                type yang:counter64;
                                                description
                                                    "The number of out-profile/exceed-profile octets
                                                     (rate above CIR) forwarded.";
                                            }

                                            leaf in-inplus-profile-dropped-packets {
                                                type yang:counter64;
                                                description
                                                    "The number of in-profile/in-plus-profile packets
                                                     discarded.";
                                            }

                                            leaf in-inplus-profile-dropped-octets {
                                                type yang:counter64;
                                                description
                                                    "The number of in-profile/in-plus-profile octets
                                                     discarded.";
                                            }

                                            leaf out-exceed-profile-dropped-packets {
                                                type yang:counter64;
                                                description
                                                    "The number of out-profile/exceed-profile packets
                                                     discarded.";
                                            }

                                            leaf out-exceed-profile-dropped-octets {
                                                type yang:counter64;
                                                description
                                                    "The number of out-profile/exceed-profile octets
                                                     discarded.";
                                            }

                                        } // container profile

                                    }
                                    case v4-v6 {

                                        container v4-v6 {
                                            description "Enter the v4-v6 context";

                                            leaf ipv4-dropped-packets {
                                                type yang:counter64;
                                                description "The number of ipv4 packets discarded.";
                                            }

                                            leaf ipv4-dropped-octets {
                                                type yang:counter64;
                                                description "The number of ipv4 octets discarded.";
                                            }

                                            leaf ipv6-dropped-packets {
                                                type yang:counter64;
                                                description "The number of ipv6 packets discarded.";
                                            }

                                            leaf ipv6-dropped-octets {
                                                type yang:counter64;
                                                description "The number of ipv6 octets discarded.";
                                            }

                                            leaf ipv4-forwarded-packets {
                                                type yang:counter64;
                                                description "The number of ipv4 packets forwarded.";
                                            }

                                            leaf ipv4-forwarded-octets {
                                                type yang:counter64;
                                                description "The number of ipv4 octets forwarded.";
                                            }

                                            leaf ipv6-forwarded-packets {
                                                type yang:counter64;
                                                description "The number of ipv6 packets forwarded.";
                                            }

                                            leaf ipv6-forwarded-octets {
                                                type yang:counter64;
                                                description "The number of ipv6 octets forwarded.";
                                            }

                                        } // container v4-v6

                                    }
                                }
                            } // container statistics

                            container overrides {
                                description "Enter the overrides context";

                                leaf pir {
                                    type types-qos:queue-pir-rate-override;
                                    units "kilobps";
                                    description "PIR rate";
                                }

                                leaf cir {
                                    type types-qos:queue-cir-rate-override;
                                    units "kilobps";
                                    description "CIR rate";
                                }

                                leaf mbs {
                                    type types-qos:queue-burst-size-override;
                                    units "bytes";
                                    description "The maximum reserved buffer space";
                                }

                                leaf cbs {
                                    type types-qos:queue-burst-size-override;
                                    units "bytes";
                                    description "The committed buffer size";
                                }

                                leaf wrr-weight {
                                    type types-qos:hs-wrr-weight-override;
                                    description
                                        "The Weighted Round Robin (WRR) weight with which
                                         this queue should parent into the scheduler.";
                                }

                                leaf class-weight {
                                    type types-qos:hs-class-weight-override;
                                    description "The scheduling class weight.";
                                }

                            } // container overrides

                        } // list queue

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                        list wrr-group {
                            key "group-id";
                            description "Enter the wrr-group list instance";

                            leaf group-id {
                                type types-qos:hs-wrr-group-id;
                                description "HS WRR group identifier";
                            }

                            container overrides {
                                description "Enter the overrides context";

                                leaf pir {
                                    type types-qos:hs-wrr-rate-override;
                                    units "kilobps";
                                    description "The rate (PIR) override for WRR group.";
                                }

                                leaf class-weight {
                                    type types-qos:hs-class-weight-override;
                                    description "The class weight override for WRR group.";
                                }

                            } // container overrides

                        } // list wrr-group

                        container statistics {
                            description "Enter the statistics context";

                            leaf in-inplus-profile-forwarded-packets {
                                type yang:counter64;
                                description
                                    "The number of in-profile/in-plus-profile packets
                                     (rate below CIR) forwarded.";
                            }

                            leaf in-inplus-profile-forwarded-octets {
                                type yang:counter64;
                                description
                                    "The number of in-profile/in-plus-profile octets
                                     (rate below CIR) forwarded.";
                            }

                            leaf out-exceed-profile-forwarded-packets {
                                type yang:counter64;
                                description
                                    "The number of out-profile/exceed-profile packets
                                     (rate above CIR) forwarded.";
                            }

                            leaf out-exceed-profile-forwarded-octets {
                                type yang:counter64;
                                description
                                    "The number of out-profile/exceed-profile octets
                                     (rate above CIR) forwarded.";
                            }

                            leaf in-inplus-profile-dropped-packets {
                                type yang:counter64;
                                description
                                    "The number of in-profile/in-plus-profile packets
                                     discarded.";
                            }

                            leaf in-inplus-profile-dropped-octets {
                                type yang:counter64;
                                description
                                    "The number of in-profile/in-plus-profile octets
                                     discarded.";
                            }

                            leaf out-exceed-profile-dropped-packets {
                                type yang:counter64;
                                description
                                    "The number of out-profile/exceed-profile packets
                                     discarded.";
                            }

                            leaf out-exceed-profile-dropped-octets {
                                type yang:counter64;
                                description
                                    "The number of out-profile/exceed-profile octets
                                     discarded.";
                            }

                            leaf ipv4-dropped-packets {
                                type yang:counter64;
                                description "The number of ipv4 packets discarded.";
                            }

                            leaf ipv4-dropped-octets {
                                type yang:counter64;
                                description "The number of ipv4 octets discarded.";
                            }

                            leaf ipv6-dropped-packets {
                                type yang:counter64;
                                description "The number of ipv6 packets discarded.";
                            }

                            leaf ipv6-dropped-octets {
                                type yang:counter64;
                                description "The number of ipv6 octets discarded.";
                            }

                            leaf ipv4-forwarded-packets {
                                type yang:counter64;
                                description "The number of ipv4 packets forwarded.";
                            }

                            leaf ipv4-forwarded-octets {
                                type yang:counter64;
                                description "The number of ipv4 octets forwarded.";
                            }

                            leaf ipv6-forwarded-packets {
                                type yang:counter64;
                                description "The number of ipv6 packets forwarded.";
                            }

                            leaf ipv6-forwarded-octets {
                                type yang:counter64;
                                description "The number of ipv6 octets forwarded.";
                            }

                        } // container statistics

                    } // container qos

                } // container egress

                container access-loop-information {
                    description "Enter the access-loop-information context";

                    leaf encap-offset {
                        type int32;
                        description
                            "Number of bytes added to or subtracted from the packet size
                             while performing rate calculations, in order to take into
                             account the encapsulation overhead in the DSL access loop.";
                    }

                    leaf data-link {
                        type enumeration {
                            enum "unknown"                      { value 0; }
                            enum "other"                        { value 1; }
                            enum "atm"                          { value 2; }
                        }
                        description "The type of data link in the DSL Access Loop.";
                    }

                } // container access-loop-information

                list session {
                    key "type id";
                    description "Enter the session list instance";

                    leaf type {
                        type types-submgt:session-type;
                        description "Session type";
                    }

                    leaf id {
                        type types-submgt:session-id;
                        description "Session identifier";
                    }

                    leaf mac-address {
                        type yang:mac-address;
                        description "MAC address";
                    }

                    leaf circuit-id {
                        type binary {
                            length "1..255";
                        }
                        description "Circuit ID";
                    }

                    leaf remote-id {
                        type binary {
                            length "1..255";
                        }
                        description "Remote ID";
                    }

                    leaf sap-session-index {
                        type uint32;
                        description "Unique index within the SAP";
                    }

                    leaf up-time {
                        type types-sros:time-interval;
                        description "Up-time";
                    }

                    leaf total-lifetime {
                        type types-sros:time-duration;
                        units "seconds";
                        description "Total lifetime";
                    }

                    leaf remaining-lifetime {
                        type types-sros:time-duration;
                        units "seconds";
                        description "Remaining lifetime";
                    }

                    leaf ignore-df-bit {
                        type boolean;
                        description
                            "Don't fragment bit in IP header is ignored and packets are
                             always fragmented when MTU is exceeded";
                    }

                    leaf anti-spoof {
                        type types-submgt:session-anti-spoof;
                        description "Anti-spoof type";
                    }

                    leaf persistence-key {
                        type uint32;
                        description "Persistence key";
                    }

                    leaf active {
                        type boolean;
                        description
                            "Active in a multi-chassis set-up or multi-chassis is not configured
                             (in which case it is always active...)";
                    }

                    container overrides {
                        description "Enter the overrides context";

                        container subscriber {
                            description "Enter the subscriber context";

                            container host-limit {
                                description "Enter the host-limit context";

                                leaf lac-overall {
                                    type int32;
                                    description "Overall LAC host limit";
                                }

                                leaf overall {
                                    type int32;
                                    description "Overall host limit";
                                }

                                container ipv4 {
                                    description "Enter the ipv4 context";

                                    leaf arp {
                                        type int32;
                                        description "IPv4 ARP host limit";
                                    }

                                    leaf dhcp {
                                        type int32;
                                        description "IPv4 DHCP host limit";
                                    }

                                    leaf overall {
                                        type int32;
                                        description "IPv4 overall host limit";
                                    }

                                    leaf ppp {
                                        type int32;
                                        description "Ipv4 PPP host limit";
                                    }

                                } // container ipv4

                                container ipv6 {
                                    description "Enter the ipv6 context";

                                    leaf overall {
                                        type int32;
                                        description "IPV6 overall host limit";
                                    }

                                    leaf pd-ipoe-dhcp {
                                        type int32;
                                        description "IPV6-PD IPOE DHCP host limit";
                                    }

                                    leaf pd-overall {
                                        type int32;
                                        description "IPV6-PD overall host limit";
                                    }

                                    leaf pd-ppp-dhcp {
                                        type int32;
                                        description "IPV6-PD PPP DHCP host limit";
                                    }

                                    leaf wan-overall {
                                        type int32;
                                        description "IPV6-WAN overall host limit";
                                    }

                                    leaf wan-ipoe-dhcp {
                                        type int32;
                                        description "IPv6-WAN IPOE DHCP host limit";
                                    }

                                    leaf wan-ipoe-slaac {
                                        type int32;
                                        description "IPv6-WAN IPOE SLAAC host limit";
                                    }

                                    leaf wan-ppp-dhcp {
                                        type int32;
                                        description "IPv6-WAN PPP DHCP host limit";
                                    }

                                    leaf wan-ppp-slaac {
                                        type int32;
                                        description "IPv6-WAN PPP SLAAC host limit";
                                    }

                                } // container ipv6

                            } // container host-limit

                            container session-limit {
                                description "Enter the session-limit context";

                                leaf ipoe {
                                    type int32;
                                    description "IPOE session limit";
                                }

                                leaf overall {
                                    type int32;
                                    description "Overall session limit";
                                }

                                container l2tp {
                                    description "Enter the l2tp context";

                                    leaf lns {
                                        type int32;
                                        description "LNS session limit";
                                    }

                                    leaf lts {
                                        type int32;
                                        description "LTS session limit";
                                    }

                                    leaf overall {
                                        type int32;
                                        description "Overall L2TP session limit";
                                    }

                                } // container l2tp

                                container pppoe {
                                    description "Enter the pppoe context";

                                    leaf lac {
                                        type int32;
                                        description "PPP LAC session limit";
                                    }

                                    leaf local {
                                        type int32;
                                        description "PPP local session limit";
                                    }

                                    leaf overall {
                                        type int32;
                                        description "Overall PPP session limit";
                                    }

                                } // container pppoe

                            } // container session-limit

                        } // container subscriber

                        container sla-profile-instance {
                            description "Enter the sla-profile-instance context";

                            container host-limit {
                                description "Enter the host-limit context";

                                leaf lac-overall {
                                    type int32;
                                    description "Overall LAC host limit";
                                }

                                leaf overall {
                                    type int32;
                                    description "Overall host limit";
                                }

                                container ipv4 {
                                    description "Enter the ipv4 context";

                                    leaf arp {
                                        type int32;
                                        description "IPv4 ARP host limit";
                                    }

                                    leaf dhcp {
                                        type int32;
                                        description "IPv4 DHCP host limit";
                                    }

                                    leaf overall {
                                        type int32;
                                        description "IPv4 overall host limit";
                                    }

                                    leaf ppp {
                                        type int32;
                                        description "Ipv4 PPP host limit";
                                    }

                                } // container ipv4

                                container ipv6 {
                                    description "Enter the ipv6 context";

                                    leaf overall {
                                        type int32;
                                        description "IPV6 overall host limit";
                                    }

                                    leaf pd-ipoe-dhcp {
                                        type int32;
                                        description "IPV6-PD IPOE DHCP host limit";
                                    }

                                    leaf pd-overall {
                                        type int32;
                                        description "IPV6-PD overall host limit";
                                    }

                                    leaf pd-ppp-dhcp {
                                        type int32;
                                        description "IPV6-PD PPP DHCP host limit";
                                    }

                                    leaf wan-overall {
                                        type int32;
                                        description "IPV6-WAN overall host limit";
                                    }

                                    leaf wan-ipoe-dhcp {
                                        type int32;
                                        description "IPv6-WAN IPOE DHCP host limit";
                                    }

                                    leaf wan-ipoe-slaac {
                                        type int32;
                                        description "IPv6-WAN IPOE SLAAC host limit";
                                    }

                                    leaf wan-ppp-dhcp {
                                        type int32;
                                        description "IPv6-WAN PPP DHCP host limit";
                                    }

                                    leaf wan-ppp-slaac {
                                        type int32;
                                        description "IPv6-WAN PPP SLAAC host limit";
                                    }

                                } // container ipv6

                            } // container host-limit

                            container session-limit {
                                description "Enter the session-limit context";

                                leaf ipoe {
                                    type int32;
                                    description "IPOE session limit";
                                }

                                leaf overall {
                                    type int32;
                                    description "Overall session limit";
                                }

                                container l2tp {
                                    description "Enter the l2tp context";

                                    leaf lns {
                                        type int32;
                                        description "LNS session limit";
                                    }

                                    leaf lts {
                                        type int32;
                                        description "LTS session limit";
                                    }

                                    leaf overall {
                                        type int32;
                                        description "Overall L2TP session limit";
                                    }

                                } // container l2tp

                                container pppoe {
                                    description "Enter the pppoe context";

                                    leaf lac {
                                        type int32;
                                        description "PPP LAC session limit";
                                    }

                                    leaf local {
                                        type int32;
                                        description "PPP local session limit";
                                    }

                                    leaf overall {
                                        type int32;
                                        description "Overall PPP session limit";
                                    }

                                } // container pppoe

                            } // container session-limit

                        } // container sla-profile-instance

                    } // container overrides

                    container service {
                        description "Enter the service context";

                        leaf retailer-service {
                            type types-services:service-name;
                            description "Retailer service";
                        }

                        leaf retailer-interface {
                            type types-sros:interface-name;
                            description "Retailer interface";
                        }

                        leaf termination-type {
                            type enumeration {
                                enum "local"                        { value 1; }
                                enum "local-wholesale"              { value 2; }
                                enum "local-retail"                 { value 3; }
                                enum "lac"                          { value 4; }
                            }
                            description
                                "Termination type of this session
                                 - local-wholesale: terminates in the wholesale service
                                 - local-retail:    terminates in the retail service
                                 - lac:             terminates in an L2TP Access Concentrator
                                 - local:           everything else";
                        }

                    } // container service

                    container pfcp {
                        description "Enter the pfcp context";

                        leaf association {
                            type types-sros:named-item;
                            description "PFCP association used by the PFCP session";
                        }

                        leaf session-id {
                            type types-submgt:pfcp-session-id;
                            description "Local Session Id used for the PFCP session";
                        }

                    } // container pfcp

                    container bonding {
                        description "Enter the bonding context";

                        leaf context-id {
                            type types-submgt:bonding-context-id;
                            description "Common identifier of the bonded connections";
                        }

                        leaf type {
                            type enumeration {
                                enum "bonding-session"              { value 0; }
                                enum "access-session"               { value 1; }
                            }
                            description "How this session is part of the bonding context";
                        }

                        container load-balancing {
                            description "Enter the load-balancing context";

                            leaf reference {
                                type uint32;
                                units "kilobps";
                                description "Reference rate of the preferred connection";
                            }

                            leaf high-threshold {
                                type uint32;
                                units "kilobps";
                                description "High-threshold rate of the preferred connection";
                            }

                            leaf low-threshold {
                                type uint32;
                                units "kilobps";
                                description "Low-threshold rate of the preferred connection";
                            }

                            leaf initial-weight {
                                type uint32;
                                units "percent";
                                description "Initial load-balancing weight of the preferred connection";
                            }

                            leaf weight-change {
                                type uint32;
                                units "percent";
                                description "Load-balancing weight change of the preferred connection";
                            }

                            leaf current-weight {
                                type uint32;
                                units "percent";
                                description "Current load-balancing weight of the preferred connection";
                            }

                        } // container load-balancing

                        container bonding-session {
                            description "Enter the bonding-session context";

                            leaf subscriber-id {
                                type types-submgt:subscriber-id;
                                description "Subscriber identifier";
                            }

                            leaf sla-profile-instance {
                                type types-submgt:sla-profile-instance-id;
                                description "SLA profile instance identifier";
                            }

                            leaf session-type {
                                type types-submgt:session-type;
                                description "Session type";
                            }

                            leaf session-id {
                                type types-submgt:session-id;
                                description "Session identifier";
                            }

                        } // container bonding-session

                        list access-session {
                            key "connection-index";
                            description "Enter the access-session list instance";

                            leaf connection-index {
                                type types-submgt:bonding-connection-index;
                                description "Bonding connection index";
                            }

                            leaf subscriber-id {
                                type types-submgt:subscriber-id;
                                description "Subscriber identifier";
                            }

                            leaf sla-profile-instance {
                                type types-submgt:sla-profile-instance-id;
                                description "SLA profile instance identifier";
                            }

                            leaf session-type {
                                type types-submgt:session-type;
                                description "Session type";
                            }

                            leaf session-id {
                                type types-submgt:session-id;
                                description "Session identifier";
                            }

                        } // list access-session

                    } // container bonding

                    container identification-strings {
                        description "Enter the identification-strings context";

                        leaf application-profile {
                            type types-sros:display-string;
                            description "Application profile string";
                        }

                        leaf ancp {
                            type types-sros:display-string {
                                length "1..63";
                            }
                            description "ANCP string";
                        }

                        leaf category-map {
                            type types-sros:named-item;
                            description "Category map name string";
                        }

                        leaf intermediate-destination-id {
                            type types-sros:display-string {
                                length "1..32";
                            }
                            description "Intermediate destination ID string, used to resolve vport, shaper, or queue group";
                        }

                        leaf sla-profile {
                            type types-sros:display-string;
                            description "SLA profile string";
                        }

                        leaf sub-profile {
                            type types-sros:display-string;
                            description "Subscriber profile string";
                        }

                    } // container identification-strings

                    container aaa {
                        description "Enter the aaa context";

                        leaf user-name {
                            type types-sros:display-string {
                                length "1..253";
                            }
                            description "Authentication user name";
                        }

                        leaf radius-accounting-session-id {
                            type types-submgt:accounting-session-id;
                            description "Id of the RADIUS accounting session";
                        }

                        leaf logical-line-id {
                            type binary {
                                length "0..64";
                            }
                            description "Authentication logical line id";
                        }

                        leaf subscriber-interface-prefix {
                            type types-sros:ipv6-prefix;
                            description "Aggregate route prefix for use with On-Demand Subnet Allocation";
                        }

                        leaf called-station-id {
                            type binary {
                                length "1..64";
                            }
                            description "Authentication called-station-id";
                        }

                        leaf last-authentication-time {
                            type yang:date-and-time;
                            description "Last time the session was authenticated";
                        }

                        leaf remaining-authentication-time {
                            type union {
                                type types-sros:time-duration;
                                type enumeration {
                                    enum "infinite"                     { value -1; }
                                }
                            }
                            units "seconds";
                            description
                                "Remaining authentication time. After this the next control
                                 packet will trigger re-authentication.";
                        }

                        leaf gx-session-id {
                            type string;
                            description "Identification of the Gx diameter session for the session";
                        }

                        list radius-accounting-overrides {
                            key "index";
                            description "Enter the radius-accounting-overrides list instance";

                            leaf index {
                                type uint32;
                                description "The index of the sub-profile on which the override is applied";
                            }

                            leaf policy {
                                type types-sros:named-item;
                                description "Configured radius-accounting-policy that matches this tag based on configuration order";
                            }

                            leaf update-interval-override {
                                type types-sros:time-duration;
                                units "seconds";
                                description "The override for the intermediate update interval";
                            }

                        } // list radius-accounting-overrides

                        list class-attribute {
                            key "index";
                            description "Enter the class-attribute list instance";

                            leaf index {
                                type uint32 {
                                    range "1..6";
                                }
                                description "Index of the class attribute";
                            }

                            leaf value {
                                type binary {
                                    length "1..253";
                                }
                                description "Value of the class attribute";
                            }

                        } // list class-attribute

                    } // container aaa

                    container vrgw {
                        description "Enter the vrgw context";

                        leaf bridge-domain {
                            type uint32;
                            description "Bridge Domain for WLAN-GW Home LAN Extension";
                        }

                    } // container vrgw

                    container ppp {
                        description "Enter the ppp context";

                        leaf lcp-state {
                            type types-ppp:ppp-control-protocol-state;
                            description "Operational state of the Link Control Protocol (LCP)";
                        }

                        leaf authentication-protocol {
                            type types-ppp:authentication-protocol;
                            description "Authentication protocol";
                        }

                        leaf user-name {
                            type types-ppp:user-name;
                            description "User name learned during session setup";
                        }

                        leaf mtu {
                            type uint32;
                            description "Negotiated MTU";
                        }

                        leaf pppoe-session-id {
                            type uint32;
                            description "Session id as used in the PPPoE protocol";
                        }

                        leaf type {
                            type types-ppp:session-type;
                            description "PPP session type";
                        }

                        leaf ipcp-state {
                            type types-ppp:ppp-control-protocol-state;
                            description "Operational state of the v4 Internet Protocol Control Protocol (IPCP)";
                        }

                        leaf ipv6cp-state {
                            type types-ppp:ppp-control-protocol-state;
                            description "Operational state of the v6 Internet Protocol Control Protocol (IPv6CP)";
                        }

                        container to-lac {
                            description "Enter the to-lac context";

                            leaf router-instance {
                                type types-sros:router-instance;
                                description "The router instance of the L2TP session";
                            }

                            leaf connection-id {
                                type types-l2tp:connection-id;
                                description "The local connection-id of the L2TP session.";
                            }

                        } // container to-lac

                        container to-lns {
                            description "Enter the to-lns context";

                            leaf router-instance {
                                type types-sros:router-instance;
                                description "The router instance of the L2TP session";
                            }

                            leaf connection-id {
                                type types-l2tp:connection-id;
                                description "The local connection-id of the L2TP session.";
                            }

                        } // container to-lns

                        container l2tp-steering {
                            description "Enter the l2tp-steering context";

                            leaf profile {
                                type types-sros:named-item;
                                description "Steering profile";
                            }

                            leaf oper-state {
                                type enumeration {
                                    enum "steered"                      { value 2; }
                                    enum "steering-failed"              { value 3; }
                                }
                                description "Operational state";
                            }

                        } // container l2tp-steering

                        container access-loop-information {
                            description "Enter the access-loop-information context";

                            leaf data-link {
                                type types-submgt:data-link;
                                description "Type of data link in the DSL Access Loop";
                            }

                            leaf encap-1 {
                                type types-submgt:access-loop-encap-1;
                                description "Encapsulation used on the DSL access loop";
                            }

                            leaf encap-2 {
                                type types-submgt:access-loop-encap-2;
                                description "Encapsulation used on the DSL access loop";
                            }

                            leaf data-rate-downstream {
                                type uint32;
                                units "kilobps";
                                description "Nominal downstream data rate of the link";
                            }

                            leaf origin {
                                type types-submgt:session-address-origin;
                                description "Origin";
                            }

                        } // container access-loop-information

                        container statistics {
                            description "Enter the statistics context";

                            leaf unknown-protocol {
                                type yang:counter32;
                                description "Number of packets with unknown PPP protocol received.";
                            }

                            container lcp {
                                description "Enter the lcp context";

                                container rx {
                                    description "Enter the rx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                    leaf protocol-reject {
                                        type yang:counter32;
                                        description "The number of protocol rejects.";
                                    }

                                    leaf echo-request {
                                        type yang:counter32;
                                        description "The number of echo requests.";
                                    }

                                    leaf echo-reply {
                                        type yang:counter32;
                                        description "The number of echo replies.";
                                    }

                                    leaf discard-request {
                                        type yang:counter32;
                                        description "The number of discard requests.";
                                    }

                                } // container rx

                                container tx {
                                    description "Enter the tx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                    leaf protocol-reject {
                                        type yang:counter32;
                                        description "The number of protocol rejects.";
                                    }

                                    leaf echo-request {
                                        type yang:counter32;
                                        description "The number of echo requests.";
                                    }

                                    leaf echo-reply {
                                        type yang:counter32;
                                        description "The number of echo replies.";
                                    }

                                    leaf discard-request {
                                        type yang:counter32;
                                        description "The number of discard requests.";
                                    }

                                } // container tx

                            } // container lcp

                            container ipcp {
                                description "Enter the ipcp context";

                                container rx {
                                    description "Enter the rx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                } // container rx

                                container tx {
                                    description "Enter the tx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                } // container tx

                            } // container ipcp

                            container ipv6cp {
                                description "Enter the ipv6cp context";

                                container rx {
                                    description "Enter the rx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                } // container rx

                                container tx {
                                    description "Enter the tx context";

                                    leaf configure-request {
                                        type yang:counter32;
                                        description "The number of configure requests.";
                                    }

                                    leaf configure-ack {
                                        type yang:counter32;
                                        description "The number of configure acknowledgements.";
                                    }

                                    leaf configure-nak {
                                        type yang:counter32;
                                        description "The number of negative configure acknowledgements.";
                                    }

                                    leaf configure-reject {
                                        type yang:counter32;
                                        description "The number of configure rejects.";
                                    }

                                    leaf terminate-request {
                                        type yang:counter32;
                                        description "The number of terminate requests.";
                                    }

                                    leaf terminate-ack {
                                        type yang:counter32;
                                        description "The number of terminate acknowledgements.";
                                    }

                                    leaf code-reject {
                                        type yang:counter32;
                                        description "The number of code rejects.";
                                    }

                                } // container tx

                            } // container ipv6cp

                            container pap {
                                description "Enter the pap context";

                                container rx {
                                    description "Enter the rx context";

                                    leaf authentication-request {
                                        type yang:counter32;
                                        description "The number of authentication requests.";
                                    }

                                } // container rx

                                container tx {
                                    description "Enter the tx context";

                                    leaf authentication-ack {
                                        type yang:counter32;
                                        description "The number of authentication acknowledgements.";
                                    }

                                    leaf authentication-nak {
                                        type yang:counter32;
                                        description "The number of negative authentication acknowledgements.";
                                    }

                                } // container tx

                            } // container pap

                            container chap {
                                description "Enter the chap context";

                                container rx {
                                    description "Enter the rx context";

                                    leaf response {
                                        type yang:counter32;
                                        description "The number of authentication responses.";
                                    }

                                } // container rx

                                container tx {
                                    description "Enter the tx context";

                                    leaf challenge {
                                        type yang:counter32;
                                        description "The number of authentication challenges.";
                                    }

                                    leaf success {
                                        type yang:counter32;
                                        description "The number of authentication acknowledgements.";
                                    }

                                    leaf failure {
                                        type yang:counter32;
                                        description "The number of negative authentication acknowledgements.";
                                    }

                                } // container tx

                            } // container chap

                        } // container statistics

                    } // container ppp

                    container mlppp {
                        description "Enter the mlppp context";

                        leaf max-links {
                            type uint32;
                            description "Maximum number of links in the bundle";
                        }

                        leaf fragment-size {
                            type uint32;
                            units "bytes";
                            description "Fragment size for this bundle";
                        }

                        leaf reassembly-timeout {
                            type uint32;
                            units "milliseconds";
                            description "Time after which buffered fragments of the frame are discarded";
                        }

                        leaf egress-rate {
                            type uint32;
                            units "kilobps";
                            description "Nominal egress rate for this bundle";
                        }

                        container local-parameters {
                            description "Enter the local-parameters context";

                            leaf mrru {
                                type uint32;
                                description "Maximum Reconstructed Receive Unit (MRRU)";
                            }

                            leaf short-sequence-numbers {
                                type boolean;
                                description "Packets are transmitted with short sequence numbers";
                            }

                            container endpoint {
                                description "Enter the endpoint context";

                                leaf endpoint-class {
                                    type types-ppp:mlppp-endpoint-class;
                                    description "Endpoint class";
                                }

                                leaf endpoint-id {
                                    type binary {
                                        length "1..20";
                                    }
                                    description "Endpoint identifier";
                                }

                                leaf description {
                                    type types-sros:description;
                                    description "The endpoint description.";
                                }

                            } // container endpoint

                        } // container local-parameters

                        container remote-parameters {
                            description "Enter the remote-parameters context";

                            leaf mrru {
                                type uint32;
                                description "Maximum Reconstructed Receive Unit (MRRU)";
                            }

                            leaf short-sequence-numbers {
                                type boolean;
                                description "Packets are transmitted with short sequence numbers";
                            }

                            container endpoint {
                                description "Enter the endpoint context";

                                leaf endpoint-class {
                                    type types-ppp:mlppp-endpoint-class;
                                    description "Endpoint class";
                                }

                                leaf endpoint-id {
                                    type binary {
                                        length "1..20";
                                    }
                                    description "Endpoint identifier";
                                }

                                leaf description {
                                    type types-sros:description;
                                    description "The endpoint description.";
                                }

                            } // container endpoint

                        } // container remote-parameters

                        container requested {
                            description "Enter the requested context";

                            leaf link-fragmentation-and-interleaving {
                                type boolean;
                                description "High priority traffic is interleaved with fragments on a single MLPPP link";
                            }

                            leaf max-delay {
                                type uint32;
                                units "milliseconds";
                                description "Maximum allowed fragment delay caused by the transmission on the link";
                            }

                        } // container requested

                        container granted {
                            description "Enter the granted context";

                            leaf link-fragmentation-and-interleaving {
                                type boolean;
                                description "High priority traffic is interleaved with fragments on a single MLPPP link";
                            }

                            leaf max-delay {
                                type uint32;
                                units "milliseconds";
                                description "Maximum allowed fragment delay caused by the transmission on the link";
                            }

                        } // container granted

                        list link-session {
                            key "link-id";
                            description "Enter the link-session list instance";

                            leaf link-id {
                                type uint32;
                                description "PPP session id of the link";
                            }

                            leaf remote-mrru {
                                type uint32;
                                units "bytes";
                                description "Maximum Reconstructed Receive Unit(MRRU) proposed by the peer";
                            }

                            leaf up-time {
                                type uint32;
                                units "centiseconds";
                                description "Session up-time";
                            }

                            leaf lcp-state {
                                type types-ppp:ppp-control-protocol-state;
                                description "Operational state of the Link Control Protocol (LCP)";
                            }

                            leaf authentication-protocol {
                                type types-ppp:authentication-protocol;
                                description "Authentication protocol";
                            }

                            leaf user-name {
                                type types-ppp:user-name;
                                description "User name learned during session setup";
                            }

                            leaf mtu {
                                type uint32;
                                description "Negotiated MTU";
                            }

                            container to-lac {
                                description "Enter the to-lac context";

                                leaf router-instance {
                                    type types-sros:router-instance;
                                    description "The router instance of the L2TP session";
                                }

                                leaf connection-id {
                                    type types-l2tp:connection-id;
                                    description "The local connection-id of the L2TP session.";
                                }

                            } // container to-lac

                            container statistics {
                                description "Enter the statistics context";

                                container lcp {
                                    description "Enter the lcp context";

                                    container rx {
                                        description "Enter the rx context";

                                        leaf configure-request {
                                            type yang:counter32;
                                            description "The number of configure requests.";
                                        }

                                        leaf configure-ack {
                                            type yang:counter32;
                                            description "The number of configure acknowledgements.";
                                        }

                                        leaf configure-nak {
                                            type yang:counter32;
                                            description "The number of negative configure acknowledgements.";
                                        }

                                        leaf configure-reject {
                                            type yang:counter32;
                                            description "The number of configure rejects.";
                                        }

                                        leaf terminate-request {
                                            type yang:counter32;
                                            description "The number of terminate requests.";
                                        }

                                        leaf terminate-ack {
                                            type yang:counter32;
                                            description "The number of terminate acknowledgements.";
                                        }

                                        leaf code-reject {
                                            type yang:counter32;
                                            description "The number of code rejects.";
                                        }

                                        leaf protocol-reject {
                                            type yang:counter32;
                                            description "The number of protocol rejects.";
                                        }

                                        leaf echo-request {
                                            type yang:counter32;
                                            description "The number of echo requests.";
                                        }

                                        leaf echo-reply {
                                            type yang:counter32;
                                            description "The number of echo replies.";
                                        }

                                        leaf discard-request {
                                            type yang:counter32;
                                            description "The number of discard requests.";
                                        }

                                    } // container rx

                                    container tx {
                                        description "Enter the tx context";

                                        leaf configure-request {
                                            type yang:counter32;
                                            description "The number of configure requests.";
                                        }

                                        leaf configure-ack {
                                            type yang:counter32;
                                            description "The number of configure acknowledgements.";
                                        }

                                        leaf configure-nak {
                                            type yang:counter32;
                                            description "The number of negative configure acknowledgements.";
                                        }

                                        leaf configure-reject {
                                            type yang:counter32;
                                            description "The number of configure rejects.";
                                        }

                                        leaf terminate-request {
                                            type yang:counter32;
                                            description "The number of terminate requests.";
                                        }

                                        leaf terminate-ack {
                                            type yang:counter32;
                                            description "The number of terminate acknowledgements.";
                                        }

                                        leaf code-reject {
                                            type yang:counter32;
                                            description "The number of code rejects.";
                                        }

                                        leaf protocol-reject {
                                            type yang:counter32;
                                            description "The number of protocol rejects.";
                                        }

                                        leaf echo-request {
                                            type yang:counter32;
                                            description "The number of echo requests.";
                                        }

                                        leaf echo-reply {
                                            type yang:counter32;
                                            description "The number of echo replies.";
                                        }

                                        leaf discard-request {
                                            type yang:counter32;
                                            description "The number of discard requests.";
                                        }

                                    } // container tx

                                } // container lcp

                                container ipcp {
                                    description "Enter the ipcp context";

                                } // container ipcp

                                container ipv6cp {
                                    description "Enter the ipv6cp context";

                                } // container ipv6cp

                                container pap {
                                    description "Enter the pap context";

                                    container rx {
                                        description "Enter the rx context";

                                        leaf authentication-request {
                                            type yang:counter32;
                                            description "The number of authentication requests.";
                                        }

                                    } // container rx

                                    container tx {
                                        description "Enter the tx context";

                                        leaf authentication-ack {
                                            type yang:counter32;
                                            description "The number of authentication acknowledgements.";
                                        }

                                        leaf authentication-nak {
                                            type yang:counter32;
                                            description "The number of negative authentication acknowledgements.";
                                        }

                                    } // container tx

                                } // container pap

                                container chap {
                                    description "Enter the chap context";

                                    container rx {
                                        description "Enter the rx context";

                                        leaf response {
                                            type yang:counter32;
                                            description "The number of authentication responses.";
                                        }

                                    } // container rx

                                    container tx {
                                        description "Enter the tx context";

                                        leaf challenge {
                                            type yang:counter32;
                                            description "The number of authentication challenges.";
                                        }

                                        leaf success {
                                            type yang:counter32;
                                            description "The number of authentication acknowledgements.";
                                        }

                                        leaf failure {
                                            type yang:counter32;
                                            description "The number of negative authentication acknowledgements.";
                                        }

                                    } // container tx

                                } // container chap

                            } // container statistics

                        } // list link-session

                    } // container mlppp

                    container gtp {
                        description "Enter the gtp context";

                        container uplink {
                            description "Enter the uplink context";

                            leaf ipv4-local-breakout {
                                type boolean;
                                description
                                    "Redirect ipv4 traffic to NAT for local routing instead of
                                     tunneling to a GGSN or PGW";
                            }

                        } // container uplink

                        container s11 {
                            description "Enter the s11 context";

                            container pdn-session {
                                description "Enter the pdn-session context";

                                leaf imsi {
                                    type types-cellular:imsi;
                                    description "International Mobile Subscriber Identity";
                                }

                                leaf apn {
                                    type types-cellular:apn;
                                    description "Access point name";
                                }

                                container mme {
                                    description "Enter the mme context";

                                    leaf control-address {
                                        type types-sros:ip-address;
                                        description "Control IP address";
                                    }

                                    leaf control-teid {
                                        type uint32;
                                        description "Control Transport Endpoint Identifier (TEID)";
                                    }

                                } // container mme

                                container local {
                                    description "Enter the local context";

                                    leaf router {
                                        type types-sros:router-instance;
                                        description "Router";
                                    }

                                    leaf control-address {
                                        type types-sros:ip-address;
                                        description "Control IP address";
                                    }

                                    leaf control-teid {
                                        type uint32;
                                        description "Control Transport Endpoint Identifier (TEID)";
                                    }

                                } // container local

                                container qos {
                                    description "Enter the qos context";

                                    leaf uplink-ambr {
                                        type uint32;
                                        units "kilobps";
                                        description "Uplink Aggregate Maximum Bit Rate";
                                    }

                                    leaf downlink-ambr {
                                        type uint32;
                                        units "kilobps";
                                        description "Downlink Aggregate Maximum Bit Rate";
                                    }

                                } // container qos

                                container charging-characteristics {
                                    description "Enter the charging-characteristics context";

                                    leaf bit0 {
                                        type boolean;
                                        description "Set bit 0 in charging characteristics information element (IE) for home UE";
                                    }

                                    leaf bit1 {
                                        type boolean;
                                        description "Set bit 1 in charging characteristics information element (IE) for home UE";
                                    }

                                    leaf bit2 {
                                        type boolean;
                                        description "Set bit 2 in charging characteristics information element (IE) for home UE";
                                    }

                                    leaf bit3 {
                                        type boolean;
                                        description "Set bit 3 in charging characteristics information element (IE) for home UE";
                                    }

                                    leaf bit4 {
                                        type boolean;
                                        description "Set bit 4 in charging characteristics information element (IE) for home UE";
                                    }

                                    leaf bit5 {
                                        type boolean;
                                        description "Set bit 5 in charging characteristics information element (IE) for home UE";
                                    }

                                    leaf bit6 {
                                        type boolean;
                                        description "Set bit 6 in charging characteristics information element (IE) for home UE";
                                    }

                                    leaf bit7 {
                                        type boolean;
                                        description "Set bit 7 in charging characteristics information element (IE) for home UE";
                                    }

                                    leaf bit8 {
                                        type boolean;
                                        description "Set bit 8 in charging characteristics information element (IE) for home UE";
                                    }

                                    leaf bit9 {
                                        type boolean;
                                        description "Set bit 9 in charging characteristics information element (IE) for home UE";
                                    }

                                    leaf bit10 {
                                        type boolean;
                                        description "Set bit 10 in charging characteristics information element (IE) for home UE";
                                    }

                                    leaf bit11 {
                                        type boolean;
                                        description "Set bit 11 in charging characteristics information element (IE) for home UE";
                                    }

                                    leaf bit12 {
                                        type boolean;
                                        description "Set bit 12 in charging characteristics information element (IE) for home UE";
                                    }

                                    leaf bit13 {
                                        type boolean;
                                        description "Set bit 13 in charging characteristics information element (IE) for home UE";
                                    }

                                    leaf bit14 {
                                        type boolean;
                                        description "Set bit 14 in charging characteristics information element (IE) for home UE";
                                    }

                                    leaf bit15 {
                                        type boolean;
                                        description "Set bit 15 in charging characteristics information element (IE) for home UE";
                                    }

                                } // container charging-characteristics

                                container user-location-information {
                                    description "Enter the user-location-information context";

                                    container cgi {
                                        description "Enter the cgi context";

                                        leaf mcc {
                                            type string;
                                            description "Mobile Country Code";
                                        }

                                        leaf mnc {
                                            type string;
                                            description "Mobile Network Code";
                                        }

                                        leaf lac {
                                            type string;
                                            description "Location Area Code";
                                        }

                                        leaf ci {
                                            type string;
                                            description "Cell Identity";
                                        }

                                    } // container cgi

                                    container sai {
                                        description "Enter the sai context";

                                        leaf mcc {
                                            type string;
                                            description "Mobile Country Code";
                                        }

                                        leaf mnc {
                                            type string;
                                            description "Mobile Network Code";
                                        }

                                        leaf lac {
                                            type string;
                                            description "Location Area Code";
                                        }

                                        leaf sac {
                                            type string;
                                            description "Service Area Code";
                                        }

                                    } // container sai

                                    container rai {
                                        description "Enter the rai context";

                                        leaf mcc {
                                            type string;
                                            description "Mobile Country Code";
                                        }

                                        leaf mnc {
                                            type string;
                                            description "Mobile Network Code";
                                        }

                                        leaf lac {
                                            type string;
                                            description "Location Area Code";
                                        }

                                        leaf rac {
                                            type string;
                                            description "Routing Area Code";
                                        }

                                    } // container rai

                                    container tai {
                                        description "Enter the tai context";

                                        leaf mcc {
                                            type string;
                                            description "Mobile Country Code";
                                        }

                                        leaf mnc {
                                            type string;
                                            description "Mobile Network Code";
                                        }

                                        leaf tac {
                                            type string;
                                            description "Tracking Area Code";
                                        }

                                    } // container tai

                                    container ecgi {
                                        description "Enter the ecgi context";

                                        leaf mcc {
                                            type string;
                                            description "Mobile Country Code";
                                        }

                                        leaf mnc {
                                            type string;
                                            description "Mobile Network Code";
                                        }

                                        leaf eci {
                                            type string;
                                            description "E-UTRAN Cell Identifier";
                                        }

                                    } // container ecgi

                                } // container user-location-information

                                list bearer {
                                    key "bearer-id";
                                    description "Enter the bearer list instance";

                                    leaf bearer-id {
                                        type uint32;
                                        description "Identifier";
                                    }

                                    container e-node-b {
                                        description "Enter the e-node-b context";

                                        leaf data-address {
                                            type types-sros:ip-address;
                                            description "IP address";
                                        }

                                        leaf data-teid {
                                            type uint32;
                                            description "Data Transport Endpoint Identifier (TEID)";
                                        }

                                    } // container e-node-b

                                    container local {
                                        description "Enter the local context";

                                        leaf data-teid {
                                            type uint32;
                                            description "Data Transport Endpoint Identifier (TEID)";
                                        }

                                    } // container local

                                    container qos {
                                        description "Enter the qos context";

                                        leaf uplink-gbr {
                                            type uint32;
                                            units "kilobps";
                                            description "Uplink Guaranteed Bit Rate";
                                        }

                                        leaf uplink-mbr {
                                            type uint32;
                                            units "kilobps";
                                            description "Uplink Maximum Bit Rate";
                                        }

                                        leaf downlink-gbr {
                                            type uint32;
                                            units "kilobps";
                                            description "Downlinklink Guaranteed Bit Rate";
                                        }

                                        leaf downlink-mbr {
                                            type uint32;
                                            units "kilobps";
                                            description "Downlink Maximum Bit Rate";
                                        }

                                        leaf qci {
                                            type uint32;
                                            description "QoS Class ID";
                                        }

                                        leaf arp {
                                            type uint32;
                                            description "Allocation/Retention Priority";
                                        }

                                    } // container qos

                                } // list bearer

                            } // container pdn-session

                        } // container s11

                    } // container gtp

                    list managed-route {
                        key "ip-prefix";
                        description "Enter the managed-route list instance";

                        leaf ip-prefix {
                            type types-sros:ip-prefix;
                            description "Managed route";
                        }

                        leaf oper-state {
                            type types-submgt:managed-route-state;
                            description "Operational state of the managed route";
                        }

                        leaf metric {
                            type uint32 {
                                range "0..65535";
                            }
                            description "Metric";
                        }

                        leaf preference {
                            type uint32 {
                                range "0..255";
                            }
                            description "Preference";
                        }

                        leaf tag {
                            type uint32;
                            description "Tag";
                        }

                    } // list managed-route

                    container ipv4 {
                        description "Enter the ipv4 context";

                        leaf-list dns {
                            type types-sros:ipv4-address;
                            description "DNS servers";
                        }

                        leaf dns-origin {
                            type types-submgt:session-address-origin;
                            description "Source from which the DNS server information is obtained";
                        }

                        leaf-list nbns {
                            type types-sros:ipv4-address;
                            description "NBNS servers";
                        }

                        leaf nbns-origin {
                            type types-submgt:session-address-origin;
                            description "Source from which the NBNS server information are obtained";
                        }

                        leaf forwarding-state {
                            type types-sros:oper-state;
                            description "Forwarding state";
                        }

                        leaf origin {
                            type types-submgt:subscriber-host-origin;
                            description "Origin";
                        }

                        leaf radius-accounting-session-id {
                            type types-submgt:accounting-session-id;
                            description "Id of the RADIUS accounting session";
                        }

                        leaf netmask {
                            type types-sros:ipv4-address;
                            description "IP netmask";
                        }

                        leaf default-router {
                            type types-sros:ipv4-address;
                            description "Default router";
                        }

                        leaf bgp-peering-status {
                            type types-submgt:bgp-peering-state;
                            description "BGP peering status";
                        }

                        leaf rip-listener-status {
                            type types-submgt:rip-listener-state;
                            description "Status of the RIP listener";
                        }

                        container ip-address {
                            description "Enter the ip-address context";

                            leaf address {
                                type types-sros:ipv4-address;
                                description "IPv4 address assigned to the session";
                            }

                            leaf pool {
                                type types-sros:named-item;
                                description "Local address pool from which the assigned IPv4 address has been drawn";
                            }

                            leaf origin {
                                type types-submgt:session-address-origin;
                                description "Origin from which the ipv4 address has been assigned";
                            }

                            leaf routing-origin {
                                type types-submgt:routing-origin;
                                description "Origin of the address as used by routing policies";
                            }

                        } // container ip-address

                        container dhcp-lease {
                            description "Enter the dhcp-lease context";

                            leaf creation-time {
                                type yang:date-and-time;
                                description "Creation time";
                            }

                            leaf server-address {
                                type types-sros:ip-address;
                                description "Server IP address";
                            }

                            leaf expiration-time {
                                type yang:date-and-time;
                                description "Expiration time";
                            }

                            leaf up-time {
                                type uint32;
                                units "seconds";
                                description "Up-time";
                            }

                            leaf last-renew-time {
                                type yang:date-and-time;
                                description "Most recent renew time";
                            }

                            leaf remaining-lease-time {
                                type union {
                                    type uint32 {
                                        range "0..4294967294";
                                    }
                                    type enumeration {
                                        enum "infinite"                     { value -1; }
                                    }
                                }
                                units "seconds";
                                description "Remaining lease time";
                            }

                            leaf lease-split {
                                type boolean;
                                description "DHCP proxy server overrides the lease-time value provided by DHCP server or RADIUS server";
                            }

                            leaf lease-time {
                                type uint32;
                                units "seconds";
                                description "Lease time";
                            }

                            leaf nak-next-renew {
                                type boolean;
                                description
                                    "Next DHCP lease renewal request sent by the client will
                                     be answered with a DHCP-NAK";
                            }

                            leaf option-60-vendor-class-id {
                                type string;
                                description "Vendor class identifier (option 60)";
                            }

                            leaf option-82-circuit-id {
                                type string;
                                description "Circuit-id (option 82)";
                            }

                            leaf option-82-remote-id {
                                type string;
                                description "Remote-id (option 82)";
                            }

                            leaf broadcast {
                                type types-sros:ipv4-address;
                                description "Broadcast ip-address";
                            }

                        } // container dhcp-lease

                        container arp {
                            description "Enter the arp context";

                            leaf last-refresh-time {
                                type yang:date-and-time;
                                description "Last time the arp host was refreshed";
                            }

                        } // container arp

                        container shcv {
                            description "Enter the shcv context";

                            leaf oper-state {
                                type types-submgt:shcv-oper-state;
                                description "Operational state";
                            }

                            leaf requests-sent {
                                type uint32;
                                description "Number of host connectivity check requests sent";
                            }

                            leaf replies-received {
                                type uint32;
                                description "Number of host connectivity check replies received";
                            }

                            leaf last-reply-time {
                                type yang:date-and-time;
                                description "Time of the last successful host connectivity reply";
                            }

                        } // container shcv

                        container bgp-peering-parameters {
                            description "Enter the bgp-peering-parameters context";

                            leaf policy {
                                type types-sros:named-item;
                                description "BGP peering policy";
                            }

                            leaf authentication-key-chain {
                                type types-sros:named-item;
                                description "Authentication key chain";
                            }

                            leaf md5-authentication-key {
                                type binary {
                                    length "1..255";
                                }
                                description "MD5 authentication key";
                            }

                            leaf import-policy {
                                type types-sros:named-item;
                                description "Routing policy controling BGP advertisements received from the peer";
                            }

                            leaf export-policy {
                                type types-sros:named-item;
                                description "Routing policy controling BGP advertisements sent to the peer";
                            }

                            leaf autonomous-system {
                                type uint32;
                                description "Autonomous system number of the remote peer";
                            }

                        } // container bgp-peering-parameters

                        container rip-listener-parameters {
                            description "Enter the rip-listener-parameters context";

                            leaf policy {
                                type types-sros:named-item;
                                description "RIP policy used to set up the RIP listener for this lease state";
                            }

                        } // container rip-listener-parameters

                        container wpp {
                            description "Enter the wpp context";

                            leaf oper-state {
                                type enumeration {
                                    enum "initial"                      { value 1; }
                                    enum "registering"                  { value 2; }
                                    enum "registered"                   { value 3; }
                                    enum "authenticating"               { value 4; }
                                    enum "authenticated"                { value 5; }
                                }
                                description "Operational WPP state for this lease state";
                            }

                            leaf router-instance {
                                type types-sros:router-instance;
                                description "Routing instance through which the WPP portal is reachable";
                            }

                            leaf portal {
                                type types-sros:named-item;
                                description "WPP portal name";
                            }

                            leaf portal-group {
                                type types-sros:named-item;
                                description "WPP portal group name";
                            }

                            leaf restore-on-disconnect {
                                type boolean;
                                description "Initial profiles are restored for the session once it disconnects from the WPP portal";
                            }

                            leaf is-triggered {
                                type boolean;
                                description "Session creation is triggered by WPP";
                            }

                            leaf initial-sub-profile {
                                type types-sros:named-item;
                                description "Initial subscriber profile used before WPP portal is contacted";
                            }

                            leaf initial-sla-profile {
                                type types-sros:named-item;
                                description "Initial SLA profile used before WPP portal is contacted";
                            }

                            leaf local-user-db {
                                type types-sros:named-item;
                                description "Local user database from which initial profiles are restored";
                            }

                            leaf authentication-policy {
                                type types-sros:named-item;
                                description "Radius authentication policy used before WPP portal is contacted";
                            }

                        } // container wpp

                        container nat {
                            description "Enter the nat context";

                            list nat-policy {
                                key "name";
                                description "Enter the nat-policy list instance";

                                leaf name {
                                    type types-sros:named-item;
                                    description "Policy name";
                                }

                                leaf vas-filter {
                                    type types-sros:named-item;
                                    description "Override filter used for Value Added Services (VAS) steering";
                                }

                                container intra-chassis-redundancy {
                                    description "Enter the intra-chassis-redundancy context";

                                    leaf bypass-active {
                                        type boolean;
                                        description
                                            "Traffic from a failed MS-ISA is routed according to the routing
                                             table without being NAT-ed";
                                    }

                                } // container intra-chassis-redundancy

                                container dnat-override {
                                    description "Enter the dnat-override context";

                                    leaf admin-state {
                                        type types-sros:admin-state;
                                        description "Whether the host's traffic should be subjected to DNAT";
                                    }

                                    leaf default-address {
                                        type types-sros:ipv4-address;
                                        description "The default DNAT address to substitute for the destination IP address";
                                    }

                                } // container dnat-override

                                container outside {
                                    description "Enter the outside context";

                                    leaf first-port {
                                        type types-sros:tcp-udp-port;
                                        description "First outside port";
                                    }

                                    leaf last-port {
                                        type types-sros:tcp-udp-port;
                                        description "Last outside port";
                                    }

                                } // container outside

                            } // list nat-policy

                        } // container nat

                    } // container ipv4

                    container ipv6 {
                        description "Enter the ipv6 context";

                        leaf-list dns {
                            type types-sros:ipv6-address;
                            description "DNS servers";
                        }

                        leaf interface-id {
                            type binary {
                                length "8";
                            }
                            description "IPV6CP Interface Identifier";
                        }

                        leaf router-advertisement-policy {
                            type types-sros:named-item;
                            description "Router advertisement (RA) policy";
                        }

                        container na {
                            description "Enter the na context";

                            leaf forwarding-state {
                                type types-sros:oper-state;
                                description "Forwarding state";
                            }

                            leaf origin {
                                type types-submgt:subscriber-host-origin;
                                description "Origin";
                            }

                            leaf radius-accounting-session-id {
                                type types-submgt:accounting-session-id;
                                description "Id of the RADIUS accounting session";
                            }

                            leaf bgp-peering-status {
                                type types-submgt:bgp-peering-state;
                                description "BGP peering status";
                            }

                            container ip-prefix {
                                description "Enter the ip-prefix context";

                                leaf prefix {
                                    type types-sros:ipv6-prefix;
                                    description "IPv6 prefix assigned to the session";
                                }

                                leaf pool {
                                    type types-sros:named-item;
                                    description "Local address pool from which the prefix has been allocated";
                                }

                                leaf origin {
                                    type types-submgt:session-address-origin;
                                    description "Origin of the address";
                                }

                                leaf routing-origin {
                                    type types-submgt:routing-origin;
                                    description "Origin of the address as used by routing policies";
                                }

                            } // container ip-prefix

                            container shcv {
                                description "Enter the shcv context";

                                leaf oper-state {
                                    type types-submgt:shcv-oper-state;
                                    description "Operational state";
                                }

                                leaf requests-sent {
                                    type uint32;
                                    description "Number of host connectivity check requests sent";
                                }

                                leaf replies-received {
                                    type uint32;
                                    description "Number of host connectivity check replies received";
                                }

                                leaf last-reply-time {
                                    type yang:date-and-time;
                                    description "Time of the last successful host connectivity reply";
                                }

                            } // container shcv

                            container firewall {
                                description "Enter the firewall context";

                                leaf dmz {
                                    type boolean;
                                    description
                                        "The host is part of a DeMilitarized Zone (DMZ) and traffic
                                         for this host bypasses firewall functionality";
                                }

                            } // container firewall

                        } // container na

                        container slaac {
                            description "Enter the slaac context";

                            leaf forwarding-state {
                                type types-sros:oper-state;
                                description "Forwarding state";
                            }

                            leaf origin {
                                type types-submgt:subscriber-host-origin;
                                description "Origin";
                            }

                            leaf radius-accounting-session-id {
                                type types-submgt:accounting-session-id;
                                description "Id of the RADIUS accounting session";
                            }

                            leaf bgp-peering-status {
                                type types-submgt:bgp-peering-state;
                                description "BGP peering status";
                            }

                            container ip-prefix {
                                description "Enter the ip-prefix context";

                                leaf prefix {
                                    type types-sros:ipv6-prefix;
                                    description "IPv6 prefix assigned to the session";
                                }

                                leaf pool {
                                    type types-sros:named-item;
                                    description "Local address pool from which the prefix has been allocated";
                                }

                                leaf origin {
                                    type types-submgt:session-address-origin;
                                    description "Origin of the address";
                                }

                                leaf routing-origin {
                                    type types-submgt:routing-origin;
                                    description "Origin of the address as used by routing policies";
                                }

                            } // container ip-prefix

                            list address {
                                key "address";
                                description "Enter the address list instance";

                                leaf address {
                                    type types-sros:ipv6-address;
                                    description "Address";
                                }

                                container shcv {
                                    description "Enter the shcv context";

                                    leaf oper-state {
                                        type types-submgt:shcv-oper-state;
                                        description "Operational state";
                                    }

                                    leaf requests-sent {
                                        type uint32;
                                        description "Number of host connectivity check requests sent";
                                    }

                                    leaf replies-received {
                                        type uint32;
                                        description "Number of host connectivity check replies received";
                                    }

                                    leaf last-reply-time {
                                        type yang:date-and-time;
                                        description "Time of the last successful host connectivity reply";
                                    }

                                } // container shcv

                            } // list address

                            container firewall {
                                description "Enter the firewall context";

                                leaf dmz {
                                    type boolean;
                                    description
                                        "The host is part of a DeMilitarized Zone (DMZ) and traffic
                                         for this host bypasses firewall functionality";
                                }

                            } // container firewall

                        } // container slaac

                        container pd {
                            description "Enter the pd context";

                            leaf forwarding-state {
                                type types-sros:oper-state;
                                description "Forwarding state";
                            }

                            leaf origin {
                                type types-submgt:subscriber-host-origin;
                                description "Origin";
                            }

                            leaf radius-accounting-session-id {
                                type types-submgt:accounting-session-id;
                                description "Id of the RADIUS accounting session";
                            }

                            leaf bgp-peering-status {
                                type types-submgt:bgp-peering-state;
                                description "BGP peering status";
                            }

                            container managed-route-nexthop {
                                description "Enter the managed-route-nexthop context";

                                leaf address-type {
                                    type types-submgt:host-id;
                                    description "Address-type of the nexthop";
                                }

                                leaf status {
                                    type types-submgt:managed-route-state;
                                    description "Status of the nexthop";
                                }

                            } // container managed-route-nexthop

                            container ip-prefix {
                                description "Enter the ip-prefix context";

                                leaf prefix {
                                    type types-sros:ipv6-prefix;
                                    description "IPv6 prefix assigned to the session";
                                }

                                leaf pool {
                                    type types-sros:named-item;
                                    description "Local address pool from which the prefix has been allocated";
                                }

                                leaf origin {
                                    type types-submgt:session-address-origin;
                                    description "Origin of the address";
                                }

                                leaf routing-origin {
                                    type types-submgt:routing-origin;
                                    description "Origin of the address as used by routing policies";
                                }

                            } // container ip-prefix

                            container shcv {
                                description "Enter the shcv context";

                                leaf oper-state {
                                    type types-submgt:shcv-oper-state;
                                    description "Operational state";
                                }

                                leaf requests-sent {
                                    type uint32;
                                    description "Number of host connectivity check requests sent";
                                }

                                leaf replies-received {
                                    type uint32;
                                    description "Number of host connectivity check replies received";
                                }

                                leaf last-reply-time {
                                    type yang:date-and-time;
                                    description "Time of the last successful host connectivity reply";
                                }

                            } // container shcv

                        } // container pd

                        container dhcp6-lease {
                            description "Enter the dhcp6-lease context";

                            leaf creation-time {
                                type yang:date-and-time;
                                description "Creation time";
                            }

                            leaf server-address {
                                type types-sros:ip-address;
                                description "Server IP address";
                            }

                            leaf client-address {
                                type types-sros:ipv6-address;
                                description "Link-local address of the DHCP client that owns the lease info";
                            }

                            leaf interface-id {
                                type binary {
                                    length "1..255";
                                }
                                description "Interface identifier";
                            }

                            container client-id {
                                description "Enter the client-id context";

                                leaf raw-data {
                                    type binary;
                                }

                                container duid-llt {
                                    description "Enter the duid-llt context";

                                    leaf hardware-type {
                                        type types-dhcp:dhcp6-duid-hardware-type;
                                    }

                                    leaf time {
                                        type yang:date-and-time;
                                    }

                                    leaf link-layer-address {
                                        type binary;
                                    }

                                } // container duid-llt

                                container duid-en {
                                    description "Enter the duid-en context";

                                    leaf enterprise-number {
                                        type uint32;
                                    }

                                    leaf identifier {
                                        type binary;
                                    }

                                } // container duid-en

                                container duid-ll {
                                    description "Enter the duid-ll context";

                                    leaf hardware-type {
                                        type types-dhcp:dhcp6-duid-hardware-type;
                                    }

                                    leaf link-layer-address {
                                        type binary;
                                    }

                                } // container duid-ll

                            } // container client-id

                            container server-id {
                                description "Enter the server-id context";

                                leaf raw-data {
                                    type binary;
                                }

                                container duid-llt {
                                    description "Enter the duid-llt context";

                                    leaf hardware-type {
                                        type types-dhcp:dhcp6-duid-hardware-type;
                                    }

                                    leaf time {
                                        type yang:date-and-time;
                                    }

                                    leaf link-layer-address {
                                        type binary;
                                    }

                                } // container duid-llt

                                container duid-en {
                                    description "Enter the duid-en context";

                                    leaf enterprise-number {
                                        type uint32;
                                    }

                                    leaf identifier {
                                        type binary;
                                    }

                                } // container duid-en

                                container duid-ll {
                                    description "Enter the duid-ll context";

                                    leaf hardware-type {
                                        type types-dhcp:dhcp6-duid-hardware-type;
                                    }

                                    leaf link-layer-address {
                                        type binary;
                                    }

                                } // container duid-ll

                            } // container server-id

                            container remote-id {
                                description "Enter the remote-id context";

                                leaf raw-data {
                                    type binary;
                                }

                                leaf enterprise-number {
                                    type uint32;
                                }

                                leaf identifier {
                                    type binary;
                                }

                            } // container remote-id

                            container na {
                                description "Enter the na context";

                                leaf expiration-time {
                                    type yang:date-and-time;
                                    description "Expiration time";
                                }

                                leaf up-time {
                                    type uint32;
                                    units "seconds";
                                    description "Up-time";
                                }

                                leaf last-renew-time {
                                    type yang:date-and-time;
                                    description "Most recent renew time";
                                }

                                leaf remaining-lease-time {
                                    type union {
                                        type uint32 {
                                            range "0..4294967294";
                                        }
                                        type enumeration {
                                            enum "infinite"                     { value -1; }
                                        }
                                    }
                                    units "seconds";
                                    description "Remaining lease time";
                                }

                                leaf lease-split {
                                    type boolean;
                                    description "The BNG overrides the lifetimes provided by the DHCPv6 server";
                                }

                                leaf subscriber-interface-prefix {
                                    type types-sros:ipv6-prefix;
                                    description "IPv6 aggregate route prefix";
                                }

                                leaf iaid {
                                    type uint32;
                                    description "Identity Association ID (IAID) the ip-address or prefix is assigned to";
                                }

                            } // container na

                            container pd {
                                description "Enter the pd context";

                                leaf expiration-time {
                                    type yang:date-and-time;
                                    description "Expiration time";
                                }

                                leaf up-time {
                                    type uint32;
                                    units "seconds";
                                    description "Up-time";
                                }

                                leaf last-renew-time {
                                    type yang:date-and-time;
                                    description "Most recent renew time";
                                }

                                leaf remaining-lease-time {
                                    type union {
                                        type uint32 {
                                            range "0..4294967294";
                                        }
                                        type enumeration {
                                            enum "infinite"                     { value -1; }
                                        }
                                    }
                                    units "seconds";
                                    description "Remaining lease time";
                                }

                                leaf lease-split {
                                    type boolean;
                                    description "The BNG overrides the lifetimes provided by the DHCPv6 server";
                                }

                                leaf subscriber-interface-prefix {
                                    type types-sros:ipv6-prefix;
                                    description "IPv6 aggregate route prefix";
                                }

                                leaf iaid {
                                    type uint32;
                                    description "Identity Association ID (IAID) the ip-address or prefix is assigned to";
                                }

                            } // container pd

                        } // container dhcp6-lease

                        container bgp-peering-parameters {
                            description "Enter the bgp-peering-parameters context";

                            leaf policy {
                                type types-sros:named-item;
                                description "BGP peering policy";
                            }

                            leaf authentication-key-chain {
                                type types-sros:named-item;
                                description "Authentication key chain";
                            }

                            leaf md5-authentication-key {
                                type binary {
                                    length "1..255";
                                }
                                description "MD5 authentication key";
                            }

                            leaf import-policy {
                                type types-sros:named-item;
                                description "Routing policy controling BGP advertisements received from the peer";
                            }

                            leaf export-policy {
                                type types-sros:named-item;
                                description "Routing policy controling BGP advertisements sent to the peer";
                            }

                            leaf autonomous-system {
                                type uint32;
                                description "Autonomous system number of the remote peer";
                            }

                        } // container bgp-peering-parameters

                    } // container ipv6

                    container ingress {
                        description "Enter the ingress context";

                        container filter {
                            description "Enter the filter context";

                            container overrides {
                                description "Enter the overrides context";

                                container ipv4 {
                                    description "Enter the ipv4 context";

                                    leaf filter {
                                        type types-submgt:overrule-filter-name;
                                        description "Overrides the filter specified in the sla-profile";
                                    }

                                    leaf http-redirect-url {
                                        type types-sros:http-redirect-url;
                                        description "Overrides the HTTP redirect URL specified in the sla-profile";
                                    }

                                    container one-time-http-redirect {
                                        description "Enter the one-time-http-redirect context";

                                        leaf filter {
                                            type types-submgt:overrule-filter-name;
                                            description "Overrides the one-time HTTP redirection filter specified in the sla-profile";
                                        }

                                        leaf source {
                                            type types-submgt:subscriber-host-one-time-http-redirect-filter-source;
                                            description "Source of the one-time HTTP redirect override";
                                        }

                                        leaf status {
                                            type types-submgt:subscriber-host-one-time-http-redirect-state;
                                            description "State of the one-time HTTP redirection";
                                        }

                                    } // container one-time-http-redirect

                                } // container ipv4

                                container ipv6 {
                                    description "Enter the ipv6 context";

                                    leaf filter {
                                        type types-submgt:overrule-filter-name;
                                        description "Overrides the filter specified in the sla-profile";
                                    }

                                    leaf http-redirect-url {
                                        type types-sros:http-redirect-url;
                                        description "Overrides the HTTP redirect URL specified in the sla-profile";
                                    }

                                } // container ipv6

                            } // container overrides

                        } // container filter

                        container qos {
                            description "Enter the qos context";

                            container overrides {
                                description "Enter the overrides context";

                                list arbiter {
                                    key "arbiter-name";
                                    description "Enter the arbiter list instance";

                                    leaf arbiter-name {
                                        type types-sros:named-item;
                                        description "Name of overridden arbiter";
                                    }

                                    leaf pir {
                                        type types-qos:policer-pir-rate-override;
                                        units "kilobps";
                                        description "PIR rate";
                                    }

                                } // list arbiter

                                list policer {
                                    key "policer-id";
                                    description "Enter the policer list instance";

                                    leaf policer-id {
                                        type types-qos:ingress-policer-id;
                                        description "The unique identifier for the policer.";
                                    }

                                    leaf pir {
                                        type types-qos:policer-pir-rate-override;
                                        units "kilobps";
                                        description "PIR rate";
                                    }

                                    leaf cir {
                                        type types-qos:policer-cir-rate-override;
                                        units "kilobps";
                                        description "CIR rate";
                                    }

                                    leaf mbs {
                                        type types-qos:policer-burst-size-override;
                                        units "bytes";
                                        description "The maximum reserved buffer space";
                                    }

                                    leaf cbs {
                                        type types-qos:policer-burst-size-override;
                                        units "bytes";
                                        description "The committed buffer size";
                                    }

                                } // list policer

                                list queue {
                                    key "queue-id";
                                    description "Enter the queue list instance";

                                    leaf queue-id {
                                        type types-qos:ingress-queue-id;
                                        description "The unique identifier for the queue.";
                                    }

                                    leaf pir {
                                        type types-qos:queue-pir-rate-override;
                                        units "kilobps";
                                        description "PIR rate";
                                    }

                                    leaf cir {
                                        type types-qos:queue-cir-rate-override;
                                        units "kilobps";
                                        description "CIR rate";
                                    }

                                    leaf mbs {
                                        type types-qos:queue-burst-size-override;
                                        units "bytes";
                                        description "The maximum reserved buffer space";
                                    }

                                    leaf cbs {
                                        type types-qos:queue-burst-size-override;
                                        units "bytes";
                                        description "The committed buffer size";
                                    }

                                    leaf wrr-weight {
                                        type types-qos:hs-wrr-weight-override;
                                        description
                                            "The Weighted Round Robin (WRR) weight with which
                                             this queue should parent into the scheduler.";
                                    }

                                    leaf class-weight {
                                        type types-qos:hs-class-weight-override;
                                        description "The scheduling class weight.";
                                    }

                                } // list queue

                                list scheduler {
                                    key "scheduler-name";
                                    description "Enter the scheduler list instance";

                                    leaf scheduler-name {
                                        type types-sros:named-item;
                                        description "Name of overridden scheduler";
                                    }

                                    leaf pir {
                                        type types-qos:scheduler-cir-rate;
                                        units "kilobps";
                                        description "PIR rate";
                                    }

                                    leaf cir {
                                        type types-qos:scheduler-cir-rate-override;
                                        units "kilobps";
                                        description "CIR rate";
                                    }

                                } // list scheduler

                            } // container overrides

                        } // container qos

                    } // container ingress

                    container egress {
                        description "Enter the egress context";

                        container filter {
                            description "Enter the filter context";

                            container overrides {
                                description "Enter the overrides context";

                                container ipv4 {
                                    description "Enter the ipv4 context";

                                    leaf filter {
                                        type types-submgt:overrule-filter-name;
                                        description "Overrides the filter specified in the sla-profile";
                                    }

                                } // container ipv4

                                container ipv6 {
                                    description "Enter the ipv6 context";

                                    leaf filter {
                                        type types-submgt:overrule-filter-name;
                                        description "Overrides the filter specified in the sla-profile";
                                    }

                                } // container ipv6

                            } // container overrides

                        } // container filter

                        container qos {
                            description "Enter the qos context";

                            container overrides {
                                description "Enter the overrides context";

                                leaf sub-aggregate-rate {
                                    type types-qos:rate-limit;
                                    units "kilobps";
                                    description "The maximum total rate of all egress queues of the subscriber.";
                                }

                                leaf sla-aggregate-rate {
                                    type types-qos:rate-limit;
                                    units "kilobps";
                                    description "The maximum rate of all egress queues of the SLA profile instance.";
                                }

                                list arbiter {
                                    key "arbiter-name";
                                    description "Enter the arbiter list instance";

                                    leaf arbiter-name {
                                        type types-sros:named-item;
                                        description "Name of overridden arbiter";
                                    }

                                    leaf pir {
                                        type types-qos:policer-pir-rate-override;
                                        units "kilobps";
                                        description "PIR rate";
                                    }

                                } // list arbiter

                                list policer {
                                    key "policer-id";
                                    description "Enter the policer list instance";

                                    leaf policer-id {
                                        type types-qos:sap-egress-policer-id;
                                        description "The unique identifier for the policer.";
                                    }

                                    leaf pir {
                                        type types-qos:policer-pir-rate-override;
                                        units "kilobps";
                                        description "PIR rate";
                                    }

                                    leaf cir {
                                        type types-qos:policer-cir-rate-override;
                                        units "kilobps";
                                        description "CIR rate";
                                    }

                                    leaf mbs {
                                        type types-qos:policer-burst-size-override;
                                        units "bytes";
                                        description "The maximum reserved buffer space";
                                    }

                                    leaf cbs {
                                        type types-qos:policer-burst-size-override;
                                        units "bytes";
                                        description "The committed buffer size";
                                    }

                                } // list policer

                                list queue {
                                    key "queue-id";
                                    description "Enter the queue list instance";

                                    leaf queue-id {
                                        type types-qos:egress-queue-id;
                                        description "The unique identifier for the queue.";
                                    }

                                    leaf pir {
                                        type types-qos:queue-pir-rate-override;
                                        units "kilobps";
                                        description "PIR rate";
                                    }

                                    leaf cir {
                                        type types-qos:queue-cir-rate-override;
                                        units "kilobps";
                                        description "CIR rate";
                                    }

                                    leaf mbs {
                                        type types-qos:queue-burst-size-override;
                                        units "bytes";
                                        description "The maximum reserved buffer space";
                                    }

                                    leaf cbs {
                                        type types-qos:queue-burst-size-override;
                                        units "bytes";
                                        description "The committed buffer size";
                                    }

                                    leaf wrr-weight {
                                        type types-qos:hs-wrr-weight-override;
                                        description
                                            "The Weighted Round Robin (WRR) weight with which
                                             this queue should parent into the scheduler.";
                                    }

                                    leaf class-weight {
                                        type types-qos:hs-class-weight-override;
                                        description "The scheduling class weight.";
                                    }

                                } // list queue

                                list scheduler {
                                    key "scheduler-name";
                                    description "Enter the scheduler list instance";

                                    leaf scheduler-name {
                                        type types-sros:named-item;
                                        description "Name of overridden scheduler";
                                    }

                                    leaf pir {
                                        type types-qos:scheduler-cir-rate;
                                        units "kilobps";
                                        description "PIR rate";
                                    }

                                    leaf cir {
                                        type types-qos:scheduler-cir-rate-override;
                                        units "kilobps";
                                        description "CIR rate";
                                    }

                                } // list scheduler

                                list wrr-group {
                                    key "group-id";
                                    description "Enter the wrr-group list instance";

                                    leaf group-id {
                                        type types-qos:hs-wrr-group-id;
                                        description "HS WRR group identifier";
                                    }

                                    leaf pir {
                                        type types-qos:hs-wrr-rate-override;
                                        units "kilobps";
                                        description "The rate (PIR) override for WRR group.";
                                    }

                                    leaf class-weight {
                                        type types-qos:hs-class-weight-override;
                                        description "The class weight override for WRR group.";
                                    }

                                } // list wrr-group

                            } // container overrides

                        } // container qos

                    } // container egress

                    list pcc-rule {
                        key "name";
                        description "Enter the pcc-rule list instance";

                        leaf name {
                            type types-pcc-rule:pcc-rule-name;
                            description "PCC rule name.";
                        }

                        leaf index {
                            type uint32;
                            description
                                "The PCC rule index for the given subscriber host.
                                 The rules are applied in order of this index.";
                        }

                        leaf id {
                            type uint32;
                            description "System wide unique identifier assigned to the rule.";
                        }

                        leaf direction {
                            type types-sros:direction;
                            description "Direction on which the rule acts.";
                        }

                        leaf precedence {
                            type uint32;
                            description "The rules are applied in the order of increasing precedence.";
                        }

                        container action {
                            description "Enter the action context";

                            leaf drop {
                                type boolean;
                                description "Packets will be dropped";
                            }

                            container forward {
                                description "Enter the forward context";

                                leaf filter-accept {
                                    type boolean;
                                    description
                                        "An explicit accept rule is created in the ACL filter
                                         for packets matching this PCC rule";
                                }

                                leaf accounting {
                                    type boolean;
                                    description "The packets matching this PCC rule are accounted separately";
                                }

                                leaf monitoring-key {
                                    type string {
                                        length "1..80";
                                    }
                                    description "Usage monitoring is done for the packets matching this pcc rule using this key";
                                }

                                leaf fc {
                                    type types-sros:fc-name;
                                    description "Explicitly map packets matching this PCC rule to this forwarding class";
                                }

                                leaf qos-accept {
                                    type boolean;
                                    description "An explicit accept rule is created in QoS IP criteria for packets matching this PCC rule";
                                }

                                container redirect {
                                    description "Enter the redirect context";

                                    container ipv4 {
                                        description "Enter the ipv4 context";

                                        leaf router-instance {
                                            type types-services:service-name;
                                            description "VPRN Service where IPv4 packets matching the PCC rule will be forwarded";
                                        }

                                        leaf address {
                                            type types-sros:ipv4-address;
                                            description "IPv4 address used in the routing lookup for forwarding flows that match the PCC rule";
                                        }

                                    } // container ipv4

                                    container ipv6 {
                                        description "Enter the ipv6 context";

                                        leaf router-instance {
                                            type types-services:service-name;
                                            description "VPRN Service where IPv6 packets matching the PCC rule will be forwarded";
                                        }

                                        leaf address {
                                            type types-sros:ipv6-address;
                                            description "IPv6 address used in the routing lookup for forwarding flows that match the PCC rule";
                                        }

                                    } // container ipv6

                                } // container redirect

                                container rate-limit {
                                    description "Enter the rate-limit context";

                                    leaf pir {
                                        type types-qos:policer-pir-rate;
                                        description "PIR";
                                    }

                                    leaf cir {
                                        type types-qos:policer-cir-rate;
                                        description "CIR";
                                    }

                                } // container rate-limit

                                container dynamic-policer-override {
                                    description "Enter the dynamic-policer-override context";

                                    leaf cbs {
                                        type types-qos:policer-burst-size-override;
                                        description "Policer CBS for the PCC-rule";
                                    }

                                    leaf mbs {
                                        type types-qos:policer-burst-size-override;
                                        description "Policer MBS for the PCC-rule";
                                    }

                                    leaf packet-byte-offset {
                                        type int32;
                                        description "Policer packet-byte-offset for the PCC-rule";
                                    }

                                    container arbiter-parent {
                                        description "Enter the arbiter-parent context";

                                        leaf arbiter-name {
                                            type types-sros:named-item;
                                            description "Parent arbiter name for the PCC-rule";
                                        }

                                        leaf level {
                                            type types-qos:hierarchy-level;
                                            description "Parent level for the PCC-rule";
                                        }

                                        leaf weight {
                                            type types-qos:weight;
                                            description "Parent weight for the PCC-rule";
                                        }

                                    } // container arbiter-parent

                                    container ingress {
                                        description "Enter the ingress context";

                                        leaf stat-mode {
                                            type types-qos:ingress-policer-stat-mode;
                                            description "Policer stat-mode for the PCC-rule";
                                        }

                                    } // container ingress

                                    container egress {
                                        description "Enter the egress context";

                                        leaf stat-mode {
                                            type types-qos:egress-policer-stat-mode;
                                            description "Policer stat-mode for the PCC-rule";
                                        }

                                    } // container egress

                                } // container dynamic-policer-override

                            } // container forward

                            container http-redirect {
                                description "Enter the http-redirect context";

                                leaf url {
                                    type types-sros:http-redirect-url;
                                    description "URL of the targeted redirect server, will be sent in the redirect message";
                                }

                            } // container http-redirect

                        } // container action

                        list flow {
                            key "id";
                            description "Enter the flow list instance";

                            leaf id {
                                type uint32 {
                                    range "1..128";
                                }
                                description "The ordered precedence number of the flow.";
                            }

                            leaf direction {
                                type types-sros:direction;
                                description "Direction";
                            }

                            leaf protocol-next-header {
                                type types-submgt:match-protocol-next-header;
                                description "IPv4 protocol or IPv6 next-header";
                            }

                            leaf dscp {
                                type types-qos:dscp-name;
                                description "DSCP";
                            }

                            container src-ip {
                                description "Enter the src-ip context";

                                leaf address {
                                    type types-sros:ip-prefix-with-host-bits;
                                    description "Source IP address and mask";
                                }

                            } // container src-ip

                            container src-port {
                                description "Enter the src-port context";

                                container range {
                                    description "Enter the range context";

                                    leaf start {
                                        type types-sros:tcp-udp-port;
                                        description "Lower bound of source port range";
                                    }

                                    leaf end {
                                        type types-sros:tcp-udp-port;
                                        description "Upper bound of source port range";
                                    }

                                } // container range

                            } // container src-port

                            container dst-ip {
                                description "Enter the dst-ip context";

                                leaf address {
                                    type types-sros:ip-prefix-with-host-bits;
                                    description "Destination IP address and mask";
                                }

                            } // container dst-ip

                            container dst-port {
                                description "Enter the dst-port context";

                                container range {
                                    description "Enter the range context";

                                    leaf start {
                                        type types-sros:tcp-udp-port;
                                        description "Lower bound of destination port range";
                                    }

                                    leaf end {
                                        type types-sros:tcp-udp-port;
                                        description "Upper bound of destination port range";
                                    }

                                } // container range

                            } // container dst-port

                        } // list flow

                    } // list pcc-rule

                    list subscriber-service {
                        key "name";
                        description "Enter the subscriber-service list instance";

                        leaf name {
                            type types-sros:display-string;
                            description "Subscriber service name.";
                        }

                        leaf id {
                            type uint32;
                            description "Subscriber service identifier.";
                        }

                        leaf type {
                            type types-sros:display-string;
                            description "Type of the subscriber service.";
                        }

                        leaf up-time {
                            type types-sros:time-interval;
                            description "Time duration that this subscriber service is active.";
                        }

                        container accounting {
                            description "Enter the accounting context";

                            leaf type {
                                type enumeration {
                                    enum "volume-time"                  { value 2; }
                                    enum "time"                         { value 3; }
                                }
                                description "Accounting type of the subscriber service.";
                            }

                            leaf update-interval {
                                type types-sros:time-interval;
                                description "Interval at which accounting interim updates are sent.";
                            }

                            leaf radius-accounting-session-id {
                                type types-sros:display-string;
                                description "Accounting session-id.";
                            }

                            container statistics {
                                description "Enter the statistics context";

                                container ingress {
                                    description "Enter the ingress context";

                                    leaf packets {
                                        type yang:counter64;
                                        description "The number of packets.";
                                    }

                                    leaf octets {
                                        type yang:counter64;
                                        description "The number of octets.";
                                    }

                                } // container ingress

                                container egress {
                                    description "Enter the egress context";

                                    leaf packets {
                                        type yang:counter64;
                                        description "The number of packets.";
                                    }

                                    leaf octets {
                                        type yang:counter64;
                                        description "The number of octets.";
                                    }

                                } // container egress

                            } // container statistics

                        } // container accounting

                        list pcc-rule {
                            key "pcc-rule-name";
                            description "Enter the pcc-rule list instance";

                            leaf pcc-rule-name {
                                type types-pcc-rule:pcc-rule-name;
                                description "PCC rule name.";
                            }

                            leaf index {
                                type uint32;
                                description
                                    "The PCC rule index for the given subscriber service.
                                     The rules are applied in order of this index.";
                            }

                            leaf id {
                                type uint32;
                                description "System wide unique identifier assigned to the rule.";
                            }

                        } // list pcc-rule

                        container overrides {
                            description "Enter the overrides context";

                            container ingress {
                                description "Enter the ingress context";

                                list arbiter {
                                    key "arbiter-name";
                                    description "Enter the arbiter list instance";

                                    leaf arbiter-name {
                                        type types-sros:named-item;
                                        description "Name of overridden arbiter";
                                    }

                                    leaf pir {
                                        type types-qos:policer-pir-rate-override;
                                        units "kilobps";
                                        description "PIR rate";
                                    }

                                } // list arbiter

                                list policer {
                                    key "policer-id";
                                    description "Enter the policer list instance";

                                    leaf policer-id {
                                        type types-qos:ingress-policer-id;
                                        description "The unique identifier for the policer.";
                                    }

                                    leaf pir {
                                        type types-qos:policer-pir-rate-override;
                                        units "kilobps";
                                        description "PIR rate";
                                    }

                                    leaf cir {
                                        type types-qos:policer-cir-rate-override;
                                        units "kilobps";
                                        description "CIR rate";
                                    }

                                    leaf mbs {
                                        type types-qos:policer-burst-size-override;
                                        units "bytes";
                                        description "The maximum reserved buffer space";
                                    }

                                    leaf cbs {
                                        type types-qos:policer-burst-size-override;
                                        units "bytes";
                                        description "The committed buffer size";
                                    }

                                } // list policer

                                list queue {
                                    key "queue-id";
                                    description "Enter the queue list instance";

                                    leaf queue-id {
                                        type types-qos:ingress-queue-id;
                                        description "The unique identifier for the queue.";
                                    }

                                    leaf pir {
                                        type types-qos:queue-pir-rate-override;
                                        units "kilobps";
                                        description "PIR rate";
                                    }

                                    leaf cir {
                                        type types-qos:queue-cir-rate-override;
                                        units "kilobps";
                                        description "CIR rate";
                                    }

                                    leaf mbs {
                                        type types-qos:queue-burst-size-override;
                                        units "bytes";
                                        description "The maximum reserved buffer space";
                                    }

                                    leaf cbs {
                                        type types-qos:queue-burst-size-override;
                                        units "bytes";
                                        description "The committed buffer size";
                                    }

                                    leaf wrr-weight {
                                        type types-qos:hs-wrr-weight-override;
                                        description
                                            "The Weighted Round Robin (WRR) weight with which
                                             this queue should parent into the scheduler.";
                                    }

                                    leaf class-weight {
                                        type types-qos:hs-class-weight-override;
                                        description "The scheduling class weight.";
                                    }

                                } // list queue

                                list scheduler {
                                    key "scheduler-name";
                                    description "Enter the scheduler list instance";

                                    leaf scheduler-name {
                                        type types-sros:named-item;
                                        description "Name of overridden scheduler";
                                    }

                                    leaf pir {
                                        type types-qos:scheduler-cir-rate;
                                        units "kilobps";
                                        description "PIR rate";
                                    }

                                    leaf cir {
                                        type types-qos:scheduler-cir-rate-override;
                                        units "kilobps";
                                        description "CIR rate";
                                    }

                                } // list scheduler

                            } // container ingress

                            container egress {
                                description "Enter the egress context";

                                leaf sub-aggregate-rate {
                                    type types-qos:rate-limit;
                                    units "kilobps";
                                    description "The maximum total rate of all egress queues of the subscriber.";
                                }

                                leaf sla-aggregate-rate {
                                    type types-qos:rate-limit;
                                    units "kilobps";
                                    description "The maximum rate of all egress queues of the SLA profile instance.";
                                }

                                list arbiter {
                                    key "arbiter-name";
                                    description "Enter the arbiter list instance";

                                    leaf arbiter-name {
                                        type types-sros:named-item;
                                        description "Name of overridden arbiter";
                                    }

                                    leaf pir {
                                        type types-qos:policer-pir-rate-override;
                                        units "kilobps";
                                        description "PIR rate";
                                    }

                                } // list arbiter

                                list policer {
                                    key "policer-id";
                                    description "Enter the policer list instance";

                                    leaf policer-id {
                                        type types-qos:sap-egress-policer-id;
                                        description "The unique identifier for the policer.";
                                    }

                                    leaf pir {
                                        type types-qos:policer-pir-rate-override;
                                        units "kilobps";
                                        description "PIR rate";
                                    }

                                    leaf cir {
                                        type types-qos:policer-cir-rate-override;
                                        units "kilobps";
                                        description "CIR rate";
                                    }

                                    leaf mbs {
                                        type types-qos:policer-burst-size-override;
                                        units "bytes";
                                        description "The maximum reserved buffer space";
                                    }

                                    leaf cbs {
                                        type types-qos:policer-burst-size-override;
                                        units "bytes";
                                        description "The committed buffer size";
                                    }

                                } // list policer

                                list queue {
                                    key "queue-id";
                                    description "Enter the queue list instance";

                                    leaf queue-id {
                                        type types-qos:egress-queue-id;
                                        description "The unique identifier for the queue.";
                                    }

                                    leaf pir {
                                        type types-qos:queue-pir-rate-override;
                                        units "kilobps";
                                        description "PIR rate";
                                    }

                                    leaf cir {
                                        type types-qos:queue-cir-rate-override;
                                        units "kilobps";
                                        description "CIR rate";
                                    }

                                    leaf mbs {
                                        type types-qos:queue-burst-size-override;
                                        units "bytes";
                                        description "The maximum reserved buffer space";
                                    }

                                    leaf cbs {
                                        type types-qos:queue-burst-size-override;
                                        units "bytes";
                                        description "The committed buffer size";
                                    }

                                    leaf wrr-weight {
                                        type types-qos:hs-wrr-weight-override;
                                        description
                                            "The Weighted Round Robin (WRR) weight with which
                                             this queue should parent into the scheduler.";
                                    }

                                    leaf class-weight {
                                        type types-qos:hs-class-weight-override;
                                        description "The scheduling class weight.";
                                    }

                                } // list queue

                                list scheduler {
                                    key "scheduler-name";
                                    description "Enter the scheduler list instance";

                                    leaf scheduler-name {
                                        type types-sros:named-item;
                                        description "Name of overridden scheduler";
                                    }

                                    leaf pir {
                                        type types-qos:scheduler-cir-rate;
                                        units "kilobps";
                                        description "PIR rate";
                                    }

                                    leaf cir {
                                        type types-qos:scheduler-cir-rate-override;
                                        units "kilobps";
                                        description "CIR rate";
                                    }

                                } // list scheduler

                                list wrr-group {
                                    key "group-id";
                                    description "Enter the wrr-group list instance";

                                    leaf group-id {
                                        type types-qos:hs-wrr-group-id;
                                        description "HS WRR group identifier";
                                    }

                                    leaf pir {
                                        type types-qos:hs-wrr-rate-override;
                                        units "kilobps";
                                        description "The rate (PIR) override for WRR group.";
                                    }

                                    leaf class-weight {
                                        type types-qos:hs-class-weight-override;
                                        description "The class weight override for WRR group.";
                                    }

                                } // list wrr-group

                            } // container egress

                        } // container overrides

                    } // list subscriber-service

                } // list session

                list category {
                    key "name";
                    description "Enter the category list instance";

                    leaf name {
                        type types-sros:named-item;
                        description "Credit category name";
                    }

                    leaf alias {
                        type types-sros:named-item-255;
                        description "The full name of the credit category";
                    }

                    container credit-control {
                        description "Enter the credit-control context";

                        leaf policy {
                            type types-sros:named-item;
                            description "Credit control policy name";
                        }

                        leaf out-of-credit-action {
                            type enumeration {
                                enum "none"                         { value 0; }
                                enum "continue"                     { value 1; }
                                enum "disconnect-host"              { value 2; }
                                enum "block-category"               { value 3; }
                                enum "change-service-level"         { value 4; }
                            }
                            description "The action to take when out of credit";
                        }

                        leaf quota-holding-time {
                            type uint32;
                            units "seconds";
                            description "Timer after which credit negotiation will start";
                        }

                        leaf http-redirect-url-override {
                            type string {
                                length "1..255";
                            }
                            description "The override of the HTTP redirect URL for this credit control instance";
                        }

                        leaf expired {
                            type boolean;
                            description "Indicates whether credit has expired or not";
                        }

                        leaf negotiating {
                            type boolean;
                            description "Indicates whether credit is being negotiated or not";
                        }

                    } // container credit-control

                    container statistics {
                        description "Enter the statistics context";

                        container volume {
                            description "Enter the volume context";

                            leaf used {
                                type yang:counter64;
                                description "Used volume based credit";
                            }

                            leaf available {
                                type yang:counter64;
                                description "Available volume based credit";
                            }

                            leaf threshold {
                                type yang:counter64;
                                description "Volume based credit threshold";
                            }

                            leaf available-ingress {
                                type yang:counter64;
                                description "Volume based credit available for ingress packets";
                            }

                            leaf available-egress {
                                type yang:counter64;
                                description "Volume based credit available for egress packets";
                            }

                            leaf used-ingress {
                                type yang:counter64;
                                description "Volume based credit used by ingress packets";
                            }

                            leaf used-egress {
                                type yang:counter64;
                                description "Volume based credit used by egress packets";
                            }

                        } // container volume

                        container time {
                            description "Enter the time context";

                            leaf used {
                                type yang:gauge32;
                                units "seconds";
                                description "Used time based credit";
                            }

                            leaf available {
                                type yang:gauge32;
                                units "seconds";
                                description "Available time based credit";
                            }

                            leaf threshold {
                                type yang:gauge32;
                                units "seconds";
                                description "Time based credit threshold";
                            }

                        } // container time

                        container validity-time {
                            description "Enter the validity-time context";

                            leaf used {
                                type yang:gauge32;
                                units "seconds";
                                description "The used portion of the validity time of the granted service units";
                            }

                            leaf available {
                                type yang:gauge32;
                                units "seconds";
                                description "The time left for the validity time of the granted service units";
                            }

                        } // container validity-time

                        container extended-failure-handling {
                            description "Enter the extended-failure-handling context";

                            leaf volume-currently-unreported {
                                type yang:counter64;
                                description "The used volume based credit not yet reported to the OCS, while the EFH state is active for this diameter session";
                            }

                            leaf time-currently-unreported {
                                type yang:gauge32;
                                description "The used time based credit not yet reported to the OCS, while the EFH state is active for this diameter session";
                            }

                            leaf volume-total-unreported {
                                type yang:counter64;
                                description "The total used volume based credit not yet reported to the OCS, of all the periods that the diameter session was in EFH mode";
                            }

                            leaf time-total-unreported {
                                type yang:gauge32;
                                units "seconds";
                                description "The total used time based credit not yet reported to the OCS, of all the periods that the diameter session was in EFH mode";
                            }

                        } // container extended-failure-handling

                    } // container statistics

                } // list category

            } // list sla-profile-instance

            container virtual-subnet-info {
                description "Enter the virtual-subnet-info context";

                leaf service-name {
                    type types-services:service-name;
                    description "The service associated with the virtual subnet";
                }

                leaf default-router {
                    type types-sros:ip-address;
                    description "The IP address of the default router associated with the subnet.";
                }

                leaf subnet {
                    type types-sros:ip-prefix;
                    description "The subnet associated with this subscriber.";
                }

                leaf sap {
                    type types-sros:sap;
                    description "The SAP associated with this virtual-subnet.";
                }

            } // container virtual-subnet-info

            container l2-aware {
                description "Enter the l2-aware context";

                leaf nat-group {
                    type uint32;
                    description "NAT group ID";
                }

                leaf group-member {
                    type types-nat:bb-group-member;
                    description "Group member ID";
                }

                leaf upnp-policy {
                    type types-sros:named-item;
                    description "uPNP policy";
                }

                leaf host-port-block-size {
                    type uint32;
                    description "Size of the host port blocks";
                }

                list nat-policy {
                    key "name";
                    description "Enter the nat-policy list instance";

                    leaf name {
                        type types-sros:named-item;
                        description "Policy name";
                    }

                    leaf primary {
                        type boolean;
                        description "Primary NAT policy";
                    }

                    container outside {
                        description "Enter the outside context";

                        leaf service-name {
                            type types-services:service-name;
                            description "Outside service";
                        }

                        leaf router-instance {
                            type types-sros:router-instance;
                            description "Outside router instance";
                        }

                        leaf nat-pool {
                            type types-sros:named-item;
                            description "NAT pool";
                        }

                        leaf address {
                            type types-sros:ipv4-unicast-address;
                            description "Outside IP address";
                        }

                        leaf first-port {
                            type types-nat:port-number;
                            description "First outside port";
                        }

                        leaf last-port {
                            type types-nat:port-number;
                            description "Last outside port";
                        }

                        leaf allocation-time {
                            type types-sros:date-time;
                            description "Allocation time";
                        }

                    } // container outside

                    container dnat-override {
                        description "Enter the dnat-override context";

                        leaf address {
                            type types-sros:ipv4-unicast-address;
                            description "DNAT address override";
                        }

                        leaf admin-state {
                            type types-sros:admin-state;
                            description "Administrative state of DNAT override";
                        }

                    } // container dnat-override

                    container statistics {
                        description "Enter the statistics context";

                        container icmp {
                            description "Enter the icmp context";

                            leaf port-usage {
                                type types-sros:percent;
                                description "ICMP port usage";
                            }

                            leaf high-watermark-reached {
                                type boolean;
                                description "High watermark reached for ICMP port usage";
                            }

                        } // container icmp

                        container udp {
                            description "Enter the udp context";

                            leaf port-usage {
                                type types-sros:percent;
                                description "UDP port usage";
                            }

                            leaf high-watermark-reached {
                                type boolean;
                                description "High watermark reached for UDP port usage";
                            }

                        } // container udp

                        container tcp {
                            description "Enter the tcp context";

                            leaf port-usage {
                                type types-sros:percent;
                                description "TCP port usage";
                            }

                            leaf high-watermark-reached {
                                type boolean;
                                description "High watermark reached for TCP port usage";
                            }

                        } // container tcp

                        container session {
                            description "Enter the session context";

                            leaf usage {
                                type types-sros:percent;
                                description "Session usage";
                            }

                            leaf high-watermark-reached {
                                type boolean;
                                description "High watermark reached for session usage";
                            }

                            container active-sessions {
                                description "Enter the active-sessions context";

                                leaf current {
                                    type uint32;
                                    description "Number of current active sessions";
                                }

                                leaf priority {
                                    type uint32;
                                    description "Number of current active prioritized sessions";
                                }

                                leaf peak {
                                    type uint32;
                                    description "Maximum number of sessions active at the same time";
                                }

                            } // container active-sessions

                        } // container session

                    } // container statistics

                } // list nat-policy

                list firewall-policy {
                    key "name";
                    description "Enter the firewall-policy list instance";

                    leaf name {
                        type types-sros:named-item;
                        description "Policy name";
                    }

                    leaf router-instance {
                        type types-sros:router-instance;
                        description "Domain router";
                    }

                    leaf service-name {
                        type types-services:service-name;
                        description "Firewall service";
                    }

                    container statistics {
                        description "Enter the statistics context";

                        leaf downstream-drop {
                            type uint64;
                            description "Number of dropped downstream packets";
                        }

                        leaf unknown-host-drop {
                            type uint64;
                            description "Number of dropped packets because no matching host was found";
                        }

                        container session {
                            description "Enter the session context";

                            container active-sessions {
                                description "Enter the active-sessions context";

                                leaf current {
                                    type uint32;
                                    description "Number of current active sessions";
                                }

                                leaf priority {
                                    type uint32;
                                    description "Number of current active prioritized sessions";
                                }

                                leaf peak {
                                    type uint32;
                                    description "Maximum number of sessions active at the same time";
                                }

                            } // container active-sessions

                        } // container session

                    } // container statistics

                } // list firewall-policy

                list firewall-neighbor {
                    key "address";
                    description "Enter the firewall-neighbor list instance";

                    leaf address {
                        type types-sros:ipv6-unicast-address;
                        description "IP address";
                    }

                    leaf mac-address {
                        type types-sros:mac-unicast-address;
                        description "MAC address";
                    }

                } // list firewall-neighbor

            } // container l2-aware

        } // list subscriber

    } // grouping state-submgt-subscriber

}
