submodule nokia-conf-port-otu {

    yang-version "1.1";

    belongs-to nokia-conf { prefix "conf"; }

    import nokia-sros-yang-extensions     { prefix "sros-ext"; }
    import nokia-types-port               { prefix "types-port"; }

    include nokia-conf-groups;


    sros-ext:sros-major-release "rel21";

    organization "Nokia";

    contact
        "Nokia SR OS Support
         Web: <http://www.nokia.com>";

    description
        "Nokia YANG Data model to configure optical transport unit ports on SR OS based routers.

         Copyright 2016 Nokia. All rights reserved. Reproduction of this document
         is authorized on the condition that the foregoing copyright notice is included.

         This nokia-conf-port-otu YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-02-02";

    grouping conf-port-otu {
        container otu {
            presence "Enable the otu context";
            description "Enable the otu context";

            leaf async-mapping {
                type boolean;
                description "Allow asynchoronous mapping of the payload inside the OTU";
            }

            leaf fec {
                type types-port:otu-fec-mode;
                description "Forwarding Error Correction (FEC) encapsulation on the port";
            }

            leaf otu2-lan-data-rate {
                type types-port:otu2-lan-data-rate;
                units "gigabps";
                description "Data rate for 10GE LAN OTU2 on the port";
            }

            leaf sd-threshold {
                type uint32 {
                    range "5..9";
                }
                default "7";
                description "Error rate at which to declare the signal fail condition for the signal degrade (SD)";
            }

            leaf sf-threshold {
                type uint32 {
                    range "3..6";
                }
                default "5";
                description "Error rate at which to declare the signal fail condition for the signal fail (SF)";
            }

            leaf sf-sd-method {
                type types-port:otu-sf-sd-method;
                default "fec";
                description "Method used to determine the signal fail and signal degrade alarms";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container report-alarm {
                description "Enter the report-alarm context";

                leaf loc {
                    type boolean;
                    default "true";
                    description "Report alarm for a loss of clock that causes the port to shut down";
                }

                leaf los {
                    type boolean;
                    default "true";
                    description "Report alarm for the loss of signal transitions on data";
                }

                leaf lof {
                    type boolean;
                    default "true";
                    description "Report alarm for the loss of OTU framing";
                }

                leaf lom {
                    type boolean;
                    default "true";
                    description "Report alarm for the loss of multi-frame";
                }

                leaf otu-ais {
                    type boolean;
                    default "false";
                    description "Report OTU Alarm Indication Signal alarm";
                }

                leaf otu-ber-sf {
                    type boolean;
                    default "true";
                    description "Report SM Signal Fail alarm";
                }

                leaf otu-ber-sd {
                    type boolean;
                    default "false";
                    description "Report SM Signal Degrade alarm";
                }

                leaf otu-bdi {
                    type boolean;
                    default "true";
                    description "Report SM Backward Defect Indication alarm";
                }

                leaf otu-tim {
                    type boolean;
                    default "false";
                    description "Report SM Trace ID Mismatch alarm";
                }

                leaf otu-iae {
                    type boolean;
                    default "false";
                    description "Report SM Incoming Alignment Error alarm";
                }

                leaf otu-biae {
                    type boolean;
                    default "false";
                    description "Report SM Backward Incoming Alignment Error alarm";
                }

                leaf fec-sf {
                    type boolean;
                    default "true";
                    description "Report Signal Fail alarm";
                }

                leaf fec-sd {
                    type boolean;
                    default "false";
                    description "Report Signal Degrade alarm";
                }

                leaf fec-fail {
                    type boolean;
                    default "false";
                    description "Report FEC mode mismatch alarm";
                }

                leaf fec-uncorr {
                    type boolean;
                    default "false";
                    description "Report one or more Uncorrectable FEC errors alarm";
                }

                leaf odu-ais {
                    type boolean;
                    default "false";
                    description "Report ODU Alarm Indication Signal alarm";
                }

                leaf odu-oci {
                    type boolean;
                    default "false";
                    description "Report ODU Open Connection Indication alarm";
                }

                leaf odu-lck {
                    type boolean;
                    default "false";
                    description "Report ODU Locked alarm";
                }

                leaf odu-bdi {
                    type boolean;
                    default "false";
                    description "Report PM Backward Defect Indication alarm";
                }

                leaf odu-tim {
                    type boolean;
                    default "false";
                    description "Report PM Trace ID Mismatch alarm";
                }

                leaf opu-plm {
                    type boolean;
                    default "false";
                    description "Report PSI Payload Type Mismatch alarm";
                }

            } // container report-alarm

            container fine-granularity-ber {
                description "Enter the fine-granularity-ber context";

                container signal-degrade {
                    description "Enter the signal-degrade context";

                    container raise {
                        description "Enter the raise context";

                        leaf threshold {
                            type uint32 {
                                range "3..9";
                            }
                            default "7";
                            description "SD raise threshold";
                        }

                        leaf multiplier {
                            type uint32 {
                                range "10..99";
                            }
                            default "10";
                            description "Multiplier of the SD raise threshold";
                        }

                    } // container raise

                    container clear {
                        description "Enter the clear context";

                        leaf threshold {
                            type uint32 {
                                range "3..10";
                            }
                            default "8";
                            description "SD clear threshold";
                        }

                        leaf multiplier {
                            type uint32 {
                                range "10..99";
                            }
                            default "10";
                            description "Multiplier of the SD clear threshold";
                        }

                    } // container clear

                } // container signal-degrade

                container signal-failure {
                    description "Enter the signal-failure context";

                    container raise {
                        description "Enter the raise context";

                        leaf threshold {
                            type uint32 {
                                range "3..8";
                            }
                            default "5";
                            description "SF raise threshold";
                        }

                        leaf multiplier {
                            type uint32 {
                                range "10..99";
                            }
                            default "10";
                            description "SF raise threshold";
                        }

                    } // container raise

                    container clear {
                        description "Enter the clear context";

                        leaf threshold {
                            type uint32 {
                                range "3..9";
                            }
                            default "6";
                            description "Threshold for the Multiplier of SD clear";
                        }

                        leaf multiplier {
                            type uint32 {
                                range "10..99";
                            }
                            default "10";
                            description "Threshold for the Multiplier of SD clear";
                        }

                    } // container clear

                } // container signal-failure

            } // container fine-granularity-ber

            container path-monitoring {
                description "Enter the path-monitoring context";

                container trail-trace-identifier {
                    description "Enter the trail-trace-identifier context";

                    leaf mismatch-reaction {
                        type types-port:otu-tim-reaction;
                        description "Configure the reaction to a mismatched TTI.";
                    }

                    container expected {
                        description "Enter the expected context";

                        choice expected {
                            default "auto-generated";
                            case auto-generated {

                                leaf auto-generated {
                                    type empty;
                                    description "Use the system generated TTI";
                                }

                            }
                            case string {

                                leaf string {
                                    type string {
                                        length "0..64";
                                    }
                                    description "Configure the TTI as a sequence of printable ASCII.";
                                }

                            }
                            case bytes {

                                leaf bytes {
                                    type string {
                                        length "0..192";
                                    }
                                    description "Configure the TTI as a sequence of bytes.";
                                }

                            }
                        }
                    } // container expected

                    container transmit {
                        description "Enter the transmit context";

                        choice transmit {
                            default "auto-generated";
                            case auto-generated {

                                leaf auto-generated {
                                    type empty;
                                    description "Use the system generated TTI";
                                }

                            }
                            case string {

                                leaf string {
                                    type string {
                                        length "0..64";
                                    }
                                    description "Configure the TTI as a sequence of printable ASCII.";
                                }

                            }
                            case bytes {

                                leaf bytes {
                                    type string {
                                        length "0..192";
                                    }
                                    description "Configure the TTI as a sequence of bytes.";
                                }

                            }
                        }
                    } // container transmit

                } // container trail-trace-identifier

            } // container path-monitoring

            container payload-structure-identifier {
                description "Enter the payload-structure-identifier context";

                container payload {
                    description "Enter the payload context";

                    leaf expected {
                        type types-port:otu-psi-payload-type;
                        default "auto";
                        description "Configure the port's PSI payload expected parameters.";
                    }

                    leaf mismatch-reaction {
                        type types-port:otu-tim-reaction;
                        description "Configure the reaction to a mismatched payload.";
                    }

                    leaf transmit {
                        type types-port:otu-psi-payload-type;
                        default "auto";
                        description "Configure the port's PSI payload transmit parameters.";
                    }

                } // container payload

            } // container payload-structure-identifier

            container section-monitoring {
                description "Enter the section-monitoring context";

                container trail-trace-identifier {
                    description "Enter the trail-trace-identifier context";

                    leaf mismatch-reaction {
                        type types-port:otu-tim-reaction;
                        description "Configure the reaction to a mismatched TTI.";
                    }

                    container expected {
                        description "Enter the expected context";

                        choice expected {
                            default "auto-generated";
                            case auto-generated {

                                leaf auto-generated {
                                    type empty;
                                    description "Use the system generated TTI";
                                }

                            }
                            case string {

                                leaf string {
                                    type string {
                                        length "0..64";
                                    }
                                    description "Configure the TTI as a sequence of printable ASCII.";
                                }

                            }
                            case bytes {

                                leaf bytes {
                                    type string {
                                        length "0..192";
                                    }
                                    description "Configure the TTI as a sequence of bytes.";
                                }

                            }
                        }
                    } // container expected

                    container transmit {
                        description "Enter the transmit context";

                        choice transmit {
                            default "auto-generated";
                            case auto-generated {

                                leaf auto-generated {
                                    type empty;
                                    description "Use the system generated TTI";
                                }

                            }
                            case string {

                                leaf string {
                                    type string {
                                        length "0..64";
                                    }
                                    description "Configure the TTI as a sequence of printable ASCII.";
                                }

                            }
                            case bytes {

                                leaf bytes {
                                    type string {
                                        length "0..192";
                                    }
                                    description "Configure the TTI as a sequence of bytes.";
                                }

                            }
                        }
                    } // container transmit

                } // container trail-trace-identifier

            } // container section-monitoring

        } // container otu

    } // grouping conf-port-otu

}
