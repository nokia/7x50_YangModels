submodule nokia-conf-submgt-up-resiliency {

    yang-version "1.1";

    belongs-to nokia-conf { prefix "conf"; }

    import nokia-sros-yang-extensions     { prefix "sros-ext"; }
    import nokia-types-services           { prefix "types-services"; }
    import nokia-types-sros               { prefix "types-sros"; }

    include nokia-conf-groups;

    sros-ext:sros-major-release "rel25";
    organization "Nokia";
    contact
        "Nokia SR OS Support
         Web: <http://www.nokia.com>";
    description
        "Nokia YANG Data model to configure subscriber management CUPS UP resiliency on SR OS based routers.

         Copyright 2016 Nokia. All rights reserved. Reproduction of this document
         is authorized on the condition that the foregoing copyright notice is included.

         This nokia-conf-submgt-up-resiliency YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-07-16";

    grouping conf-submgt-up-resiliency {
        container up-resiliency {
            description "Enter the up-resiliency context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list fate-sharing-group-template {
                key "name";
                max-elements 256;
                description "Enter the fate-sharing-group-template list instance";

                leaf name {
                    type types-sros:named-item {
                        pattern "[^_].*" {
                            error-message "Identifiers starting with '_' are reserved for internal use";
                        }
                    }
                    description "FSG template ID";
                }

                leaf description {
                    type types-sros:description;
                    description "Text description";
                }

                leaf gratuitous-arp {
                    type enumeration {
                        enum one-per-outer-tag {
                            value 1;
                            description "Send a single Gratuitous ARP for all q-in-q SAPs sharing the same outer tag on any one of those SAP";
                        }
                        enum one-per-sap {
                            value 2;
                            description "Send a single Gratuitous ARP per SAP";
                        }
                    }
                    default "one-per-sap";
                    description "Granularity for sending GARP packets on switchover";
                }

                leaf uplink-forwarding-while-standby {
                    type boolean;
                    default "false";
                    description "Allows a standby BNG-UP to forward packets";
                }

                leaf path-restoration-state {
                    type enumeration {
                        enum standby {
                            value 1;
                            description "Always change FSG state to standby";
                        }
                        enum auto {
                            value 2;
                            description "Change FSG state based on a series of heuristic tests";
                        }
                    }
                    default "auto";
                    description "Method for managing FSGs during headless mode";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container redundant-interface {
                    description "Enter the redundant-interface context";

                    leaf service {
                        type types-services:service-name;
                        description "Service that contains the redundant interface";
                    }

                    leaf name {
                        type types-sros:interface-name;
                        description "Redundant interface name";
                    }

                } // container redundant-interface

            } // list fate-sharing-group-template

        } // container up-resiliency

    } // grouping conf-submgt-up-resiliency

}
