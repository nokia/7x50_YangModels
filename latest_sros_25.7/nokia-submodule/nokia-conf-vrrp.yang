submodule nokia-conf-vrrp {

    yang-version "1.1";

    belongs-to nokia-conf { prefix "conf"; }

    import nokia-sros-yang-extensions     { prefix "sros-ext"; }
    import nokia-types-services           { prefix "types-services"; }
    import nokia-types-sros               { prefix "types-sros"; }
    import nokia-types-vrrp               { prefix "types-vrrp"; }

    include nokia-conf-groups;

    sros-ext:sros-major-release "rel25";
    organization "Nokia";
    contact
        "Nokia SR OS Support
         Web: <http://www.nokia.com>";
    description
        "Nokia YANG Data model to configure VRRP policy options on SR OS based routers.

         Copyright 2016 Nokia. All rights reserved. Reproduction of this document
         is authorized on the condition that the foregoing copyright notice is included.

         This nokia-conf-vrrp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-vrrp {
        container vrrp {
            description "Enter the vrrp context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list policy {
                key "policy-id";
                description "Enter the policy list instance";

                leaf policy-id {
                    type uint32 {
                        range "1..9999";
                    }
                    description "Policy ID";
                }

                leaf admin-state {
                    type types-sros:admin-state;
                    default "enable";
                    description "Administrative state of VRRP priority control policy";
                }

                leaf context {
                    type types-services:service-name;
                    sros-ext:immutable;
                    description "Service name to which this policy applies";
                }

                leaf delta-in-use-limit {
                    type types-vrrp:priority;
                    default "1";
                    description "Limit on the delta priority control events";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container priority-event {
                    description "Enter the priority-event context";

                    list host-unreachable {
                        key "ip-address";
                        description "Enter the host-unreachable list instance";

                        leaf ip-address {
                            type types-sros:ip-address-with-zone;
                            description "Host IP address that receives a constant ping probe";
                        }

                        leaf hold-clear {
                            type types-vrrp:event-hold;
                            units "seconds";
                            description "Delay time for a cleared event on the router instance";
                        }

                        leaf hold-set {
                            type types-vrrp:event-hold;
                            units "seconds";
                            description "Hold time before transitioning to cleared state";
                        }

                        leaf drop-count {
                            type uint32 {
                                range "1..60";
                            }
                            default "3";
                            description "Threshold for consecutive message send attempts";
                        }

                        leaf request-interval {
                            type uint32 {
                                range "1..60";
                            }
                            units "seconds";
                            default "1";
                            description "Time interval between consecutive ICMP echo requests";
                        }

                        leaf padding-size {
                            type uint32 {
                                range "0..16384";
                            }
                            units "bytes";
                            default "56";
                            description "Packet length padding of the ICMP packet";
                        }

                        leaf timeout {
                            type uint32 {
                                range "1..60";
                            }
                            units "seconds";
                            default "1";
                            description "Timeout for ICMP echo request messages";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container priority {
                            description "Enter the priority context";

                            leaf priority-level {
                                type types-vrrp:priority;
                                description "Priority level associated with this event";
                            }

                            leaf event-type {
                                type enumeration {
                                    enum delta                          { value 1; }
                                    enum explicit                       { value 2; }
                                }
                                default "delta";
                                description "Effect of priority-level value on base priority value";
                            }

                        } // container priority

                    } // list host-unreachable

                    list lag-port-down {
                        key "lag-name";
                        description "Enter the lag-port-down list instance";

                        leaf lag-name {
                            type types-sros:lag-interface;
                            description "LAG name";
                        }

                        leaf hold-clear {
                            type types-vrrp:event-hold;
                            units "seconds";
                            description "Delay time for a cleared event on the router instance";
                        }

                        leaf hold-set {
                            type types-vrrp:event-hold;
                            units "seconds";
                            description "Hold time before transitioning to cleared state";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list number-down {
                            key "number-of-lag-ports-down";
                            description "Enter the number-down list instance";

                            leaf number-of-lag-ports-down {
                                type uint8 {
                                    range "1..64";
                                }
                                description "Threshold of down LAG ports that create a set event";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container priority {
                                description "Enter the priority context";

                                leaf priority-level {
                                    type types-vrrp:priority;
                                    description "Priority level associated with this event";
                                }

                                leaf event-type {
                                    type enumeration {
                                        enum delta                          { value 1; }
                                        enum explicit                       { value 2; }
                                    }
                                    default "delta";
                                    description "Effect of priority-level value on base priority value";
                                }

                            } // container priority

                        } // list number-down

                        list weight-down {
                            key "lag-ports-down-weight";
                            description "Enter the weight-down list instance";

                            leaf lag-ports-down-weight {
                                type uint8 {
                                    range "1..64";
                                }
                                description "LAG name for the reduced LAG ports";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container priority {
                                description "Enter the priority context";

                                leaf priority-level {
                                    type types-vrrp:priority;
                                    description "Priority level associated with this event";
                                }

                                leaf event-type {
                                    type enumeration {
                                        enum delta                          { value 1; }
                                        enum explicit                       { value 2; }
                                    }
                                    default "delta";
                                    description "Effect of priority-level value on base priority value";
                                }

                            } // container priority

                        } // list weight-down

                    } // list lag-port-down

                    list mc-ipsec-non-forwarding {
                        key "tunnel-group-id";
                        description "Enter the mc-ipsec-non-forwarding list instance";

                        leaf tunnel-group-id {
                            type uint32 {
                                range "1..64";
                            }
                            description "IPSEC tunnel group monitored by priority control event";
                        }

                        leaf hold-clear {
                            type types-vrrp:event-hold;
                            units "seconds";
                            description "Delay time for a cleared event on the router instance";
                        }

                        leaf hold-set {
                            type types-vrrp:event-hold;
                            units "seconds";
                            description "Hold time before transitioning to cleared state";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container priority {
                            description "Enter the priority context";

                            leaf priority-level {
                                type types-vrrp:priority;
                                description "Priority level associated with this event";
                            }

                            leaf event-type {
                                type enumeration {
                                    enum delta                          { value 1; }
                                    enum explicit                       { value 2; }
                                }
                                default "delta";
                                description "Event type";
                            }

                        } // container priority

                    } // list mc-ipsec-non-forwarding

                    list port-down {
                        key "port-id";
                        description "Enter the port-down list instance";

                        leaf port-id {
                            type types-sros:port-named;
                            description "Port ID for the reduced LAG ports";
                        }

                        leaf hold-clear {
                            type types-vrrp:event-hold;
                            units "seconds";
                            description "Delay time for a cleared event on the router instance";
                        }

                        leaf hold-set {
                            type types-vrrp:event-hold;
                            units "seconds";
                            description "Hold time before transitioning to cleared state";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container priority {
                            description "Enter the priority context";

                            leaf priority-level {
                                type types-vrrp:priority;
                                description "Priority level associated with this event";
                            }

                            leaf event-type {
                                type enumeration {
                                    enum delta                          { value 1; }
                                    enum explicit                       { value 2; }
                                }
                                default "delta";
                                description "Effect of priority-level value on base priority value";
                            }

                        } // container priority

                    } // list port-down

                    list route-unknown {
                        key "ip-prefix";
                        description "Enter the route-unknown list instance";

                        leaf ip-prefix {
                            type types-sros:ip-prefix;
                            description "IP prefix of route monitored by priority control event";
                        }

                        leaf hold-clear {
                            type types-vrrp:event-hold;
                            units "seconds";
                            description "Delay time for a cleared event on the router instance";
                        }

                        leaf hold-set {
                            type types-vrrp:event-hold;
                            units "seconds";
                            description "Hold time before transitioning to cleared state";
                        }

                        leaf-list protocol {
                            type enumeration {
                                enum bgp                            { value 0; }
                                enum ospf                           { value 1; }
                                enum isis                           { value 2; }
                                enum rip                            { value 3; }
                                enum static                         { value 4; }
                                enum bgp-vpn                        { value 5; }
                            }
                            max-elements 6;
                            description "Routing protocol as match criterion";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container priority {
                            description "Enter the priority context";

                            leaf priority-level {
                                type types-vrrp:priority;
                                description "Priority level associated with this event";
                            }

                            leaf event-type {
                                type enumeration {
                                    enum delta                          { value 1; }
                                    enum explicit                       { value 2; }
                                }
                                default "delta";
                                description "Effect of priority-level value on base priority value";
                            }

                        } // container priority

                        container less-specific {
                            presence "Enable the less-specific context";
                            description "Enable the less-specific context";

                            leaf allow-default {
                                type boolean;
                                default "false";
                                description "Match on default route";
                            }

                        } // container less-specific

                        list next-hop {
                            key "ip-address";
                            description "Add a list entry for next-hop";

                            leaf ip-address {
                                type types-sros:ip-address-with-zone;
                                description "Next-hop IP address for a returned route prefix";
                            }

                        } // list next-hop

                    } // list route-unknown

                } // container priority-event

            } // list policy

        } // container vrrp

    } // grouping conf-vrrp

}
