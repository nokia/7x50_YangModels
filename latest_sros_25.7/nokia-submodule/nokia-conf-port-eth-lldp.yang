submodule nokia-conf-port-eth-lldp {

    yang-version "1.1";

    belongs-to nokia-conf { prefix "conf"; }

    import nokia-sros-yang-extensions     { prefix "sros-ext"; }
    import nokia-types-lldp               { prefix "types-lldp"; }
    import nokia-types-sros               { prefix "types-sros"; }

    include nokia-conf-groups;

    sros-ext:sros-major-release "rel25";
    organization "Nokia";
    contact
        "Nokia SR OS Support
         Web: <http://www.nokia.com>";
    description
        "Nokia YANG Data model to configure ethernet ports supporting link layer discovery protocol capabilities on SR OS based routers.

         Copyright 2016 Nokia. All rights reserved. Reproduction of this document
         is authorized on the condition that the foregoing copyright notice is included.

         This nokia-conf-port-eth-lldp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-port-eth-lldp {
        container lldp {
            description "Enter the lldp context";

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            list dest-mac {
                key "mac-type";
                description "Enter the dest-mac list instance";

                leaf mac-type {
                    type types-lldp:mac-addr-type;
                    description "Destination MAC address type";
                }

                leaf notification {
                    type boolean;
                    default "false";
                    description "Enable LLDP notifications";
                }

                leaf port-id-subtype {
                    type enumeration {
                        enum tx-if-alias                    { value 1; }
                        enum tx-if-name                     { value 5; }
                        enum tx-local                       { value 7; }
                    }
                    default "tx-local";
                    description "Port ID TLV encoding method for transmission to peer";
                }

                leaf receive {
                    type boolean;
                    default "false";
                    description "Enable LLDP agent to receive but not transmit frames";
                }

                leaf transmit {
                    type boolean;
                    default "false";
                    description "Enable the LLDP agent to transmit frames";
                }

                leaf tunnel-nearest-bridge {
                    when "../mac-type = 'nearest-bridge'" {
                        description "Only valid for nearest-bridge mac-type";
                    }
                    type boolean;
                    default "false";
                    description "Allow the received LLDP packets to be tunneled";
                }

                leaf tunnel-nearest-customer {
                    when "../mac-type = 'nearest-customer'" {
                        description "Only valid for nearest-customer mac-type";
                    }
                    type boolean;
                    default "true";
                    description "Enable the nearest customer tunneling";
                }

                leaf tunnel-nearest-non-tpmr {
                    when "../mac-type = 'nearest-non-tpmr'" {
                        description "Only valid for nearest-non-tpmr mac-type";
                    }
                    type boolean;
                    default "true";
                    description "Enable the nearest non-TPMR tunneling";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container tx-tlvs {
                    description "Enter the tx-tlvs context";

                    leaf port-desc {
                        type boolean;
                        default "false";
                        description "Transmit port description TLVs";
                    }

                    leaf sys-name {
                        type boolean;
                        default "false";
                        description "Transmit system name TLVs";
                    }

                    leaf sys-desc {
                        type boolean;
                        default "false";
                        description "Transmit system description TLVs";
                    }

                    leaf sys-cap {
                        type boolean;
                        default "false";
                        description "Transmit system capabilities TLVs";
                    }

                } // container tx-tlvs

                list tx-mgmt-address {
                    key "mgmt-address-system-type";
                    description "Enter the tx-mgmt-address list instance";

                    leaf mgmt-address-system-type {
                        type enumeration {
                            enum oob                            { value 0; }
                            enum system                         { value 1; }
                            enum system-ipv6                    { value 2; }
                            enum oob-ipv6                       { value 3; }
                        }
                        description "Management address to transmit";
                    }

                    leaf admin-state {
                        type types-sros:admin-state;
                        default "disable";
                        description "Administrative state of transmitting management address";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tx-mgmt-address

            } // list dest-mac

        } // container lldp

    } // grouping conf-port-eth-lldp

}
