submodule nokia-state-router-p2mp-sr-tree {

    yang-version "1.1";

    belongs-to nokia-state { prefix "state"; }

    import nokia-sros-yang-extensions     { prefix "sros-ext"; }
    import nokia-types-sros               { prefix "types-sros"; }

    sros-ext:sros-major-release "rel25";
    organization "Nokia";
    contact
        "Nokia SR OS Support
         Web: <http://www.nokia.com>";
    description
        "Nokia YANG Data model with operational state for Base router p2mp-sr-tree on SR OS based routers.

         Copyright 2016 Nokia. All rights reserved. Reproduction of this document
         is authorized on the condition that the foregoing copyright notice is included.

         This nokia-state-router-p2mp-sr-tree YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-router-p2mp-sr-tree {
        container p2mp-sr-tree {
            description "Enter the p2mp-sr-tree context";

            leaf oper-state {
                type enumeration {
                    enum unknown                        { value 1; }
                    enum in-service                     { value 2; }
                    enum out-of-service                 { value 3; }
                    enum transition                     { value 4; }
                }
                description "oper-state for p2mp-sr-tree status entry.";
            }

            container statistics {
                description "Enter the statistics context";

                leaf total-static-policies {
                    type uint32;
                    description "This value indicates the total number of p2mp static policies.";
                }

                leaf total-pce-policies {
                    type uint32;
                    description "This value indicates the total number of p2mp pce policies.";
                }

                leaf total-sr-policies {
                    type uint32;
                    description "This value indicates the total number of p2mp sr policies.";
                }

                leaf total-static-candidate-paths {
                    type uint32;
                    description "This value indicates the total number of p2mp static candidate paths.";
                }

                leaf total-pce-candidate-paths {
                    type uint32;
                    description "This value indicates the total number of pce candidate paths.";
                }

                leaf total-sr-plcy-candidate-paths {
                    type uint32;
                    description "This value indicates the total number of sr policy candidate paths.";
                }

                leaf total-static-replication-seg {
                    type uint32;
                    description "This value indicates the total number of static replication segments.";
                }

                leaf total-pce-replication-seg {
                    type uint32;
                    description "This value indicates the total number of pce replication segments.";
                }

                leaf total-sr-plcy-replication-seg {
                    type uint32;
                    description "This value indicates the total number of sr policy replication segments.";
                }

                leaf total-static-nh {
                    type uint32;
                    description "This value indicates the total number of static next-hops.";
                }

                leaf total-pce-nh {
                    type uint32;
                    description "This value indicates the total number of pce next-hops.";
                }

                leaf total-sr-plcy-nh {
                    type uint32;
                    description "This value indicates the total number of sr-plcy next-hops.";
                }

                leaf total-num-push {
                    type uint32;
                    description "This value indicates the total number of push.";
                }

                leaf total-num-swap {
                    type uint32;
                    description "This value indicates the total number of swap.";
                }

                leaf total-num-pop {
                    type uint32;
                    description "This value indicates the total number of pop.";
                }

                leaf total-num-tnls-allocated {
                    type uint32;
                    description "This value indicates the total number of tunnels allocated.";
                }

                leaf total-num-nhif-insvc {
                    type uint32;
                    description "This value indicates the total number of in-service next-hop interfaces.";
                }

                leaf total-num-nhif-outsvc {
                    type uint32;
                    description "This value indicates the total number of out-of-service next-hop interfaces.";
                }

                leaf total-num-nhif-unsupported {
                    type uint32;
                    description "This value indicates the total number of unsupported next-hop interfaces.";
                }

                leaf total-num-nhif-mismatched {
                    type uint32;
                    description "This value indicates the total number of mismatched next-hop interfaces.";
                }

                leaf total-num-nhif-nobfd {
                    type uint32;
                    description "This value indicates the total number of no-bfd next-hop interfaces.";
                }

                leaf dataplane-backpressure-active {
                    type uint32;
                    description "This value indicates whether dataplane backpressure active or not.";
                }

                leaf dataplane-backpressure-count {
                    type uint32;
                    description "This value indicates dataplane backpressure count.";
                }

                leaf unknown-originator-owner-error-count {
                    type uint32;
                    description "This value indicates unknown originator owner error count.";
                }

                leaf duplicate-treeids-error-count {
                    type uint32;
                    description "This value indicates duplicate treeids error count.";
                }

                leaf progfail-nhidx-error-count {
                    type uint32;
                    description "This value indicates progfail nexthop index error count.";
                }

                leaf progfail-labels-error-count {
                    type uint32;
                    description "This value indicates progfail labels error count.";
                }

                leaf progfail-tunnels-error-count {
                    type uint32;
                    description "This value indicates progfail tunnels error count.";
                }

                leaf progfail-protgroup-error-count {
                    type uint32;
                    description "This value indicates progfail protgroup error count.";
                }

            } // container statistics

            container labels {
                description "Enter the labels context";

                list label {
                    key "label-id";
                    description "Enter the label list instance";

                    leaf label-id {
                        type int32;
                        description "This value indicates the owner of this label.";
                    }

                    leaf owner {
                        type enumeration {
                            enum none                           { value 0; }
                            enum static                         { value 1; }
                            enum pce                            { value 2; }
                            enum sr-pol                         { value 3; }
                        }
                        description "This value indicates the owner of this label.";
                    }

                    leaf in-use {
                        type enumeration {
                            enum no                             { value 0; }
                            enum yes                            { value 1; }
                        }
                        description "This value indicates whether the label is in use";
                    }

                } // list label

            } // container labels

            container database {
                description "Enter the database context";

                list p2mp-policy {
                    key "root-address tree-id";
                    description "Enter the p2mp-policy list instance";

                    leaf root-address {
                        type types-sros:ip-address;
                        description "root-address for replication-segment entries.";
                    }

                    leaf tree-id {
                        type uint32;
                        description "tree-id for replication-segment entries.";
                    }

                    leaf num-paths {
                        type uint32;
                        description "num-paths for replication segment entries.";
                    }

                    leaf oper-state {
                        type enumeration {
                            enum unknown                        { value 1; }
                            enum in-service                     { value 2; }
                            enum out-of-service                 { value 3; }
                            enum transition                     { value 4; }
                        }
                        description "operation state for replication segment entries.";
                    }

                    leaf policy-name {
                        type types-sros:named-item;
                        description "policy-name for replication segment entries.";
                    }

                    leaf tunnel-id {
                        type uint32;
                        description "tunnel index for replication segment entries.";
                    }

                    leaf active-candidate-path {
                        type types-sros:named-item-or-empty;
                        description "active-candidate-path for replication segment entries.";
                    }

                    list candidate-path {
                        key "protocol-id originator-asn originator discriminator";
                        description "Enter the candidate-path list instance";

                        leaf protocol-id {
                            type enumeration {
                                enum pcep                           { value 10; }
                                enum bgp-sr-policy                  { value 20; }
                                enum configuration                  { value 30; }
                            }
                            description "protocol-id for the p2mp policy candidate path entry.";
                        }

                        leaf originator-asn {
                            type uint32;
                            description "originator asn value for the p2mp policy candidate path entry.";
                        }

                        leaf originator {
                            type types-sros:ipv4-unicast-or-zero-address;
                            description "originator node address for the p2mp policy candidate path entry.";
                        }

                        leaf discriminator {
                            type uint32;
                            description "discriminator value for the p2mp policy candidate path entry.";
                        }

                        leaf oper-state {
                            type enumeration {
                                enum unknown                        { value 1; }
                                enum in-service                     { value 2; }
                                enum out-of-service                 { value 3; }
                                enum transition                     { value 4; }
                            }
                            description "operational state for the p2mp policy candidate path entry.";
                        }

                        leaf path-plsp-id {
                            type uint32;
                            description "path-plsp-id for the p2mp policy candidate path entry.";
                        }

                        leaf active-instance {
                            type uint32;
                            description "active instance for the p2mp policy candidate path entry.";
                        }

                        leaf standby-instance {
                            type uint32;
                            description "standby instance for the p2mp policy candidate path entry.";
                        }

                        leaf preference {
                            type uint32;
                            description "preference for the p2mp policy candidate path entry.";
                        }

                        leaf create-time {
                            type types-sros:time-interval;
                            description
                                "The value indicates the sysUpTime when this candidate path
                                 was created.";
                        }

                    } // list candidate-path

                } // list p2mp-policy

                list replication-segment {
                    key "root-address tree-id instance-id protocol-id";
                    description "Enter the replication-segment list instance";

                    leaf root-address {
                        type types-sros:ip-address;
                        description "root-address for replication-segment entries.";
                    }

                    leaf tree-id {
                        type uint32;
                        description "tree-id for replication-segment entries.";
                    }

                    leaf instance-id {
                        type uint32;
                        description "instance-id for replication-segment entries.";
                    }

                    leaf protocol-id {
                        type enumeration {
                            enum pcep                           { value 10; }
                            enum bgp-sr-policy                  { value 20; }
                            enum configuration                  { value 30; }
                        }
                        description "protocol-id for replication-segment entries.";
                    }

                    leaf num-hops {
                        type uint32;
                        description "num-paths for replication segment entries.";
                    }

                    leaf oper-state {
                        type enumeration {
                            enum unknown                        { value 1; }
                            enum in-service                     { value 2; }
                            enum out-of-service                 { value 3; }
                            enum transition                     { value 4; }
                        }
                        description "operation state for replication segment entries.";
                    }

                    leaf policy-name {
                        type types-sros:named-item;
                        description "policy-name for replication segment entries.";
                    }

                    leaf tunnel-id {
                        type uint32;
                        description "tunnel index for replication segment entries.";
                    }

                    leaf down-reason {
                        type enumeration {
                            enum none                           { value 0; }
                            enum idx-alloc-fail                 { value 1; }
                            enum all-nh-down                    { value 2; }
                            enum label-reg-fail                 { value 3; }
                            enum iom-pgrm-fail                  { value 4; }
                            enum iom-ack-pend                   { value 5; }
                        }
                        description "down-reason for replication segment entries.";
                    }

                    leaf ltn {
                        type boolean;
                        description
                            "The value of ltn indicates whether this replication policy is rooted
                             in this node(ingress LSP).";
                    }

                    leaf is-local {
                        type boolean;
                        description
                            "The value of is-local indicates whether this replication policy has
                             any MVPN leaf(egress LSP).";
                    }

                    leaf ccid {
                        type uint32;
                        description
                            "The value of ccid indicates the referenced CCI(central controler
                             instruction) object ID in PCC.";
                    }

                    leaf update-id {
                        type uint32;
                        description
                            "The value of update-id indicates the referenced update id among the list
                             of CCID objects in PCC. ";
                    }

                    container segment-routing-mpls {
                        description "Enter the segment-routing-mpls context";

                        leaf incoming-sid {
                            type uint32;
                            description "incoming-sid for segment-routing-mpls replication-segment entries.";
                        }

                        leaf sid-action {
                            type enumeration {
                                enum none                           { value 0; }
                                enum push                           { value 1; }
                                enum pop                            { value 2; }
                                enum swap                           { value 3; }
                            }
                            description "sid-action for replication-segment entries.";
                        }

                        list downstream-nodes {
                            key "downstream-index";
                            description "Enter the downstream-nodes list instance";

                            leaf downstream-index {
                                type uint32;
                                description
                                    "The value of downstream-index indicates the downstream-nodes group index within a
                                     candidate path entry inside a tree-side replication policy instance.";
                            }

                            leaf next-hop-address {
                                type types-sros:ip-address-with-zone;
                                description "next-hop-address for a replication segment next hop entry.";
                            }

                            leaf oper-state {
                                type enumeration {
                                    enum unknown                        { value 1; }
                                    enum in-service                     { value 2; }
                                    enum out-of-service                 { value 3; }
                                    enum transition                     { value 4; }
                                }
                                description "operation state for replication segment next-hop entries.";
                            }

                            leaf down-reason {
                                type enumeration {
                                    enum none                           { value 0; }
                                    enum invalid-nhop                   { value 1; }
                                    enum pip-if-not-found               { value 2; }
                                    enum pip-if-down                    { value 3; }
                                    enum pip-if-v6-down                 { value 4; }
                                    enum rtm-unresolved                 { value 5; }
                                    enum if-not-unnum                   { value 6; }
                                    enum if-not-ipv6-link-local         { value 7; }
                                    enum bfd-down                       { value 8; }
                                    enum idx-alloc-fail                 { value 9; }
                                    enum invalid-label-stack            { value 10; }
                                    enum sr-tunnel-pgrm-fail            { value 11; }
                                    enum sr-tunnel-down                 { value 12; }
                                }
                                description "down-reason for replication segment next-hop entries.";
                            }

                            leaf protect-nexthop-address {
                                type types-sros:ip-address-with-zone;
                                description "protect-nexthop-address for replication segment next-hop entries.";
                            }

                            leaf nexthop-interface-name {
                                type types-sros:named-item-or-empty;
                                description "protect interface name for replication-segment next-hop entries.";
                            }

                            leaf protect-oper-state {
                                type enumeration {
                                    enum unknown                        { value 1; }
                                    enum in-service                     { value 2; }
                                    enum out-of-service                 { value 3; }
                                    enum transition                     { value 4; }
                                }
                                description "protect operational state for replication-segment next-hop entries.";
                            }

                            leaf protect-oper-down-reason {
                                type enumeration {
                                    enum none                           { value 0; }
                                    enum invalid-nhop                   { value 1; }
                                    enum pip-if-not-found               { value 2; }
                                    enum pip-if-down                    { value 3; }
                                    enum pip-if-v6-down                 { value 4; }
                                    enum rtm-unresolved                 { value 5; }
                                    enum if-not-unnum                   { value 6; }
                                    enum if-not-ipv6-link-local         { value 7; }
                                    enum bfd-down                       { value 8; }
                                    enum idx-alloc-fail                 { value 9; }
                                    enum invalid-label-stack            { value 10; }
                                    enum sr-tunnel-pgrm-fail            { value 11; }
                                    enum sr-tunnel-down                 { value 12; }
                                }
                                description "protect-oper-down-reason for the replication-segment next-hop entry.";
                            }

                            leaf protect-nexthop-id {
                                type uint32;
                                description "protect nexthop id for the replication-segment next-hop entry.";
                            }

                            leaf protect-nexthop-if-name {
                                type types-sros:named-item-or-empty;
                                description "protect nexthop interface name for the replication-segment next-hop entry.";
                            }

                            container label {
                                description "Enter the label context";

                                list sid-list {
                                    key "index";
                                    description "Enter the sid-list list instance";

                                    leaf index {
                                        type uint32 {
                                            range "0..10";
                                        }
                                        description "index for the replication segment next hop outgoing replication sid entry.";
                                    }

                                    leaf replication-sid {
                                        type uint32;
                                        description "replication-sid for the replication segment next hop outgoing replication sid entry.";
                                    }

                                } // list sid-list

                                list protect-sid-list {
                                    key "index";
                                    description "Enter the protect-sid-list list instance";

                                    leaf index {
                                        type uint32 {
                                            range "0..10";
                                        }
                                        description "index for the replication segment next hop outgoing protect replication sid entry.";
                                    }

                                    leaf replication-sid {
                                        type uint32;
                                        description "replication-sid for the replication segment downstream nodes outgoing replication sid entry.";
                                    }

                                } // list protect-sid-list

                            } // container label

                        } // list downstream-nodes

                    } // container segment-routing-mpls

                    container segment-routing-v6 {
                        description "Enter the segment-routing-v6 context";

                        leaf incoming-sid {
                            type types-sros:ipv6-address-with-zone;
                            description "incoming-sid for segment-routing-v6 replication-segment entries.";
                        }

                        leaf role {
                            type enumeration {
                                enum none                           { value 0; }
                                enum root                           { value 1; }
                                enum leaf                           { value 2; }
                                enum transit                        { value 3; }
                            }
                            description "Role for segment-routing-v6 replication-segment entries.";
                        }

                        list downstream-nodes {
                            key "downstream-index";
                            description "Enter the downstream-nodes list instance";

                            leaf downstream-index {
                                type uint32;
                                description
                                    "The value of downstream-index indicates the downstream-nodes group index within a
                                     candidate path entry inside a tree-side replication policy instance.";
                            }

                            leaf replication-sid {
                                type types-sros:ipv6-address-with-zone;
                                description "replication-sid for a replication segment next hop entry.";
                            }

                            leaf oper-state {
                                type enumeration {
                                    enum unknown                        { value 1; }
                                    enum in-service                     { value 2; }
                                    enum out-of-service                 { value 3; }
                                    enum transition                     { value 4; }
                                }
                                description "operation state for replication segment next-hop entries.";
                            }

                            leaf down-reason {
                                type enumeration {
                                    enum none                           { value 0; }
                                    enum invalid-nhop                   { value 1; }
                                    enum pip-if-not-found               { value 2; }
                                    enum pip-if-down                    { value 3; }
                                    enum pip-if-v6-down                 { value 4; }
                                    enum rtm-unresolved                 { value 5; }
                                    enum if-not-unnum                   { value 6; }
                                    enum if-not-ipv6-link-local         { value 7; }
                                    enum bfd-down                       { value 8; }
                                    enum idx-alloc-fail                 { value 9; }
                                    enum invalid-label-stack            { value 10; }
                                    enum sr-tunnel-pgrm-fail            { value 11; }
                                    enum sr-tunnel-down                 { value 12; }
                                }
                                description "down-reason for replication segment next-hop entries.";
                            }

                            leaf nexthop-interface-name {
                                type types-sros:named-item-or-empty;
                                description "nexthop interface name for replication-segment next-hop entries.";
                            }

                            leaf resolved-nexthop {
                                type types-sros:ipv6-address-with-zone;
                                description "resolved nexthop address for a replication-segment next-hop entry.";
                            }

                        } // list downstream-nodes

                    } // container segment-routing-v6

                } // list replication-segment

            } // container database

        } // container p2mp-sr-tree

    } // grouping state-router-p2mp-sr-tree

}
