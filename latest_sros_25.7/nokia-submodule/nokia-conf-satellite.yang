submodule nokia-conf-satellite {

    yang-version "1.1";

    belongs-to nokia-conf { prefix "conf"; }

    import nokia-sros-yang-extensions     { prefix "sros-ext"; }
    import nokia-types-chassis            { prefix "types-chassis"; }
    import nokia-types-sros               { prefix "types-sros"; }
    import nokia-types-system             { prefix "types-system"; }

    include nokia-conf-groups;
    include nokia-conf-port;
    include nokia-conf-system;

    sros-ext:sros-major-release "rel25";
    organization "Nokia";
    contact
        "Nokia SR OS Support
         Web: <http://www.nokia.com>";
    description
        "Nokia YANG Data model to configure satellite parameters on SR OS based routers.

         Copyright 2016 Nokia. All rights reserved. Reproduction of this document
         is authorized on the condition that the foregoing copyright notice is included.

         This nokia-conf-satellite YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-satellite {
        container satellite {
            description "Enter the satellite context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container file-transfer {
                description "Enter the file-transfer context";

                leaf ftp {
                    type boolean;
                    default "true";
                    description "Use FTP between host and satellite";
                }

                leaf scp {
                    type boolean;
                    default "false";
                    description "Use FTP between host and satellite";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container file-transfer

            list port-template {
                key "template-name";
                description "Enter the port-template list instance";

                leaf template-name {
                    type types-sros:named-item;
                    description "Associated port template name";
                }

                leaf description {
                    type types-sros:description;
                    description "Text description";
                }

                leaf admin-state {
                    type types-sros:admin-state;
                    default "disable";
                    description "Administrative state of the port template";
                }

                leaf sat-type {
                    type types-chassis:sat-type;
                    sros-ext:immutable;
                    sros-ext:auto-restart-to-modify;
                    mandatory true;
                    description "Satellite type for use with the port template";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list port {
                    key "sat-phys-port-id";
                    description "Enter the port list instance";

                    leaf sat-phys-port-id {
                        type types-sros:named-item-255;
                        description "Satellite physical port ID";
                    }

                    leaf role {
                        type enumeration {
                            enum none                           { value 0; }
                            enum uplink                         { value 1; }
                            enum client                         { value 2; }
                        }
                        sros-ext:immutable;
                        description "Satellite port role";
                    }

                    leaf uplink {
                        type union {
                            type string;
                            type enumeration {
                                enum none                           { value 0; }
                            }
                        }
                        sros-ext:immutable;
                        description "Uplink association used for associated satellite port";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list port

            } // list port-template

            list ethernet-satellite {
                key "satellite-id";
                description "Enter the ethernet-satellite list instance";

                leaf satellite-id {
                    type types-chassis:sat-id;
                    description "Ethernet satellite ID";
                }

                leaf description {
                    type types-sros:description;
                    description "Text description";
                }

                leaf mac-address {
                    type types-sros:mac-unicast-address-no-zero;
                    description "MAC address for the satellite chassis";
                }

                leaf sat-type {
                    type types-chassis:sat-type;
                    sros-ext:immutable;
                    description "Type of satellite variant for the associated chassis";
                }

                leaf software-repository {
                    type leafref {
                        path "../../../system/software-repository/repository-name";
                    }
                    description "Software repository bound to the associated satellite";
                }

                leaf sync-e {
                    type boolean;
                    default "false";
                    description "Enable the synchronous Ethernet operation";
                }

                leaf admin-state {
                    type types-sros:admin-state;
                    default "disable";
                    description "Administrative state of the satellite";
                }

                leaf-list feature {
                    type enumeration {
                        enum local-forward                  { value 0; }
                        enum ptp-tc                         { value 1; }
                    }
                    max-elements 2;
                    description "Functionality to enable";
                }

                leaf port-template {
                    when "../sat-type" {
                        description "sat-type must be set when port-template is set";
                    }
                    type types-sros:named-item;
                    sros-ext:immutable;
                    description "Port template name";
                }

                leaf ptp-tc {
                    type boolean;
                    default "false";
                    description "Enable the 1EEE 1588 transparent clock function";
                }

                leaf client-down-delay {
                    type int32 {
                        range "0..1800";
                    }
                    description "Delay between uplink as unavailable and disabling ports";
                }

                leaf console-access {
                    type types-sros:admin-state;
                    default "disable";
                    description "Satellite console interface access";
                }

                leaf dynamic-uplink {
                    type boolean;
                    sros-ext:immutable;
                    default "false";
                    description "Enable dynamic uplink resilience for Ethernet satellite";
                }

                leaf uplink-distribution {
                    type enumeration {
                        enum single-complex                 { value 1; }
                        enum dual-complex                   { value 2; }
                    }
                    sros-ext:immutable;
                    description "Forwarding complex type for uplink distribution";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container ptp-ip {
                    description "Enter the ptp-ip context";

                    leaf admin-state {
                        type types-sros:admin-state;
                        default "disable";
                        description "Administrative state of PTP over IP transparent clock";
                    }

                    leaf ipv4-address {
                        type types-sros:ipv4-address;
                        description "IPv4 destination address of PTP messages";
                    }

                    leaf ipv6-address {
                        type types-sros:ipv6-address;
                        description "IPv6 destination address of PTP messages";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container ptp-ip

                container central-frequency-clock {
                    description "Enter the central-frequency-clock context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container ref1 {
                        description "Enter the ref1 context";

                        leaf quality-level-override {
                            type types-system:ref-ssm-quality-level-override;
                            default "unused";
                            description "Quality level of the satellite timing reference";
                        }

                        leaf admin-state {
                            type types-sros:admin-state;
                            default "disable";
                            description "Administrative state of the satellite timing reference";
                        }

                        leaf source-port {
                            type types-sros:port;
                            description "Source port for timing reference within satellite";
                        }

                    } // container ref1

                    container ref2 {
                        description "Enter the ref2 context";

                        leaf quality-level-override {
                            type types-system:ref-ssm-quality-level-override;
                            default "unused";
                            description "Quality level of the satellite timing reference";
                        }

                        leaf admin-state {
                            type types-sros:admin-state;
                            default "disable";
                            description "Administrative state of the satellite timing reference";
                        }

                        leaf source-port {
                            type types-sros:port;
                            description "Source port for timing reference within satellite";
                        }

                    } // container ref2

                } // container central-frequency-clock


                list port-map {
                    key "client-port-id";
                    description "Enter the port-map list instance";

                    leaf client-port-id {
                        type leafref {
                            path "../../../../port/port-id";
                        }
                        description "Satellite client port associated with the port mapping";
                    }

                    leaf primary {
                        type leafref {
                            path "../../../../port/port-id";
                        }
                        description "Primary satellite uplink for the associate client port";
                    }

                    leaf secondary {
                        type leafref {
                            path "../../../../port/port-id";
                        }
                        description "Secondary satellite uplink for associate client port";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list port-map

            } // list ethernet-satellite

            list port-topology {
                key "local-port-id";
                description "Enter the port-topology list instance";

                leaf local-port-id {
                    type leafref {
                        path "../../../port/port-id";
                    }
                    description "Local port identifier";
                }

                leaf far-end-port-id {
                    type leafref {
                        path "../../../port/port-id";
                    }
                    sros-ext:immutable;
                    mandatory true;
                    description "Far end port ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list port-topology

        } // container satellite

    } // grouping conf-satellite

}
