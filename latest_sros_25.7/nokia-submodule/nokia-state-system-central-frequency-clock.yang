submodule nokia-state-system-central-frequency-clock {

    yang-version "1.1";

    belongs-to nokia-state { prefix "state"; }

    import nokia-sros-yang-extensions     { prefix "sros-ext"; }
    import nokia-types-card               { prefix "types-card"; }
    import nokia-types-system             { prefix "types-system"; }

    sros-ext:sros-major-release "rel25";
    organization "Nokia";
    contact
        "Nokia SR OS Support
         Web: <http://www.nokia.com>";
    description
        "Nokia YANG Data model with operational state for system central-frequency-clock parameters on SR OS based routers.

         Copyright 2016 Nokia. All rights reserved. Reproduction of this document
         is authorized on the condition that the foregoing copyright notice is included.

         This nokia-state-system-central-frequency-clock YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-07-16";

    grouping state-system-central-frequency-clock {
        container central-frequency-clock {
            description "Enter the central-frequency-clock context";

            list cpm {
                key "cpm-slot";
                description "Enter the cpm list instance";

                leaf cpm-slot {
                    type types-card:cpm-card-slot;
                    description "The unique value which identifies this CPM slot.";
                }

                leaf clock-state {
                    type types-system:sets-clock-state;
                    description "Indicates the present status of the synchronous timing equipment subsystem (SETS)";
                }

                leaf quality-level {
                    type types-system:ssm-quality-level;
                    description "The QL of the system timing reference";
                }

                leaf current-frequency-offset {
                    type int32;
                    units "parts per million";
                    description "Current PLL frequency offset";
                }

                leaf selector-b {
                    type types-system:reference-source;
                    description "Setting of selector b (input to SETS)";
                }

                leaf current-frequency-offset-ppb {
                    type int32;
                    units "parts per billion";
                    description "Current PLL frequency offset in parts per billion";
                }

                container bits-input-a {
                    description "Enter the bits-input-a context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container bits-input-a

                container bits-input-b {
                    description "Enter the bits-input-b context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container bits-input-b

                container reference-1 {
                    description "Enter the reference-1 context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container reference-1

                container reference-2 {
                    description "Enter the reference-2 context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container reference-2

                container synce-a {
                    description "Enter the synce-a context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container synce-a

                container synce-b {
                    description "Enter the synce-b context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container synce-b

                container gnss-a {
                    description "Enter the gnss-a context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container gnss-a

                container gnss-b {
                    description "Enter the gnss-b context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container gnss-b

                container ptp {
                    description "Enter the ptp context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                    leaf rx-quality-level {
                        type types-system:ssm-quality-level;
                        description "Received QL for this input";
                    }

                } // container ptp

                container mate-cpm {
                    description "Enter the mate-cpm context";

                    leaf input-state {
                        type types-system:reference-input-state;
                        description "State of this input";
                    }

                    leaf-list alarms {
                        type types-system:reference-input-alarm;
                        description "Active alarms for this input";
                    }

                    leaf qualified-for-use {
                        type boolean;
                        description "Indicates the input is qualified for use";
                    }

                    leaf selected-for-use {
                        type boolean;
                        description "Indicates the input is selected for use";
                    }

                } // container mate-cpm

                container bits-output-a {
                    description "Enter the bits-output-a context";

                    leaf output-source {
                        type types-system:reference-source;
                        description "Source used for this output";
                    }

                    leaf tx-quality-level {
                        type types-system:ssm-quality-level;
                        description "QL transmitted on this output";
                    }

                    leaf squelched {
                        type boolean;
                        description "Indicates if the output is squelched";
                    }

                } // container bits-output-a

                container bits-output-b {
                    description "Enter the bits-output-b context";

                    leaf output-source {
                        type types-system:reference-source;
                        description "Source used for this output";
                    }

                    leaf tx-quality-level {
                        type types-system:ssm-quality-level;
                        description "QL transmitted on this output";
                    }

                    leaf squelched {
                        type boolean;
                        description "Indicates if the output is squelched";
                    }

                } // container bits-output-b

            } // list cpm

        } // container central-frequency-clock

    } // grouping state-system-central-frequency-clock

}
