submodule nokia-conf-svc-epipe {

    yang-version "1.1";

    belongs-to nokia-conf { prefix "conf"; }

    import nokia-sros-yang-extensions     { prefix "sros-ext"; }
    import nokia-types-eth-cfm            { prefix "types-eth-cfm"; }
    import nokia-types-qos                { prefix "types-qos"; }
    import nokia-types-router             { prefix "types-router"; }
    import nokia-types-services           { prefix "types-services"; }
    import nokia-types-sros               { prefix "types-sros"; }

    include nokia-conf-aa-group;
    include nokia-conf-anysec;
    include nokia-conf-application-assurance;
    include nokia-conf-bfd;
    include nokia-conf-eth-cfm;
    include nokia-conf-filter;
    include nokia-conf-groups;
    include nokia-conf-log;
    include nokia-conf-policy-options;
    include nokia-conf-port;
    include nokia-conf-port-eth-access;
    include nokia-conf-port-ethernet;
    include nokia-conf-qos;
    include nokia-conf-router;
    include nokia-conf-router-segment-routing;
    include nokia-conf-service;
    include nokia-conf-svc-vpls;
    include nokia-conf-system;
    include nokia-conf-system-security;

    sros-ext:sros-major-release "rel25";
    organization "Nokia";
    contact
        "Nokia SR OS Support
         Web: <http://www.nokia.com>";
    description
        "Nokia YANG Data model to configure epipe services on SR OS based routers.

         Copyright 2016 Nokia. All rights reserved. Reproduction of this document
         is authorized on the condition that the foregoing copyright notice is included.

         This nokia-conf-svc-epipe YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-svc-epipe {
        list epipe {
            key "service-name";
            description "Enter the epipe list instance";

            leaf service-name {
                type types-services:service-name;
                description "Administrative service name";
            }

            leaf service-id {
                type types-services:external-service-id;
                sros-ext:immutable;
                description "Service ID";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the service";
            }

            leaf vpn-id {
                type types-services:vpn-id;
                sros-ext:immutable;
                description "VPN identifier for the service";
            }

            leaf vc-switching {
                type boolean;
                sros-ext:immutable;
                default "false";
                description "Use PW switching signaling for spoke SDPs in service";
            }

            leaf test {
                type boolean;
                sros-ext:immutable;
                default "false";
                description "Designate as a test service";
            }

            leaf service-mtu {
                type int32 {
                    range "1..9782";
                }
                description "MTU size";
            }

            leaf flexible-cross-connect {
                type boolean;
                sros-ext:immutable;
                default "false";
                description "Enable FXC mode";
            }

            leaf oper-group {
                type leafref {
                    path "../../oper-group/name";
                }
                description "Oper-group name";
            }

            leaf ignore-l2vpn-mtu-mismatch {
                type boolean;
                default "false";
                description "Ignore the L2 VPN MTU mismatch with local service MTU";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list segment-routing-v6 {
                key "instance";
                description "Enter the segment-routing-v6 list instance";

                leaf instance {
                    type types-services:epipe-srv6-instance;
                    description "Segment routing v6 instance";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list locator {
                    key "locator-name";
                    max-elements 1;
                    description "Enter the locator list instance";

                    leaf locator-name {
                        type leafref {
                            path "../../../../../router/segment-routing/segment-routing-v6/locator/locator-name";
                        }
                        description "SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container end-dx2 {
                            presence "Enable the end-dx2 context";
                            description "Enable the end-dx2 context";

                            leaf value {
                                type uint32 {
                                    range "1..1048575";
                                }
                                description "SRv6 function value";
                            }

                        } // container end-dx2

                    } // container function

                } // list locator

                list micro-segment-locator {
                    key "locator-name";
                    max-elements 1;
                    description "Enter the micro-segment-locator list instance";

                    leaf locator-name {
                        type leafref {
                            path "../../../../../router/segment-routing/segment-routing-v6/micro-segment-locator/locator-name";
                        }
                        description "Micro-segment SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container udx2 {
                            presence "Enable the udx2 context";
                            description "Enable the udx2 context";

                            leaf value {
                                type uint32 {
                                    range "1..1048575";
                                }
                                description "SRv6 function value";
                            }

                        } // container udx2

                    } // container function

                } // list micro-segment-locator

            } // list segment-routing-v6

            list bgp {
                key "bgp-instance";
                description "Enter the bgp list instance";

                leaf bgp-instance {
                    type int32 {
                        range "1..2";
                    }
                    description "BGP instance";
                }

                leaf route-distinguisher {
                    type types-services:vpn-route-distinguisher-or-auto-rd;
                    description "RD component for NLRI for L2VPN and EVPN families";
                }

                leaf-list vsi-import {
                    type leafref {
                        path "../../../../policy-options/policy-statement/name";
                    }
                    max-elements 5;
                    ordered-by user;
                    description "VSI import policies";
                }

                leaf-list vsi-export {
                    type leafref {
                        path "../../../../policy-options/policy-statement/name";
                    }
                    max-elements 5;
                    ordered-by user;
                    description "VSI export policies";
                }

                leaf adv-service-mtu {
                    type int32 {
                        range "0..9782";
                    }
                    description "Advertised service MTU value";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container route-target {
                    description "Enter the route-target context";

                    leaf export {
                        type types-services:route-target;
                        description "Extended community name for default import policy";
                    }

                    leaf import {
                        type types-services:route-target;
                        description "Extended community name for default import policy";
                    }

                } // container route-target

                list pw-template-binding {
                    key "pw-template-name";
                    max-elements 100;
                    description "Enter the pw-template-binding list instance";

                    leaf pw-template-name {
                        type leafref {
                            path "../../../../pw-template/pw-template-name";
                        }
                        description "Policy name";
                    }

                    leaf bfd-template {
                        type leafref {
                            path "../../../../../bfd/bfd-template/name";
                        }
                        description "BFD template name for PW-Template binding";
                    }

                    leaf bfd-liveness {
                        type boolean;
                        default "false";
                        description "Enable BFD";
                    }

                    leaf-list import-rt {
                        type types-services:route-target;
                        max-elements 5;
                        description "Import route-target communities";
                    }

                    leaf endpoint {
                        type leafref {
                            path "../../../endpoint/name";
                        }
                        sros-ext:immutable;
                        description "Endpoint name associated with the BGP PW template";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list pw-template-binding

            } // list bgp

            container bgp-vpws {
                presence "Enable the bgp-vpws context";
                description "Enable the bgp-vpws context";

                leaf admin-state {
                    type types-sros:admin-state;
                    default "disable";
                    description "Administrative state of the VPWS edge instance";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container local-ve {
                    description "Enter the local-ve context";

                    leaf name {
                        type types-sros:named-item;
                        sros-ext:auto-restart-to-modify;
                        description "Local VPWS instance name";
                    }

                    leaf id {
                        type types-services:site-id;
                        sros-ext:auto-restart-to-modify;
                        description "Local VPWS edge ID";
                    }

                } // container local-ve

                list remote-ve {
                    key "name";
                    max-elements 2;
                    description "Enter the remote-ve list instance";

                    leaf name {
                        type types-sros:named-item;
                        description "Remote PE name to which a PW is to be signaled";
                    }

                    leaf id {
                        type types-services:site-id;
                        description "Remote VPWS edge ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list remote-ve

            } // container bgp-vpws

            list endpoint {
                key "name";
                max-elements 2;
                description "Enter the endpoint list instance";

                leaf name {
                    type types-sros:named-item;
                    description "Service endpoint name";
                }

                leaf description {
                    type types-sros:description;
                    description "Text description";
                }

                leaf revert-time {
                    type types-services:revert-time;
                    default "immediate";
                    description "Time to wait before reverting to primary spoke SDP";
                }

                leaf hold-time-active {
                    type types-services:hold-time-active;
                    description "Time before entering standby when MC-LAG SAP goes down";
                }

                leaf standby-signaling {
                    type enumeration {
                        enum master                         { value 1; }
                        enum slave                          { value 2; }
                    }
                    description "Endpoint behavior to handle the PW standby bit";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list endpoint

            container eth-cfm {
                description "Enter the eth-cfm context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container eth-cfm

            container load-balancing {
                description "Enter the load-balancing context";

                leaf per-service-hashing {
                    type boolean;
                    default "false";
                    description "Enable per-service hashing for Ethernet services";
                }

                leaf lbl-eth-or-ip-l4-teid {
                    type boolean;
                    default "false";
                    description "Enable hashing of MPLS ethernet and IP packets on SAPs";
                }

            } // container load-balancing

            list nat-outside {
                key "nat-group";
                description "Enter the nat-outside list instance";

                leaf nat-group {
                    type uint32;
                    description "NAT group";
                }

                leaf admin-state {
                    type types-sros:admin-state;
                    default "disable";
                    description "Administrative state of Epipe as a NAT outside service";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list nat-outside

            container pbb {
                description "Enter the pbb context";

                leaf force-qtag-forwarding {
                    type boolean;
                    default "false";
                    description "Add an IEEE 802.1q tag after CMAC addresses PBB header";
                }

                leaf local-switch-service-state {
                    type enumeration {
                        enum sap                            { value 0; }
                        enum pbb-tunnel                     { value 1; }
                    }
                    default "sap";
                    description "Endpoint state used to determine PBB-Epipe state";
                }

                container tunnel {
                    presence "Enable the tunnel context";
                    description "Enable the tunnel context";

                    leaf backbone-vpls-service-name {
                        type leafref {
                            path "../../../../vpls/service-name";
                        }
                        sros-ext:immutable;
                        mandatory true;
                        description "Backbone VPLS service";
                    }

                    leaf isid {
                        type types-services:isid;
                        sros-ext:immutable;
                        mandatory true;
                        description "Service instance ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice backbone-mac {
                        mandatory true;
                        case backbone-dest-mac {

                            leaf backbone-dest-mac {
                                type types-sros:mac-unicast-address-no-zero;
                                description "Backbone Destination MAC address";
                            }

                        }
                        case backbone-dest-mac-name {

                            leaf backbone-dest-mac-name {
                                type leafref {
                                    path "../../../../pbb/mac/name";
                                }
                                description "Backbone destination MAC name for PBB packets";
                            }

                        }
                    }
                } // container tunnel

            } // container pbb

            list spoke-sdp {
                key "sdp-bind-id";
                description "Enter the spoke-sdp list instance";

                leaf sdp-bind-id {
                    type types-services:sdp-bind-id;
                    description "SDP binding ID";
                }

                leaf description {
                    type types-sros:description;
                    description "Text description";
                }

                leaf admin-state {
                    type types-sros:admin-state;
                    default "enable";
                    description "Administrative state of the SDP binding to the service";
                }

                leaf adv-service-mtu {
                    type int32 {
                        range "0..9782";
                    }
                    description "Service MTU used in signaling";
                }

                leaf vlan-vc-tag {
                    type types-services:vlan-vc-tag;
                    description "SDP bind VC tag";
                }

                leaf collect-stats {
                    type boolean;
                    default "false";
                    description "Allow agent to collect accounting statistics";
                }

                leaf accounting-policy {
                    type leafref {
                        path "../../../../log/accounting-policy/policy-id";
                    }
                    description "Policy to collect accounting statistics";
                }

                leaf control-word {
                    type boolean;
                    default "false";
                    description "Use the control word as preferred";
                }

                leaf force-vc-forwarding {
                    type enumeration {
                        enum vlan                           { value 1; }
                        enum qinq-c-tag-c-tag               { value 2; }
                        enum qinq-s-tag-c-tag               { value 3; }
                    }
                    description "VC forwarding action";
                }

                leaf bandwidth {
                    type types-services:sdp-bind-bandwidth;
                    units "kilobps";
                    default "0";
                    description "Bandwidth that is reserved for this SDP binding";
                }

                leaf app-profile {
                    type leafref {
                        path "../../../../application-assurance/group/partition/policy/app-profile/app-profile-name";
                    }
                    description "Application profile name for this SDP";
                }

                leaf bfd-template {
                    status obsolete;
                    type leafref {
                        path "../../../../bfd/bfd-template/name";
                    }
                    description "BFD template associated with SDP binding";
                }

                leaf vc-type {
                    type types-services:epipe-sdp-bind-vc-type;
                    sros-ext:auto-restart-to-modify;
                    default "ether";
                    description "Virtual circuit type associated with the SDP binding";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice label {
                    case entropy {

                        leaf entropy-label {
                            type empty;
                            description "Enable the use of entropy labels for spoke SDPs";
                        }

                    }
                    case hash {

                        container hash-label {
                            presence "Enable the hash-label context";
                            description "Enable the hash-label context";

                            leaf signal-capability {
                                type empty;
                                description "Signal hash label capability to the remote PE";
                            }

                        } // container hash-label

                    }
                }
                choice oper-group-association {
                    case oper-group {

                        leaf oper-group {
                            type leafref {
                                path "../../../oper-group/name";
                            }
                            description "Operational group identifier";
                        }

                    }
                    case monitor-oper-group {

                        leaf monitor-oper-group {
                            type leafref {
                                path "../../../oper-group/name";
                            }
                            description "Operational group that affects state of the SDP bind";
                        }

                    }
                }
                container ingress {
                    description "Enter the ingress context";

                    leaf vc-label {
                        type types-services:ingress-vc-label;
                        sros-ext:auto-restart-to-modify;
                        description "Ingress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container fp-redirect-group {
                                description "Enter the fp-redirect-group context";

                                leaf group-name {
                                    type leafref {
                                        path "../../../../../../../../qos/queue-group-templates/ingress/queue-group/ingress-queue-group-name";
                                    }
                                    description "Name of the forwarding plane queue group template";
                                }

                                leaf instance {
                                    type types-services:qos-qgrp-instance-id;
                                    description "Instance of FP ingress queue group for the SDP binding";
                                }

                            } // container fp-redirect-group

                        } // container network

                    } // container qos

                    container l2tpv3 {
                        description "Enter the l2tpv3 context";

                        container cookie {
                            description "Enter the cookie context";

                            leaf cookie1 {
                                type types-services:cookie-value;
                                description "Value of cookie-1 for the tunnel";
                            }

                            leaf cookie2 {
                                type types-services:cookie-value;
                                description "Value of cookie-1 for the tunnel";
                            }

                        } // container cookie

                    } // container l2tpv3

                } // container ingress

                container egress {
                    description "Enter the egress context";

                    leaf vc-label {
                        type types-services:egress-vc-label;
                        sros-ext:auto-restart-to-modify;
                        description "Egress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container port-redirect-group {
                                description "Enter the port-redirect-group context";

                                leaf group-name {
                                    type leafref {
                                        path "../../../../../../../../qos/queue-group-templates/egress/queue-group/egress-queue-group-name";
                                    }
                                    description "Name of the egress port queue group";
                                }

                                leaf instance {
                                    type types-services:qos-qgrp-instance-id;
                                    description "Queue-group instance ID";
                                }

                            } // container port-redirect-group

                        } // container network

                    } // container qos

                    container l2tpv3 {
                        description "Enter the l2tpv3 context";

                        leaf cookie {
                            type types-services:cookie-value;
                            description "Cookie parameters";
                        }

                    } // container l2tpv3

                } // container egress

                container eth-cfm {
                    description "Enter the eth-cfm context";

                    leaf collect-lmm-stats {
                        type boolean;
                        default "false";
                        description "Collect statistics for loss measurement message tests";
                    }

                    leaf-list squelch-ingress-levels {
                        type uint32 {
                            range "0..7";
                        }
                        max-elements 8;
                        description "Levels for which ETH-CFM packets are silently discarded";
                    }

                    leaf-list squelch-ingress-ctag-levels {
                        type uint32 {
                            range "0..7";
                        }
                        max-elements 8;
                        description "Squelch levels using additional VLAN C-Tag space";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container collect-lmm-fc-stats {
                        description "Enter the collect-lmm-fc-stats context";

                        leaf-list fc {
                            type types-eth-cfm:fc-type;
                            max-elements 8;
                            description "Forwarding class name for profile-unaware counter";
                        }

                        leaf-list fc-in-profile {
                            type types-eth-cfm:fc-type;
                            max-elements 8;
                            description "Forwarding class name for profile-aware counter";
                        }

                    } // container collect-lmm-fc-stats

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf primary-vlan {
                            type boolean;
                            sros-ext:immutable;
                            default "false";
                            description "MEP provisioned using MA primary VLAN ID";
                        }

                        leaf direction {
                            type types-eth-cfm:mp-direction;
                            sros-ext:immutable;
                            description "Direction the MEP faces";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf cfm-vlan-tag {
                            type types-sros:one-or-two-vlan-tags;
                            description "VLAN tags to apply to CFM PDUs for egress processing";
                        }

                        leaf low-priority-defect {
                            type types-eth-cfm:lowest-alarm-priority;
                            default "mac-rem-err-xcon";
                            description "Lowest priority defect allowed to generate fault alarm";
                        }

                        leaf fault-propagation {
                            type types-eth-cfm:fault-propagation-type;
                            description "Fault propagation for the MEP";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container ais {
                            presence "Enable the ais context";
                            description "Enable the ais context";

                            leaf-list client-meg-level {
                                type uint32 {
                                    range "1..7";
                                }
                                max-elements 7;
                                description "Client MEG level for AIS message generation";
                            }

                            leaf interface-support {
                                type boolean;
                                default "false";
                                description "Enable generation of AIS PDUs based on endpoint state";
                            }

                            leaf interval {
                                type uint32 {
                                    range "1|60";
                                }
                                units "seconds";
                                default "1";
                                description "Transmission interval for AIS messages";
                            }

                            leaf low-priority-defect {
                                type enumeration {
                                    enum all-def                        { value 1; }
                                    enum mac-rem-err-xcon               { value 2; }
                                }
                                default "all-def";
                                description "Lowest priority defect allowed to generate fault alarm";
                            }

                            leaf priority {
                                type types-eth-cfm:frame-priority;
                                default "7";
                                description "Priority of the AIS messages generated by the node";
                            }

                        } // container ais

                        container csf {
                            presence "Enable the csf context";
                            description "Enable the csf context";

                            leaf multiplier {
                                type decimal64 {
                                    range "0.0|2.0..30.0";
                                    fraction-digits 1;
                                }
                                default "3.5";
                                description "Multiplication factor used to clear the CSF condition";
                            }

                        } // container csf

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                    list mip {
                        key "primary-vlan";
                        description "Enter the mip list instance";

                        leaf primary-vlan {
                            type types-eth-cfm:vlan-id-or-none;
                            description "VLAN ID to which the MIP is attached";
                        }

                        leaf mac-address {
                            type types-sros:mac-unicast-address-no-zero;
                            description "MAC address of the MIP";
                        }

                        leaf cfm-vlan-tag {
                            type types-sros:one-or-two-vlan-tags;
                            description "VLAN tags to apply to CFM PDUs for egress processing";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mip

                } // container eth-cfm

                container endpoint {
                    description "Enter the endpoint context";

                    leaf name {
                        type leafref {
                            path "../../../../epipe[service-name=current()/../../../service-name]/endpoint/name";
                        }
                        sros-ext:auto-restart-to-modify;
                        description "Service endpoint name";
                    }

                    leaf precedence {
                        type types-services:sdp-precedence;
                        default "4";
                        description "Precedence when multiple SDP binds are on one endpoint";
                    }

                    leaf icb {
                        type boolean;
                        sros-ext:auto-restart-to-modify;
                        default "false";
                        description "Bind SDP as type Inter-Chassis Backup (ICB)";
                    }

                } // container endpoint

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                        case cfm {

                            container eth-cfm-monitoring {
                                presence "Enable the eth-cfm-monitoring context";
                                description "Enable the eth-cfm-monitoring context";

                                leaf aggregate {
                                    type empty;
                                    description "Apply rate limit to the sum of the per peer packet rates";
                                }

                                leaf car {
                                    type empty;
                                    description "Ignore Ethernet CFM packets when enforcing overall rate";
                                }

                            } // container eth-cfm-monitoring

                        }
                    }
                } // container cpu-protection

                container pw-status {
                    description "Enter the pw-status context";

                    leaf signaling {
                        type boolean;
                        default "true";
                        description "Allow SDP binding to support pseudowire status signaling";
                    }

                    choice sdp-bind-pw-status {
                        case block-on-peer-fault {

                            leaf block-on-peer-fault {
                                type boolean;
                                default "false";
                                description "Block transmit direction of PW based on status code";
                            }

                        }
                        case standby-signaling-slave {

                            leaf standby-signaling-slave {
                                type boolean;
                                default "false";
                                description "Block spoke transmission based on PW standby status";
                            }

                        }
                    }
                } // container pw-status

                container aarp {
                    presence "Enable the aarp context";
                    description "Enable the aarp context";

                    leaf id {
                        type leafref {
                            path "../../../../../application-assurance/aarp/aarp-id";
                        }
                        description "AARP instance ID";
                    }

                    leaf type {
                        type types-services:dual-homing-bsx-aarp-service-ref-type;
                        description "Role referenced by the AARP";
                    }

                } // container aarp

                container source-bmac {
                    description "Enter the source-bmac context";

                    leaf use-sdp-bmac-lsb {
                        type boolean;
                        default "false";
                        description "Allow the spoke SDP to be part of a redundant pseudo-wire within PBB Epipe service";
                    }

                } // container source-bmac

                container bfd-liveness {
                    status obsolete;
                    presence "Enable the bfd-liveness context";
                    description "Enable the bfd-liveness context";

                    leaf encap {
                        status obsolete;
                        type types-services:bfd-encap;
                        default "ipv4";
                        description "BFD encapsulation used on the SDP binding";
                    }

                } // container bfd-liveness

                container bfd {
                    description "Enter the bfd context";

                    leaf bfd-template {
                        type leafref {
                            path "../../../../../bfd/bfd-template/name";
                        }
                        description "BFD template associated with the SDP binding";
                    }

                    leaf failure-action {
                        type types-services:sbind-bfd-fail-action;
                        default "none";
                        description "VCCV BFD action taken on the SDP binding";
                    }

                    leaf wait-for-up-timer {
                        type uint32 {
                            range "1..60";
                        }
                        units "seconds";
                        description "Time waited for BFD up status";
                    }

                    container bfd-liveness {
                        presence "Enable the bfd-liveness context";
                        description "Enable the bfd-liveness context";

                        leaf encap {
                            type types-services:bfd-encap;
                            default "ipv4";
                            description "BFD encapsulation used on the SDP binding";
                        }

                    } // container bfd-liveness

                } // container bfd

                container transit-policy {
                    presence "Enable the transit-policy context";
                    description "Enable the transit-policy context";

                    choice transit-policy {
                        mandatory true;
                        case prefix {

                            leaf prefix {
                                type leafref {
                                    path "../../../../../application-assurance/group/partition/transit-prefix-policy/prefix-policy-id";
                                }
                                sros-ext:immutable;
                                description "IP prefix policy ID";
                            }

                        }
                        case ip {

                            leaf ip {
                                type leafref {
                                    path "../../../../../application-assurance/group/partition/transit-ip-policy/ip-policy-id";
                                }
                                sros-ext:immutable;
                                description "IP transit policy ID";
                            }

                        }
                    }
                } // container transit-policy

            } // list spoke-sdp


            list bgp-mh-site {
                key "site-name";
                max-elements 1;
                description "Enter the bgp-mh-site list instance";

                leaf site-name {
                    type types-sros:named-item;
                    description "Name for the specific site";
                }

                leaf admin-state {
                    type types-sros:admin-state;
                    default "disable";
                    description "Administrative state of the site";
                }

                leaf id {
                    type types-services:site-id;
                    sros-ext:auto-restart-to-modify;
                    description "Site ID for the service";
                }

                leaf sap {
                    type types-sros:sap;
                    sros-ext:auto-restart-to-modify;
                    description "SAP to be associated with this site";
                }

                leaf boot-timer {
                    type types-services:site-boot-timer;
                    units "seconds";
                    description "Wait time after reboot to run the DF election algorithm";
                }

                leaf activation-timer {
                    type types-services:site-activation-timer;
                    units "seconds";
                    description "Time to wait for BGP updates from remote PEs";
                }

                leaf preference {
                    type uint32 {
                        range "1..65535";
                    }
                    description "Preference to advertise in NLRI L2 extended community";
                }

                leaf min-down-timer {
                    type types-services:site-min-down-timer;
                    units "seconds";
                    description "Minimum down time when site goes operationally down";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list bgp-mh-site

            list sap {
                key "sap-id";
                max-elements 255;
                description "Enter the sap list instance";

                leaf sap-id {
                    type types-sros:sap;
                    description "SAP ID";
                }

                leaf description {
                    type types-sros:long-description;
                    description "Text description";
                }

                leaf admin-state {
                    type types-sros:admin-state;
                    default "enable";
                    description "Administrative state of the SAP";
                }

                leaf accounting-policy {
                    type leafref {
                        path "../../../../log/accounting-policy/policy-id";
                    }
                    description "Accounting policy";
                }

                leaf app-profile {
                    type leafref {
                        path "../../../../application-assurance/group/partition/policy/app-profile/app-profile-name";
                    }
                    description "Application profile name";
                }

                leaf bandwidth {
                    type types-services:sap-bandwidth;
                    units "kilobps";
                    description "SAP bandwidth";
                }

                leaf cflowd {
                    type boolean;
                    default "false";
                    description "Enable Cflowd collection and analysis on this SAP";
                }

                leaf collect-stats {
                    type boolean;
                    default "false";
                    description "Collect accounting statistics";
                }

                leaf dist-cpu-protection {
                    type leafref {
                        path "../../../../system/security/dist-cpu-protection/policy/policy-name";
                    }
                    description "Distributed CPU protection policy for SAP";
                }

                leaf ignore-oper-down {
                    type boolean;
                    default "false";
                    description "Ignore operational down state of the SAP on SAP failure";
                }

                leaf multi-service-site {
                    type leafref {
                        path "../../../customer/multi-service-site/multi-service-site-name";
                    }
                    description "Multi service site name";
                }

                leaf endpoint {
                    type leafref {
                        path "../../endpoint/name";
                    }
                    sros-ext:auto-restart-to-modify;
                    description "Name of the endpoint";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice oper-group-association {
                    case oper-group {

                        leaf oper-group {
                            type leafref {
                                path "../../../oper-group/name";
                            }
                            description "Operational group";
                        }

                    }
                    case monitor-oper-group {

                        leaf monitor-oper-group {
                            type leafref {
                                path "../../../oper-group/name";
                            }
                            description "Monitor operational group";
                        }

                    }
                }
                container qtag-normalization {
                    presence "Enable the qtag-normalization context";
                    description "Enable the qtag-normalization context";

                    choice q-tag {
                        case single-tag {

                            container single-tag {
                                description "Enter the single-tag context";

                                leaf tag {
                                    type int32 {
                                        range "1..4094";
                                    }
                                    sros-ext:immutable;
                                    description "Tag normalization value";
                                }

                            } // container single-tag

                        }
                        case double-tag {

                            container double-tag {
                                description "Enter the double-tag context";

                                leaf c-tag {
                                    type int32 {
                                        range "1..4094";
                                    }
                                    sros-ext:immutable;
                                    description "C-tag value used for the tag normalization";
                                }

                                leaf s-tag {
                                    type int32 {
                                        range "1..4094";
                                    }
                                    sros-ext:immutable;
                                    description "S-tag value used for the tag normalization";
                                }

                            } // container double-tag

                        }
                    }
                } // container qtag-normalization

                container ingress {
                    description "Enter the ingress context";

                    leaf shared-policer {
                        type leafref {
                            path "../../../../../qos/shared-policers/policer/shared-policer-name";
                        }
                        description "Ingress shared policer";
                    }

                    container qos {
                        description "Enter the qos context";

                        leaf match-qinq-dot1p {
                            type enumeration {
                                enum top                            { value 2; }
                                enum bottom                         { value 3; }
                            }
                            description "Ingress match QinQ Dot1p";
                        }

                        container sap-ingress {
                            description "Enter the sap-ingress context";

                            leaf policy-name {
                                type leafref {
                                    path "../../../../../../../qos/sap-ingress/sap-ingress-policy-name";
                                }
                                description "Policy ID";
                            }

                            leaf queuing-type {
                                type types-services:services-sap-queuing-type;
                                description "Queuing type";
                            }

                            container fp-redirect-group {
                                description "Enter the fp-redirect-group context";

                                leaf group-name {
                                    type leafref {
                                        path "../../../../../../../../qos/queue-group-templates/ingress/queue-group/ingress-queue-group-name";
                                    }
                                    description "Queue group template name created on forwarding plane";
                                }

                                leaf instance {
                                    type types-services:qos-qgrp-instance-id;
                                    description "Queue group instance";
                                }

                            } // container fp-redirect-group

                            container overrides {
                                description "Enter the overrides context";

                                container ip-criteria {
                                    description "Enter the ip-criteria context";

                                    leaf activate-entry-tag {
                                        type int32 {
                                            range "1..255";
                                        }
                                        description "Tag ID activated for IPv4 criteria";
                                    }

                                } // container ip-criteria

                                container ipv6-criteria {
                                    description "Enter the ipv6-criteria context";

                                    leaf activate-entry-tag {
                                        type int32 {
                                            range "1..255";
                                        }
                                        description "Tag ID activated for IPv6 criteria";
                                    }

                                } // container ipv6-criteria

                                list queue {
                                    key "queue-id";
                                    description "Enter the queue list instance";

                                    leaf queue-id {
                                        type leafref {
                                            path "../../../../../../../../../qos/sap-ingress[sap-ingress-policy-name=current()/../../../policy-name]/queue/queue-id";
                                        }
                                        description "Policer unique ID";
                                    }

                                    leaf cbs {
                                        type union {
                                            type uint32 {
                                                range "0..1048576";
                                            }
                                            type enumeration {
                                                enum auto                           { value -1; }
                                            }
                                        }
                                        units "kilobytes";
                                        description "CBS";
                                    }

                                    leaf mbs {
                                        type union {
                                            type types-qos:bytes {
                                                range "0..1073741824";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                    } // container monitor-queue-depth

                                } // list queue

                                list policer {
                                    key "policer-id";
                                    description "Enter the policer list instance";

                                    leaf policer-id {
                                        type leafref {
                                            path "../../../../../../../../../qos/sap-ingress[sap-ingress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:ingress-per-packet-offset-override;
                                        description "Packet size modification for policing information";
                                    }

                                    leaf stat-mode {
                                        type types-qos:ingress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                            } // container overrides

                        } // container sap-ingress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qtag-manipulation {
                        description "Enter the qtag-manipulation context";

                        choice tags {
                            case push-dot1q-vlan {

                                leaf push-dot1q-vlan {
                                    type types-services:qtag-manipulation-info;
                                    description "VLAN translation information";
                                }

                            }
                            case push-qinq-vlan {

                                leaf s-tag {
                                    type int32 {
                                        range "0..4094";
                                    }
                                    description "Outer ingress VLN translation for two service delimiting VLAN values";
                                }

                                leaf c-tag {
                                    type types-services:qinq-vlan-translation-ctag;
                                    description "Inner ingress VLAN translation for two service delimiting VLAN values";
                                }

                            }
                        }
                    } // container qtag-manipulation

                    container vlan-manipulation {
                        description "Enter the vlan-manipulation context";

                        leaf action {
                            type types-services:vlan-manipulation-ingress-action-type;
                            description "Action to manipulate the VLAN tags of the packets";
                        }

                        leaf outer-tag {
                            type types-services:vlan-manipulate-ingress-vlan-type;
                            default "null";
                            description "Outer VLAN tag to apply";
                        }

                        leaf inner-tag {
                            type types-services:vlan-manipulate-ingress-vlan-type;
                            default "null";
                            description "Inner VLAN tag to apply in case of QinQ encapsulation";
                        }

                    } // container vlan-manipulation

                    container aggregate-policer {
                        description "Enter the aggregate-policer context";

                        leaf rate {
                            type types-qos:aggr-policer-rate;
                            units "kilobps";
                            default "max";
                            description "Aggregate policer rate";
                        }

                        leaf burst {
                            status obsolete;
                            type types-qos:aggr-policer-burst;
                            default "default";
                            description "Aggregate policer burst";
                        }

                        leaf cir {
                            type types-qos:aggr-policer-cir;
                            units "kilobps";
                            description "Aggregate policer CIR";
                        }

                        leaf cbs {
                            type types-qos:aggr-policer-cbs;
                            units "kilobytes";
                            description "Aggregate policer CBS";
                        }

                        leaf mbs {
                            type types-qos:aggr-policer-mbs;
                            default "default";
                            description "Aggregate policer mbs";
                        }

                        leaf algorithm-type {
                            type enumeration {
                                enum trtcm-ds {
                                    value 1;
                                    description "Use the TRTCM non-coupled mode";
                                }
                                enum trtcm-ds-coupled {
                                    value 2;
                                    description "Use the TRTCM coupled mode";
                                }
                            }
                            default "trtcm-ds-coupled";
                            description "Policer algorithm type";
                        }

                    } // container aggregate-policer

                } // container ingress

                container egress {
                    description "Enter the egress context";

                    choice agg-rate-or-percent-agg-rate {
                        default "agg-rate";
                        case agg-rate {

                            container agg-rate {
                                description "Enter the agg-rate context";

                                leaf limit-unused-bandwidth {
                                    type boolean;
                                    default "false";
                                    description "Enable aggregate rate overrun protection";
                                }

                                leaf rate {
                                    type types-services:agg-rate-rate;
                                    units "kilobps";
                                    description "Enforced aggregate rate for all queues";
                                }

                                leaf queue-frame-based-accounting {
                                    type boolean;
                                    default "false";
                                    description "Enable frame based accounting on policers and queues";
                                }

                                leaf cir {
                                    type union {
                                        type int32 {
                                            range "0..400000000";
                                        }
                                        type enumeration {
                                            enum max                            { value -1; }
                                        }
                                    }
                                    units "kilobps";
                                    default "0";
                                    description "Administrative CIR";
                                }

                                leaf burst-limit {
                                    type union {
                                        type types-qos:bytes {
                                            range "1..14000000";
                                        }
                                        type enumeration {
                                            enum auto                           { value -1; }
                                        }
                                    }
                                    default "auto";
                                    description "Shaping burst size when an aggregate shaper is used";
                                }

                                leaf adaptation-rule {
                                    type types-qos:adaptation-rule;
                                    default "closest";
                                    description "Adaptation rule to compute the operational PIR value when an aggregate shaper is used";
                                }

                            } // container agg-rate

                        }
                        case percent-agg-rate {

                            container percent-agg-rate {
                                description "Enter the percent-agg-rate context";

                                leaf pir {
                                    type decimal64 {
                                        range "0.01..100.00";
                                        fraction-digits 2;
                                    }
                                    description "PIR percent rate";
                                }

                                leaf cir {
                                    type decimal64 {
                                        range "0.00..100.00";
                                        fraction-digits 2;
                                    }
                                    description "CIR percent rate";
                                }

                            } // container percent-agg-rate

                        }
                    }
                    container qos {
                        description "Enter the qos context";

                        leaf qinq-mark-top-only {
                            type boolean;
                            default "false";
                            description "Mark top Q-tags";
                        }

                        leaf burst-limit {
                            type types-qos:vlan-qos-burst-limit;
                            description "Maximum traffic burst size for SAP egress";
                        }

                        leaf latency-budget {
                            type uint32 {
                                range "1..1000000";
                            }
                            units "microseconds";
                            description "SAP egress latency budget";
                        }

                        container sap-egress {
                            description "Enter the sap-egress context";

                            leaf policy-name {
                                type leafref {
                                    path "../../../../../../../qos/sap-egress/sap-egress-policy-name";
                                }
                                description "Policy ID to associate with SAP for mirrored service";
                            }

                            container port-redirect-group {
                                description "Enter the port-redirect-group context";

                                leaf group-name {
                                    type leafref {
                                        path "../../../../../../../../qos/queue-group-templates/egress/queue-group/egress-queue-group-name";
                                    }
                                    description "Name of the queue group redirect list policy";
                                }

                                leaf instance {
                                    type types-services:qos-qgrp-instance-id;
                                    description "Instance of port queue group";
                                }

                            } // container port-redirect-group

                            container overrides {
                                description "Enter the overrides context";

                                leaf hs-secondary-shaper {
                                    type types-sros:named-item;
                                    description "HS Secondary Shaper";
                                }

                                list queue {
                                    key "queue-id";
                                    description "Enter the queue list instance";

                                    leaf queue-id {
                                        type leafref {
                                            path "../../../../../../../../../qos/sap-egress[sap-egress-policy-name=current()/../../../policy-name]/queue/queue-id";
                                        }
                                        description "Policer unique ID";
                                    }

                                    leaf avg-frame-overhead {
                                        type decimal64 {
                                            range "0.00..100.00";
                                            fraction-digits 2;
                                        }
                                        description "Average packet-to-frame encapsulation overhead";
                                    }

                                    leaf burst-limit {
                                        type union {
                                            type types-qos:bytes {
                                                range "1..14000000";
                                            }
                                            type enumeration {
                                                enum auto                           { value -1; }
                                            }
                                        }
                                        description "Explicit shaping burst size for the queue";
                                    }

                                    leaf cbs {
                                        type union {
                                            type uint32 {
                                                range "0..1048576";
                                            }
                                            type enumeration {
                                                enum auto                           { value -1; }
                                            }
                                        }
                                        units "kilobytes";
                                        description "CBS";
                                    }

                                    leaf mbs {
                                        type union {
                                            type types-qos:bytes {
                                                range "0..1073741824";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf hs-wrr-weight {
                                        type types-qos:hs-wrr-weight-override;
                                        default "1";
                                        description "WRR weight to parent with the queue into the scheduler";
                                    }

                                    leaf hs-class-weight {
                                        type types-qos:hs-class-weight-override;
                                        description "Class weight override for the queue";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                        leaf violation-threshold {
                                            type decimal64 {
                                                range "0.01..99.99";
                                                fraction-digits 2;
                                            }
                                            description "Threshold for queue depth before violation is raised";
                                        }

                                    } // container monitor-queue-depth

                                    container hs-wred-queue {
                                        description "Enter the hs-wred-queue context";

                                        leaf policy {
                                            type leafref {
                                                path "../../../../../../../../../../qos/slope-policy/slope-policy-name";
                                            }
                                            description "Slope policy applied to the HSQ queue group queue";
                                        }

                                    } // container hs-wred-queue

                                } // list queue

                                list policer {
                                    key "policer-id";
                                    description "Enter the policer list instance";

                                    leaf policer-id {
                                        type leafref {
                                            path "../../../../../../../../../qos/sap-egress[sap-egress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:egress-per-packet-offset-override;
                                        description "Packet size modification for policing information";
                                    }

                                    leaf stat-mode {
                                        type types-qos:egress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                                list hs-wrr-group {
                                    key "group-id";
                                    description "Enter the hs-wrr-group list instance";

                                    leaf group-id {
                                        type leafref {
                                            path "../../../../../../../../../qos/sap-egress[sap-egress-policy-name=current()/../../../policy-name]/hs-wrr-group/group-id";
                                        }
                                        description "HS WRR group identifier";
                                    }

                                    leaf hs-class-weight {
                                        type types-qos:hs-class-weight-override;
                                        description "Class weight override of the WRR group";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice rate-or-percent-rate {
                                        case rate {

                                            leaf rate {
                                                type union {
                                                    type uint32 {
                                                        range "1..2000000000";
                                                    }
                                                    type enumeration {
                                                        enum max                            { value -1; }
                                                    }
                                                }
                                                units "kilobps";
                                                description "Scheduling rate override applied to the HS WRR group";
                                            }

                                        }
                                        case percent-rate {

                                            leaf percent-rate {
                                                type decimal64 {
                                                    range "0.01..100.00";
                                                    fraction-digits 2;
                                                }
                                                description "Percent rate override applied to the HS WRR group";
                                            }

                                        }
                                    }
                                } // list hs-wrr-group

                            } // container overrides

                        } // container sap-egress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                        container vlan-qos-policy {
                            description "Enter the vlan-qos-policy context";

                            leaf policy-name {
                                type leafref {
                                    path "../../../../../../../qos/vlan-qos-policy/vlan-qos-policy-name";
                                }
                                description "Egress vlan-qos-policy name";
                            }

                            leaf port-redirect {
                                type boolean;
                                default "false";
                                description "Enable egress vlan-qos-policy port-redirect";
                            }

                        } // container vlan-qos-policy

                        container egress-remark-policy {
                            description "Enter the egress-remark-policy context";

                            leaf policy-name {
                                type leafref {
                                    path "../../../../../../../qos/egress-remark-policy/egress-remark-policy-name";
                                }
                                description "Egress-remark-policy name";
                            }

                        } // container egress-remark-policy

                    } // container qos

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container vlan-manipulation {
                        description "Enter the vlan-manipulation context";

                        leaf action {
                            type types-services:vlan-manipulation-egress-action-type;
                            description "Action to manipulate the VLAN tags of the packets";
                        }

                        leaf tag {
                            type types-services:vlan-manipulation-egress-vlan-type;
                            default "null";
                            description "VLAN tag to be applied by action";
                        }

                    } // container vlan-manipulation

                    container virtual-port {
                        description "Enter the virtual-port context";

                        leaf vport-name {
                            type leafref {
                                path "../../../../../../port/ethernet/access/egress/virtual-port/vport-name";
                            }
                            description "Virtual port assigned to the SAP";
                        }

                    } // container virtual-port

                } // container egress

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                        case cfm {

                            container eth-cfm-monitoring {
                                presence "Enable the eth-cfm-monitoring context";
                                description "Enable the eth-cfm-monitoring context";

                                leaf aggregate {
                                    type empty;
                                    description "Apply rate limit to the sum of the per peer packet rates";
                                }

                                leaf car {
                                    type empty;
                                    description "Ignore Ethernet CFM packets when enforcing overall rate";
                                }

                            } // container eth-cfm-monitoring

                        }
                    }
                } // container cpu-protection

                container lag {
                    description "Enter the lag context";

                    leaf link-map-profile {
                        type types-services:link-map-profile-id;
                        description "LAG link map profile";
                    }

                    container per-link-hash {
                        description "Enter the per-link-hash context";

                        leaf class {
                            type types-services:sap-lag-per-link-hash-class;
                            default "1";
                            description "Class used on LAG egress using weighted per-link-hash";
                        }

                        leaf weight {
                            type types-services:sap-lag-per-link-hash-weight;
                            default "1";
                            description "Weight used on LAG egress using weighted per-link-hash";
                        }

                    } // container per-link-hash

                } // container lag

                container aarp {
                    presence "Enable the aarp context";
                    description "Enable the aarp context";

                    leaf id {
                        type leafref {
                            path "../../../../../application-assurance/aarp/aarp-id";
                        }
                        description "AARP instance ID";
                    }

                    leaf type {
                        type types-services:dual-homing-bsx-aarp-service-ref-type;
                        description "Role referenced by the AARP";
                    }

                } // container aarp

                container transit-policy {
                    presence "Enable the transit-policy context";
                    description "Enable the transit-policy context";

                    choice transit-policy {
                        mandatory true;
                        case prefix {

                            leaf prefix {
                                type leafref {
                                    path "../../../../../application-assurance/group/partition/transit-prefix-policy/prefix-policy-id";
                                }
                                sros-ext:immutable;
                                description "IP prefix policy ID";
                            }

                        }
                        case ip {

                            leaf ip {
                                type leafref {
                                    path "../../../../../application-assurance/group/partition/transit-ip-policy/ip-policy-id";
                                }
                                sros-ext:immutable;
                                description "IP transit policy ID";
                            }

                        }
                    }
                } // container transit-policy


                container l2tpv3-session {
                    presence "Enable the l2tpv3-session context";
                    description "Enable the l2tpv3-session context";

                    leaf admin-state {
                        type types-sros:admin-state;
                        default "disable";
                        description "Administrative state of the session for the service";
                    }

                    leaf vc-id {
                        type types-services:vc-id;
                        sros-ext:auto-restart-to-modify;
                        description "VC ID for the L2TPv3 session";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                    container pseudo-wire {
                        sros-ext:auto-restart-to-modify;
                        description "Enter the pseudo-wire context";

                        choice type {
                            case ethernet {

                                leaf ethernet {
                                    type empty;
                                    sros-ext:auto-restart-to-modify;
                                    description "Enable the Ethernet PW-type for the L2TPv3 session";
                                }

                            }
                            case ethernet-vlan-id {

                                leaf ethernet-vlan-id {
                                    type int32 {
                                        range "0..4095";
                                    }
                                    sros-ext:auto-restart-to-modify;
                                    description "Ethernet-VLAN PW-type ID for the L2TPv3 session";
                                }

                            }
                        }
                    } // container pseudo-wire

                    container router {
                        sros-ext:auto-restart-to-modify;
                        description "Enter the router context";

                        leaf group {
                            type types-sros:named-item;
                            sros-ext:auto-restart-to-modify;
                            description "Tunnel group name";
                        }

                        leaf router-instance {
                            type types-sros:router-instance-base-vprn-loose;
                            sros-ext:auto-restart-to-modify;
                            description "Router name used to identify the router instance";
                        }

                    } // container router

                } // container l2tpv3-session

                container eth-cfm {
                    description "Enter the eth-cfm context";

                    leaf collect-lmm-stats {
                        type boolean;
                        default "false";
                        description "Collect statistics for loss measurement message tests";
                    }

                    leaf-list squelch-ingress-levels {
                        type uint32 {
                            range "0..7";
                        }
                        max-elements 8;
                        description "Levels for which ETH-CFM packets are silently discarded";
                    }

                    leaf-list squelch-ingress-ctag-levels {
                        type uint32 {
                            range "0..7";
                        }
                        max-elements 8;
                        description "Squelch levels using additional VLAN C-Tag space";
                    }

                    leaf ais {
                        type boolean;
                        default "false";
                        description "Enable the generation and the reception of AIS messages";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container collect-lmm-fc-stats {
                        description "Enter the collect-lmm-fc-stats context";

                        leaf-list fc {
                            type types-eth-cfm:fc-type;
                            max-elements 8;
                            description "Forwarding class name for profile-unaware counter";
                        }

                        leaf-list fc-in-profile {
                            type types-eth-cfm:fc-type;
                            max-elements 8;
                            description "Forwarding class name for profile-aware counter";
                        }

                    } // container collect-lmm-fc-stats

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf primary-vlan {
                            type boolean;
                            sros-ext:immutable;
                            default "false";
                            description "MEP provisioned using MA primary VLAN ID";
                        }

                        leaf cp-vlan-tag {
                            type types-sros:vlan-id;
                            description "ETH-CFM VLAN tag for egress processing on a CP SAP";
                        }

                        leaf direction {
                            type types-eth-cfm:mp-direction;
                            sros-ext:immutable;
                            description "Direction the MEP faces";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf cfm-vlan-tag {
                            type types-sros:one-or-two-vlan-tags;
                            description "VLAN tags to apply to CFM PDUs for egress processing";
                        }

                        leaf low-priority-defect {
                            type types-eth-cfm:lowest-alarm-priority;
                            default "mac-rem-err-xcon";
                            description "Lowest priority defect allowed to generate fault alarm";
                        }

                        leaf fault-propagation {
                            type types-eth-cfm:fault-propagation-type;
                            description "Fault propagation for the MEP";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf monitor-oper-group {
                            type leafref {
                                path "../../../../../oper-group/name";
                            }
                            description "Operational group to monitor";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container ais {
                            presence "Enable the ais context";
                            description "Enable the ais context";

                            leaf-list client-meg-level {
                                type uint32 {
                                    range "1..7";
                                }
                                max-elements 7;
                                description "Client MEG level for AIS message generation";
                            }

                            leaf interface-support {
                                type boolean;
                                default "false";
                                description "Enable generation of AIS PDUs based on endpoint state";
                            }

                            leaf interval {
                                type uint32 {
                                    range "1|60";
                                }
                                units "seconds";
                                default "1";
                                description "Transmission interval for AIS messages";
                            }

                            leaf low-priority-defect {
                                type enumeration {
                                    enum all-def                        { value 1; }
                                    enum mac-rem-err-xcon               { value 2; }
                                }
                                default "all-def";
                                description "Lowest priority defect allowed to generate fault alarm";
                            }

                            leaf priority {
                                type types-eth-cfm:frame-priority;
                                default "7";
                                description "Priority of the AIS messages generated by the node";
                            }

                        } // container ais

                        container csf {
                            presence "Enable the csf context";
                            description "Enable the csf context";

                            leaf multiplier {
                                type decimal64 {
                                    range "0.0|2.0..30.0";
                                    fraction-digits 1;
                                }
                                default "3.5";
                                description "Multiplication factor used to clear the CSF condition";
                            }

                        } // container csf

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                    list mip {
                        key "primary-vlan";
                        description "Enter the mip list instance";

                        leaf primary-vlan {
                            type types-eth-cfm:vlan-id-or-none;
                            description "VLAN ID to which the MIP is attached";
                        }

                        leaf mac-address {
                            type types-sros:mac-unicast-address-no-zero;
                            description "MAC address of the MIP";
                        }

                        leaf cfm-vlan-tag {
                            type types-sros:one-or-two-vlan-tags;
                            description "VLAN tags to apply to CFM PDUs for egress processing";
                        }

                        leaf cp-vlan-tag {
                            type types-sros:vlan-id;
                            description "ETH-CFM VLAN tag for egress processing on a CP SAP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mip

                } // container eth-cfm

                container mc-ring {
                    presence "Enable the mc-ring context";
                    description "Enable the mc-ring context";

                    leaf ring-node {
                        type types-sros:named-item;
                        mandatory true;
                        description "Name for the ring node associated with this SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container mc-ring

                container ethernet {
                    description "Enter the ethernet context";

                    container llf {
                        description "Enter the llf context";

                        leaf admin-state {
                            type types-sros:admin-state;
                            default "disable";
                            description "Administrative state of Link Loss Forwarding";
                        }

                    } // container llf

                } // container ethernet

            } // list sap

            container vxlan {
                description "Enter the vxlan context";

                leaf source-vtep {
                    type types-sros:ip-unicast-address;
                    description "Vxlan source virtual tunnel endpoint information";
                }

                list instance {
                    key "vxlan-instance";
                    max-elements 1;
                    description "Enter the instance list instance";

                    leaf vxlan-instance {
                        type uint32 {
                            range "1";
                        }
                        description "VXLAN instance";
                    }

                    leaf vni {
                        type types-services:vxlan-vni;
                        sros-ext:immutable;
                        mandatory true;
                        description "VNI of the VXLAN";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container egress-vtep {
                        description "Enter the egress-vtep context";

                        leaf ip-address {
                            type types-sros:ip-unicast-address;
                            description "VTEP IP address used when originating VXLAN packets";
                        }

                        leaf oper-group {
                            type leafref {
                                path "../../../../../oper-group/name";
                            }
                            description "Operational group associated with egress VTEP address";
                        }

                    } // container egress-vtep

                } // list instance

            } // container vxlan

            container bgp-evpn {
                presence "Enable the bgp-evpn context";
                description "Enable the bgp-evpn context";

                leaf evi {
                    type types-services:evi;
                    description "EVPN ID";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container local-ac {
                    status obsolete;
                    description "Enter the local-ac context";

                    leaf name {
                        status obsolete;
                        type types-sros:named-item;
                        description "Attachment circuit name";
                    }

                    leaf eth-tag {
                        status obsolete;
                        type types-services:bgp-evpn-ac-eth-tag;
                        description "Ethernet tag of the attachment circuit";
                    }

                } // container local-ac

                container remote-ac {
                    status obsolete;
                    description "Enter the remote-ac context";

                    leaf name {
                        status obsolete;
                        type types-sros:named-item;
                        description "Attachment circuit name";
                    }

                    leaf eth-tag {
                        status obsolete;
                        type types-services:bgp-evpn-ac-eth-tag;
                        description "Ethernet tag of the attachment circuit";
                    }

                } // container remote-ac

                list local-attachment-circuit {
                    key "name";
                    max-elements 2;
                    description "Enter the local-attachment-circuit list instance";

                    leaf name {
                        type types-sros:named-item;
                        description "Attachment circuit name";
                    }

                    leaf endpoint {
                        type leafref {
                            path "../../../endpoint/name";
                        }
                        sros-ext:immutable;
                        description "Endpoint name";
                    }

                    leaf eth-tag {
                        type types-services:bgp-evpn-ac-eth-tag;
                        description "Ethernet tag of the attachment circuit";
                    }

                    leaf bgp {
                        type int32 {
                            range "1..2";
                        }
                        sros-ext:immutable;
                        default "1";
                        description "BGP instance ID";
                    }

                    leaf vlan-signaled-flexible-cross-connect {
                        type boolean;
                        default "false";
                        description "Enable FXC VLAN-signaled mode";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list local-attachment-circuit

                list remote-attachment-circuit {
                    key "name";
                    max-elements 2;
                    description "Enter the remote-attachment-circuit list instance";

                    leaf name {
                        type types-sros:named-item;
                        description "Attachment circuit name";
                    }

                    leaf endpoint {
                        type leafref {
                            path "../../../endpoint/name";
                        }
                        sros-ext:immutable;
                        description "Endpoint name";
                    }

                    leaf eth-tag {
                        type types-services:bgp-evpn-ac-eth-tag;
                        description "Ethernet tag of the attachment circuit";
                    }

                    leaf bgp {
                        type int32 {
                            range "1..2";
                        }
                        sros-ext:immutable;
                        default "1";
                        description "BGP instance ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list remote-attachment-circuit

                list vxlan {
                    key "bgp-instance";
                    description "Enter the vxlan list instance";

                    leaf bgp-instance {
                        type int32 {
                            range "1..2";
                        }
                        description "BGP instance";
                    }

                    leaf vxlan-instance {
                        type leafref {
                            path "../../../vxlan/instance/vxlan-instance";
                        }
                        sros-ext:immutable;
                        mandatory true;
                        description "VXLAN instance";
                    }

                    leaf admin-state {
                        type types-sros:admin-state;
                        default "disable";
                        description "Administrative state of BGP EVPN VXLAN";
                    }

                    leaf send-tunnel-encap {
                        type boolean;
                        sros-ext:auto-restart-to-modify;
                        default "true";
                        description "Send VXLAN value in encapsulation extended community";
                    }

                    leaf ecmp {
                        type types-services:ecmp-value;
                        default "1";
                        description "Maximum ECMP routes information";
                    }

                    leaf evi-three-byte-auto-rt {
                        type boolean;
                        sros-ext:auto-restart-to-modify;
                        default "false";
                        description "Auto-derive the BGP EVPN route target";
                    }

                    leaf default-route-tag {
                        type types-services:one-byte-value;
                        sros-ext:auto-restart-to-modify;
                        description "Default route tag";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list vxlan

                list mpls {
                    key "bgp-instance";
                    description "Enter the mpls list instance";

                    leaf bgp-instance {
                        type int32 {
                            range "1..2";
                        }
                        description "BGP instance";
                    }

                    leaf admin-state {
                        type types-sros:admin-state;
                        default "disable";
                        description "Administrative state of BGP EVPN MPLS";
                    }

                    leaf control-word {
                        type boolean;
                        sros-ext:auto-restart-to-modify;
                        default "false";
                        description "Enable support for control word";
                    }

                    leaf ecmp {
                        type types-services:ecmp-value;
                        default "1";
                        description "Maximum ECMP routes information";
                    }

                    leaf entropy-label {
                        type boolean;
                        default "false";
                        description "Enable use of entropy-labels";
                    }

                    leaf domain-id {
                        type types-services:domain-id;
                        description "Domain ID of received BGP route before readvertisement";
                    }

                    leaf evi-three-byte-auto-rt {
                        type boolean;
                        sros-ext:auto-restart-to-modify;
                        default "false";
                        description "Auto-derive the BGP EVPN route target";
                    }

                    leaf default-route-tag {
                        type types-services:one-byte-value;
                        sros-ext:auto-restart-to-modify;
                        description "Default route tag";
                    }

                    leaf force-vc-forwarding {
                        type enumeration {
                            enum vlan                           { value 1; }
                            enum qinq-c-tag-c-tag               { value 2; }
                            enum qinq-s-tag-c-tag               { value 3; }
                        }
                        description "VC forwarding action";
                    }

                    leaf oper-group {
                        type leafref {
                            path "../../../../oper-group/name";
                        }
                        description "Operational group identifier";
                    }

                    leaf dynamic-egress-label-limit {
                        type boolean;
                        default "false";
                        description "Enables dynamic egress label limit";
                    }

                    leaf mh-mode {
                        type enumeration {
                            enum access                         { value 0; }
                            enum network                        { value 1; }
                        }
                        default "network";
                        description "Multihoming mode";
                    }

                    leaf hash-label {
                        type boolean;
                        default "false";
                        description "Default profile when the CP-provided profile is unknown";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container send-tunnel-encap {
                        description "Enter the send-tunnel-encap context";

                        leaf mpls {
                            type boolean;
                            sros-ext:auto-restart-to-modify;
                            default "true";
                            description "Enable MPLS encapsulation";
                        }

                        leaf mpls-over-udp {
                            type boolean;
                            sros-ext:auto-restart-to-modify;
                            default "false";
                            description "Enable MPLS over UDP encapsulation";
                        }

                    } // container send-tunnel-encap

                    container auto-bind-tunnel {
                        description "Enter the auto-bind-tunnel context";

                        leaf resolution {
                            type types-services:resolve-status;
                            default "none";
                            description "Resolution method for tunnel selection";
                        }

                        leaf enforce-strict-tunnel-tagging {
                            type boolean;
                            default "false";
                            description "Enable/disable enforcement of strict tunnel tagging";
                        }

                        leaf ecmp {
                            type types-router:mpls-ecmp;
                            default "1";
                            description "Maximum ECMP routes information";
                        }

                        leaf enforce-untagged-route {
                            type types-sros:untagged-route-type;
                            default "none";
                            description "Untagged route type enforcement";
                        }

                        leaf allow-flex-algo-fallback {
                            type boolean;
                            default "false";
                            description "Enable flexible algorithm fallback";
                        }

                        leaf weighted-ecmp {
                            type boolean;
                            default "false";
                            description "Allow weighted load balancing";
                        }

                        container resolution-filter {
                            description "Enter the resolution-filter context";

                            leaf bgp {
                                type boolean;
                                default "false";
                                description "Use BGP tunneling for next-hop resolution";
                            }

                            leaf ldp {
                                type boolean;
                                default "false";
                                description "Use LDP tunneling for next-hop resolution";
                            }

                            leaf rsvp {
                                type boolean;
                                default "false";
                                description "Use RSVP tunneling for next-hop resolution";
                            }

                            leaf sr-isis {
                                type boolean;
                                default "false";
                                description "Use IS-IS SR tunneling for next-hop resolution";
                            }

                            leaf sr-ospf {
                                type boolean;
                                default "false";
                                description "Use OSPF SR tunneling for next-hop resolution";
                            }

                            leaf sr-te {
                                type boolean;
                                default "false";
                                description "Use SR-TE tunneling for next-hop resolution";
                            }

                            leaf udp {
                                type boolean;
                                default "false";
                                description "Use MPLS over UDP tunneling for next-hop resolution";
                            }

                            leaf mpls-fwd-policy {
                                type boolean;
                                default "false";
                                description "Use MPLS forwarding policy for next-hop resolution";
                            }

                            leaf sr-policy {
                                type boolean;
                                default "false";
                                description "Use SR policies for next-hop resolution";
                            }

                            leaf rib-api {
                                type boolean;
                                default "false";
                                description "Use RIB API gRPC service for next-hop resolution";
                            }

                            leaf sr-ospf3 {
                                type boolean;
                                default "false";
                                description "Use OSPFv3 SR tunneling for next-hop resolution";
                            }

                        } // container resolution-filter

                    } // container auto-bind-tunnel

                    container route-next-hop {
                        description "Enter the route-next-hop context";

                        choice tag {
                            default "ipv4";
                            case ipv4 {

                                leaf system-ipv4 {
                                    type empty;
                                    sros-ext:auto-restart-to-modify;
                                    description "System IPv4 address for service EVPN route next hop";
                                }

                            }
                            case ipv6 {

                                leaf system-ipv6 {
                                    type empty;
                                    sros-ext:auto-restart-to-modify;
                                    description "System IPv6 address for service EVPN route next hop";
                                }

                            }
                            case explicit {

                                leaf ip-address {
                                    type types-sros:ip-address;
                                    sros-ext:auto-restart-to-modify;
                                    description "IP address of the next-hop for the service EVPN route";
                                }

                            }
                        }
                    } // container route-next-hop

                    container endpoint {
                        status obsolete;
                        description "Enter the endpoint context";

                        leaf name {
                            status obsolete;
                            type leafref {
                                path "../../../../endpoint/name";
                            }
                            sros-ext:immutable;
                            description "Name of endpoint the bgp-evpn mpls instance is associated with";
                        }

                    } // container endpoint

                } // list mpls

                list segment-routing-v6 {
                    key "bgp-instance";
                    description "Enter the segment-routing-v6 list instance";

                    leaf bgp-instance {
                        type int32 {
                            range "1..2";
                        }
                        description "BGP instance";
                    }

                    leaf admin-state {
                        type types-sros:admin-state;
                        default "disable";
                        description "Administrative state of segment routing over IPv6";
                    }

                    leaf default-route-tag {
                        type types-services:one-byte-value;
                        sros-ext:auto-restart-to-modify;
                        description "Default route tag";
                    }

                    leaf source-address {
                        type types-sros:ipv6-unicast-address;
                        sros-ext:auto-restart-to-modify;
                        description "Source IPv6 address";
                    }

                    leaf oper-group {
                        type leafref {
                            path "../../../../oper-group/name";
                        }
                        description "Operational group";
                    }

                    leaf ecmp {
                        type types-services:ecmp-value;
                        default "1";
                        description "Maximum ECMP value configured on the service";
                    }

                    leaf force-vc-forwarding {
                        type enumeration {
                            enum vlan                           { value 1; }
                            enum qinq-c-tag-c-tag               { value 2; }
                            enum qinq-s-tag-c-tag               { value 3; }
                        }
                        description "Datapath forwarding to force vlan-vc-type";
                    }

                    leaf evi-three-byte-auto-rt {
                        type boolean;
                        sros-ext:auto-restart-to-modify;
                        default "false";
                        description "Auto-derive the BGP EVPN route target";
                    }

                    leaf mh-mode {
                        type enumeration {
                            enum access                         { value 0; }
                            enum network                        { value 1; }
                        }
                        default "network";
                        description "Multi-homing mode";
                    }

                    leaf resolution {
                        type types-sros:srv6-route-resolution;
                        default "route-table";
                        description "Resolution options for routes";
                    }

                    leaf domain-id {
                        type types-services:domain-id;
                        description "Domain ID of received BGP route before readvertisement";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container srv6 {
                        description "Enter the srv6 context";

                        leaf instance {
                            type leafref {
                                path "../../../../segment-routing-v6/instance";
                            }
                            sros-ext:immutable;
                            description "Segment Routing SRv6 instance";
                        }

                        leaf default-locator {
                            type string;
                            sros-ext:immutable;
                            description "Default route locator";
                        }

                    } // container srv6

                    container route-next-hop {
                        description "Enter the route-next-hop context";

                        choice tag {
                            default "ipv4";
                            case ipv4 {

                                leaf system-ipv4 {
                                    type empty;
                                    sros-ext:auto-restart-to-modify;
                                    description "System IPv4 address for service EVPN route next hop";
                                }

                            }
                            case ipv6 {

                                leaf system-ipv6 {
                                    type empty;
                                    sros-ext:auto-restart-to-modify;
                                    description "System IPv6 address for service EVPN route next hop";
                                }

                            }
                            case explicit {

                                leaf ip-address {
                                    type types-sros:ip-address;
                                    sros-ext:auto-restart-to-modify;
                                    description "IP address of the next-hop for the service EVPN route";
                                }

                            }
                        }
                    } // container route-next-hop

                } // list segment-routing-v6

            } // container bgp-evpn

            container network {
                description "Enter the network context";

                container ingress {
                    description "Enter the ingress context";

                    leaf classification-override {
                        type leafref {
                            path "../../../../../qos/ingress-classification-policy/ingress-classification-policy-name";
                        }
                        description "Short-pipe mode for CoS propagation";
                    }

                } // container ingress

            } // container network

        } // list epipe

    } // grouping conf-svc-epipe

}
