submodule nokia-conf-esa {

    yang-version "1.1";

    belongs-to nokia-conf { prefix "conf"; }

    import nokia-sros-yang-extensions     { prefix "sros-ext"; }
    import nokia-types-esa                { prefix "types-esa"; }
    import nokia-types-sros               { prefix "types-sros"; }

    include nokia-conf-groups;

    sros-ext:sros-major-release "rel25";
    organization "Nokia";
    contact
        "Nokia SR OS Support
         Web: <http://www.nokia.com>";
    description
        "Nokia YANG Data model to configure ESA configuration on SR OS based routers.

         Copyright 2016 Nokia. All rights reserved. Reproduction of this document
         is authorized on the condition that the foregoing copyright notice is included.

         This nokia-conf-esa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-esa {
        list esa {
            key "esa-id";
            description "Enter the esa list instance";

            leaf esa-id {
                type types-esa:esa-id;
                description "ESA ID";
            }

            leaf admin-state {
                type types-sros:admin-state;
                default "disable";
                description "Administrative state of the ESA";
            }

            leaf description {
                type types-sros:description;
                description "Text description";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list host-port {
                key "host-port";
                max-elements 4;
                description "Enter the host-port list instance";

                leaf host-port {
                    type types-sros:port;
                    description "Ethernet port associated with the ESA";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container crc-monitor {
                    description "Enter the crc-monitor context";

                    leaf window-size {
                        type uint32 {
                            range "10..60";
                        }
                        units "seconds";
                        default "10";
                        description "Window size of the monitor";
                    }

                    container signal-degrade {
                        description "Enter the signal-degrade context";

                        leaf threshold {
                            type uint32 {
                                range "1..9";
                            }
                            description "SD threshold";
                        }

                        leaf multiplier {
                            type uint32;
                            default "1";
                            description "SD multiplier";
                        }

                    } // container signal-degrade

                    container signal-failure {
                        description "Enter the signal-failure context";

                        leaf threshold {
                            type uint32 {
                                range "1..9";
                            }
                            description "SF threshold";
                        }

                        leaf multiplier {
                            type uint32;
                            default "1";
                            description "SF multiplier";
                        }

                    } // container signal-failure

                } // container crc-monitor

            } // list host-port

            list vm {
                key "vm-id";
                description "Enter the vm list instance";

                leaf vm-id {
                    type types-esa:vm-id;
                    description "VM ID";
                }

                leaf admin-state {
                    type types-sros:admin-state;
                    default "disable";
                    description "Administrative state of the ESA-VM instance";
                }

                leaf description {
                    type types-sros:description;
                    description "Text description";
                }

                leaf host-port {
                    type leafref {
                        path "../../host-port/host-port";
                    }
                    sros-ext:immutable;
                    description "Ethernet port associated with the ESA-VM instance";
                }

                leaf vm-type {
                    type enumeration {
                        enum aa                             { value 1; }
                        enum bb                             { value 2; }
                        enum tunnel                         { value 3; }
                        enum video                          { value 4; }
                        enum dms                            { value 5; }
                    }
                    sros-ext:immutable;
                    description "ESA-VM type";
                }

                leaf cores {
                    type uint32 {
                        range "0..128";
                    }
                    sros-ext:auto-restart-to-modify;
                    default "0";
                    description "Number of CPU physical cores allocated to the ESA-VM";
                }

                leaf memory {
                    type uint32 {
                        range "0..256";
                    }
                    units "gigabytes";
                    sros-ext:auto-restart-to-modify;
                    default "0";
                    description "Amount of memory allocated to the ESA-VM";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list vm

        } // list esa

    } // grouping conf-esa

}
