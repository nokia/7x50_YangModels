submodule nokia-conf-svc-vprn-ospf {

    yang-version "1.1";

    belongs-to nokia-conf { prefix "conf"; }

    import nokia-sros-yang-extensions     { prefix "sros-ext"; }
    import nokia-types-igp                { prefix "types-igp"; }
    import nokia-types-ospf               { prefix "types-ospf"; }
    import nokia-types-router             { prefix "types-router"; }
    import nokia-types-sros               { prefix "types-sros"; }

    include nokia-conf-groups;
    include nokia-conf-policy-options;
    include nokia-conf-routing-options;
    include nokia-conf-system;
    include nokia-conf-system-ned;
    include nokia-conf-system-security;

    sros-ext:sros-major-release "rel25";
    organization "Nokia";
    contact
        "Nokia SR OS Support
         Web: <http://www.nokia.com>";
    description
        "Nokia YANG Data model to configure vprn ospf protocol attributes on SR OS based routers.

         Copyright 2016 Nokia. All rights reserved. Reproduction of this document
         is authorized on the condition that the foregoing copyright notice is included.

         This nokia-conf-svc-vprn-ospf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-svc-vprn-ospf {
        list ospf {
            key "ospf-instance";
            max-elements 32;
            description "Enter the ospf list instance";

            leaf ospf-instance {
                type uint32 {
                    range "0";
                }
                description "Integrated OSPF instance";
            }

            leaf admin-state {
                type types-sros:admin-state;
                default "disable";
                description "Administrative state of the OSPF instance";
            }

            leaf router-id {
                type types-igp:router-id;
                sros-ext:auto-restart-to-modify;
                description "Unique router ID for the OSPF instance";
            }

            leaf advertise-router-capability {
                type types-ospf:advertise-router-capability-type;
                default "false";
                description "Allow router advertisement capabilities";
            }

            leaf external-preference {
                type int32 {
                    range "1..255";
                }
                default "150";
                description "Preference for OSPF external routes";
            }

            leaf-list export-policy {
                type leafref {
                    path "../../../../policy-options/policy-statement/name";
                }
                max-elements 5;
                ordered-by user;
                description "Export policies that determine exported routes";
            }

            leaf-list import-policy {
                type leafref {
                    path "../../../../policy-options/policy-statement/name";
                }
                max-elements 5;
                ordered-by user;
                description "Import policy names for routes from IGP to route table";
            }

            leaf multicast-import {
                type boolean;
                default "false";
                description "Submit routes into the multicast Route Table Manager";
            }

            leaf overload-include-ext-1 {
                type boolean;
                default "false";
                description "Advertise routes with maximum metric value for overload";
            }

            leaf overload-include-ext-2 {
                type boolean;
                default "false";
                description "Advertise routes with maximum metric value for overload";
            }

            leaf overload-include-stub {
                type boolean;
                default "false";
                description "Advertise all stub interfaces with max metric value";
            }

            leaf overload {
                type boolean;
                default "false";
                description "Change local router state to appear overloaded";
            }

            leaf preference {
                type int32 {
                    range "1..255";
                }
                default "10";
                description "Preference for OSPF internal routes";
            }

            leaf reference-bandwidth {
                type types-sros:reference-bandwidth-ext;
                units "kilobps";
                default "100000000";
                description "Bandwidth to reference default costing of interfaces";
            }

            leaf unicast-import {
                type boolean;
                default "true";
                description "Submit routes into the unicast Route Table Manager";
            }

            leaf compatible-rfc1583 {
                type boolean;
                default "true";
                description "OSPF summary and external route calculations";
            }

            leaf ignore-dn-bit {
                type boolean;
                default "false";
                description "Ignore the DN bit for OSPF LSA packets for the instance";
            }

            leaf suppress-dn-bit {
                type boolean;
                default "false";
                description "Suppress the DN bit setting for OSPF LSA packets";
            }

            leaf super-backbone {
                type boolean;
                default "false";
                description "Enable super backbone functionality";
            }

            leaf vpn-tag {
                type uint32;
                default "0";
                description "OSPF VPN tag";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container external-db-overflow {
                presence "Enable the external-db-overflow context";
                description "Enable the external-db-overflow context";

                leaf limit {
                    type uint32 {
                        range "0..2147483647";
                    }
                    default "0";
                    description "Number of external LSA at which overload is triggered";
                }

                leaf interval {
                    type uint32 {
                        range "0..2147483647";
                    }
                    units "seconds";
                    default "0";
                    description "Time during which the router operates in overload";
                }

            } // container external-db-overflow

            container export-limit {
                presence "Enable the export-limit context";
                description "Enable the export-limit context";

                leaf number {
                    type uint32 {
                        range "1..max";
                    }
                    mandatory true;
                    description "Maximum routes or prefixes exported from route table";
                }

                leaf log-percent {
                    type uint32 {
                        range "1..100";
                    }
                    description "Export limit before warning and SNMP notification sent";
                }

            } // container export-limit

            container overload-on-boot {
                presence "Enable the overload-on-boot context";
                description "Enable the overload-on-boot context";

                leaf timeout {
                    type uint32 {
                        range "60..1800";
                    }
                    units "seconds";
                    description "Time during which the router operates in overload state before reestablishing normal operations";
                }

            } // container overload-on-boot

            container rib-priority {
                description "Enter the rib-priority context";

                container high {
                    description "Enter the high context";

                    leaf prefix-list {
                        type leafref {
                            path "../../../../../../policy-options/prefix-list/name";
                        }
                        description "Higher priority list used during OSPF route calculation";
                    }

                } // container high

            } // container rib-priority

            container rtr-adv-lsa-limit {
                presence "Enable the rtr-adv-lsa-limit context";
                description "Enable the rtr-adv-lsa-limit context";

                leaf max-lsa-count {
                    type uint32 {
                        range "1..max";
                    }
                    mandatory true;
                    description "Max number of LSAs one router can advertise";
                }

                leaf log-only {
                    type boolean;
                    default "false";
                    description "Log the event without triggering overload";
                }

                leaf warning-threshold {
                    type uint32 {
                        range "0..100";
                    }
                    units "percent";
                    default "0";
                    description "Percentage of the max LSA count that causes a warning";
                }

                leaf overload-timeout {
                    type types-igp:overload-timeout;
                    default "forever";
                    description "Maximum time in overload after LSA limit is reached";
                }

            } // container rtr-adv-lsa-limit

            container graceful-restart {
                presence "Enable the graceful-restart context";
                description "Enable the graceful-restart context";

                leaf helper-mode {
                    type boolean;
                    default "true";
                    description "Enable graceful restart helper for OSPF";
                }

                leaf strict-lsa-checking {
                    type boolean;
                    default "true";
                    description "Perform strict LSA checking during graceful restart";
                }

            } // container graceful-restart

            container timers {
                description "Enter the timers context";

                leaf incremental-spf-wait {
                    type uint32 {
                        range "0..1000";
                    }
                    units "milliseconds";
                    default "1000";
                    description "Delay time before an incremental SPF calculation starts";
                }

                leaf lsa-accumulate {
                    type uint32 {
                        range "0..1000";
                    }
                    units "milliseconds";
                    default "1000";
                    description "Delay to gather LSAs before advertising to neighbors";
                }

                leaf lsa-arrival {
                    type uint32 {
                        range "0..600000";
                    }
                    units "milliseconds";
                    default "1000";
                    description "Min delay between receipt of same LSAs from neighbors";
                }

                leaf redistribute-delay {
                    type uint32 {
                        range "0..1000";
                    }
                    units "milliseconds";
                    default "1000";
                    description "Hold down timer for external routes into OSPF";
                }

                container lsa-generate {
                    description "Enter the lsa-generate context";

                    leaf max-lsa-wait {
                        type uint32 {
                            range "10..600000";
                        }
                        units "milliseconds";
                        default "5000";
                        description "Max time between two LSAs being generated";
                    }

                    leaf lsa-initial-wait {
                        type uint32 {
                            range "10..600000";
                        }
                        units "milliseconds";
                        default "5000";
                        description "First wait period between OSPF LSA generation";
                    }

                    leaf lsa-second-wait {
                        type uint32 {
                            range "10..600000";
                        }
                        units "milliseconds";
                        default "5000";
                        description "Hold time between the first and second LSA generation";
                    }

                } // container lsa-generate

                container spf-wait {
                    description "Enter the spf-wait context";

                    leaf spf-max-wait {
                        type uint32 {
                            range "10..120000";
                        }
                        units "milliseconds";
                        default "10000";
                        description "Max interval between two consecutive SPF calculations";
                    }

                    leaf spf-initial-wait {
                        type uint32 {
                            range "10..100000";
                        }
                        units "milliseconds";
                        default "1000";
                        description "Initial SPF calculation delay after a topology change";
                    }

                    leaf spf-second-wait {
                        type uint32 {
                            range "10..100000";
                        }
                        units "milliseconds";
                        default "1000";
                        description "Hold time between the first and second SPF calculation";
                    }

                } // container spf-wait

            } // container timers

            container loopfree-alternate {
                presence "Enable the loopfree-alternate context";
                description "Enable the loopfree-alternate context";

                container exclude {
                    description "Enter the exclude context";

                    leaf-list prefix-policy {
                        type leafref {
                            path "../../../../../../policy-options/policy-statement/name";
                        }
                        max-elements 5;
                        ordered-by user;
                        description "Policy to exclude prefixes from LFA SPF calculation";
                    }

                } // container exclude

            } // container loopfree-alternate

            container vpn-domain {
                presence "Enable the vpn-domain context";
                description "Enable the vpn-domain context";

                leaf id {
                    type types-igp:system-id;
                    description "OSPF VPN domain ID";
                }

                leaf type {
                    type types-ospf:vpn-domain-type;
                    mandatory true;
                    description "VPN domain type";
                }

            } // container vpn-domain

            list area {
                key "area-id";
                description "Enter the area list instance";

                leaf area-id {
                    type types-sros:ipv4-address;
                    description "Area-ID attribute";
                }

                leaf advertise-router-capability {
                    type boolean;
                    default "true";
                    description "Allow router advertisement capabilities";
                }

                leaf blackhole-aggregate {
                    type boolean;
                    default "true";
                    description "Install a low priority blackhole route to avoid loops";
                }

                leaf-list export-policy {
                    type leafref {
                        path "../../../../../policy-options/policy-statement/name";
                    }
                    max-elements 5;
                    ordered-by user;
                    description "Type 3 Summary-LSA/OSPFv3 inter-area-prefix-LSA route";
                }

                leaf-list import-policy {
                    type leafref {
                        path "../../../../../policy-options/policy-statement/name";
                    }
                    max-elements 5;
                    ordered-by user;
                    description "Route imported as Summary Type 3/Inter-Area-Prefix-LSA";
                }

                leaf loopfree-alternate-exclude {
                    type boolean;
                    default "false";
                    description "Exclude interfaces in OSPF areas in SPF LFA computation";
                }

                leaf advertise-ne-profile {
                    type leafref {
                        path "../../../../../system/network-element-discovery/profile/name";
                    }
                    description "Network element profile to be advertised";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container stub {
                    presence "Enable the stub context";
                    description "Enable the stub context";

                    leaf default-metric {
                        type uint32 {
                            range "1..16777214";
                        }
                        default "1";
                        description "Metric used by ABR for default route into the stub area";
                    }

                    leaf summaries {
                        type boolean;
                        default "true";
                        description "Send summary (Type 3) LSAs into the stub area on an ABR";
                    }

                } // container stub

                container nssa {
                    presence "Enable the nssa context";
                    description "Enable the nssa context";

                    leaf redistribute-external {
                        type boolean;
                        default "true";
                        description "Redistribute external routes into the NSSA";
                    }

                    leaf summaries {
                        type boolean;
                        default "true";
                        description "Send summary (Type 3) LSAs into the NSSA on an ABR";
                    }

                    list area-range {
                        key "ip-prefix-mask";
                        description "Enter the area-range list instance";

                        leaf ip-prefix-mask {
                            type types-sros:ipv4-unicast-prefix;
                            description "IPv4 unicast address prefix and mask";
                        }

                        leaf advertise {
                            type boolean;
                            default "true";
                            description "Advertise summarized range of addresses to other areas";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list area-range

                    container originate-default-route {
                        presence "Enable the originate-default-route context";
                        description "Enable the originate-default-route context";

                        leaf type-nssa {
                            type boolean;
                            default "false";
                            description "Generate a default route using NSSA-LSA type";
                        }

                        leaf adjacency-check {
                            type boolean;
                            default "false";
                            description "Perform adjacency checks before originating a default route";
                        }

                    } // container originate-default-route

                } // container nssa

                list area-range {
                    key "ip-prefix-mask";
                    description "Enter the area-range list instance";

                    leaf ip-prefix-mask {
                        type types-sros:ipv4-unicast-prefix;
                        description "IPv4 unicast address prefix and mask";
                    }

                    leaf advertise {
                        type boolean;
                        default "true";
                        description "Advertise summarized range of addresses to other areas";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list area-range

                list interface {
                    key "interface-name";
                    description "Enter the interface list instance";

                    leaf interface-name {
                        type types-sros:interface-name;
                        description "IP interface name";
                    }

                    leaf advertise-router-capability {
                        type boolean;
                        default "true";
                        description "Allow router advertisement capabilities";
                    }

                    leaf advertise-subnet {
                        type boolean;
                        default "true";
                        description "Advertise point-to-point interfaces as subnet routes";
                    }

                    leaf interface-type {
                        type types-ospf:interface-type;
                        sros-ext:immutable;
                        description "Interface type";
                    }

                    leaf lsa-filter-out {
                        type types-ospf:lsa-filter-out;
                        default "none";
                        description "LSA flooding reduction";
                    }

                    leaf metric {
                        type uint32 {
                            range "1..65535";
                        }
                        description "Route cost metric for the interface";
                    }

                    leaf mtu {
                        type types-router:ip-mtu-ext;
                        description "MTU for the OSPF to use on the interface";
                    }

                    leaf passive {
                        type boolean;
                        description "Advertise passive interfaces as OSPF interfaces";
                    }

                    leaf poll-interval {
                        type uint32;
                        units "seconds";
                        default "120";
                        description "Interval for Hellos to non-adjacent OSPF NBMA neighbor";
                    }

                    leaf priority {
                        type uint16 {
                            range "0..255";
                        }
                        default "1";
                        description "Interface priority in the DR election on the subnet";
                    }

                    leaf rib-priority {
                        type types-ospf:rib-priority;
                        description "RIB priority for OSPF";
                    }

                    leaf load-balancing-weight {
                        type uint32 {
                            range "1..max";
                        }
                        description "Load-balancing weight";
                    }

                    leaf admin-state {
                        type types-sros:admin-state;
                        default "enable";
                        description "Administrative state of the OSPF interface";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        description "OSPF wait time for Hellos before neighbor declared down";
                    }

                    leaf retransmit-interval {
                        type uint32 {
                            range "1..1800";
                        }
                        units "seconds";
                        default "5";
                        description "Time before OSPF retransmits an unacknowledged LSA";
                    }

                    leaf transit-delay {
                        type uint32 {
                            range "1..1800";
                        }
                        units "seconds";
                        default "1";
                        description "Required LSA transmit time";
                    }

                    leaf authentication-keychain {
                        type leafref {
                            path "../../../../../../system/security/keychains/keychain/keychain-name";
                        }
                        description "TCP authentication keychain for the session";
                    }

                    leaf authentication-key {
                        type types-sros:encrypted-leaf {
                            length "1..38";
                        }
                        description "Authentication key";
                    }

                    leaf authentication-type {
                        type types-ospf:authentication-type;
                        description "Authentication type used on OSPF interface";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container bfd-liveness {
                        presence "Enable the bfd-liveness context";
                        description "Enable the bfd-liveness context";

                        leaf remain-down-on-failure {
                            type boolean;
                            default "false";
                            description "Force adjacency down on failure until session returns";
                        }

                        leaf strict {
                            type boolean;
                            default "false";
                            description "Enable BFD strict mode";
                        }

                        leaf strict-mode-holddown {
                            type int32 {
                                range "1..600";
                            }
                            units "seconds";
                            description "Adjacency up time delay after BFD session establishment";
                        }

                    } // container bfd-liveness

                    container loopfree-alternate {
                        description "Enter the loopfree-alternate context";

                        leaf exclude {
                            type boolean;
                            default "false";
                            description "Enable fast reroute at OSPF primary interface level";
                        }

                        container policy-map {
                            presence "Enable the policy-map context";
                            description "Enable the policy-map context";

                            leaf route-nh-template {
                                type leafref {
                                    path "../../../../../../../../routing-options/route-next-hop-policy/template/template-name";
                                }
                                mandatory true;
                                description "Route next hop policy template name";
                            }

                        } // container policy-map

                    } // container loopfree-alternate

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 hash key";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list message-digest-key

                    list neighbor {
                        key "address";
                        description "Add a list entry for neighbor";

                        leaf address {
                            type types-sros:ipv4-unicast-address;
                            description "IPv4 address of the OSPFv2 neighbor";
                        }

                    } // list neighbor

                } // list interface

                list virtual-link {
                    key "router-id transit-area";
                    description "Enter the virtual-link list instance";

                    leaf router-id {
                        type types-sros:ipv4-address;
                        description "Router identity of the virtual link neighbor";
                    }

                    leaf transit-area {
                        type leafref {
                            path "../../../area/area-id";
                        }
                        description "Transit area that links backbone area to area without physical connection with the backbone";
                    }

                    leaf admin-state {
                        type types-sros:admin-state;
                        default "enable";
                        description "Administrative state of the OSPF interface";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        description "OSPF wait time for Hellos before neighbor declared down";
                    }

                    leaf retransmit-interval {
                        type uint32 {
                            range "1..1800";
                        }
                        units "seconds";
                        default "5";
                        description "Time before OSPF retransmits an unacknowledged LSA";
                    }

                    leaf transit-delay {
                        type uint32 {
                            range "1..1800";
                        }
                        units "seconds";
                        default "1";
                        description "Required LSA transmit time";
                    }

                    leaf authentication-keychain {
                        type leafref {
                            path "../../../../../../system/security/keychains/keychain/keychain-name";
                        }
                        description "TCP authentication keychain for the session";
                    }

                    leaf authentication-key {
                        type types-sros:encrypted-leaf {
                            length "1..38";
                        }
                        description "Authentication key";
                    }

                    leaf authentication-type {
                        type types-ospf:authentication-type;
                        description "Authentication type used on OSPF interface";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 hash key";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list message-digest-key

                } // list virtual-link

                list sham-link {
                    key "interface ip-address";
                    description "Enter the sham-link list instance";

                    leaf interface {
                        type types-sros:interface-name;
                        description "Local interface name used for the sham-link";
                    }

                    leaf ip-address {
                        type types-sros:ipv4-unicast-address;
                        description "IP address of the sham-link neighbor";
                    }

                    leaf admin-state {
                        type types-sros:admin-state;
                        default "enable";
                        description "Administrative state of the OSPF interface";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        description "OSPF wait time for Hellos before neighbor declared down";
                    }

                    leaf retransmit-interval {
                        type uint32 {
                            range "1..1800";
                        }
                        units "seconds";
                        default "5";
                        description "Time before OSPF retransmits an unacknowledged LSA";
                    }

                    leaf transit-delay {
                        type uint32 {
                            range "1..1800";
                        }
                        units "seconds";
                        default "1";
                        description "Required LSA transmit time";
                    }

                    leaf authentication-keychain {
                        type leafref {
                            path "../../../../../../system/security/keychains/keychain/keychain-name";
                        }
                        description "TCP authentication keychain for the session";
                    }

                    leaf authentication-key {
                        type types-sros:encrypted-leaf {
                            length "1..38";
                        }
                        description "Authentication key to send and receive OSPF packets";
                    }

                    leaf authentication-type {
                        type types-ospf:authentication-type;
                        description "Authentication type to be used";
                    }

                    leaf metric {
                        type uint32 {
                            range "1..65535";
                        }
                        default "1";
                        description "Explicit route cost metric that is applied to the sham link";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 key or hash key";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list message-digest-key

                } // list sham-link

            } // list area

        } // list ospf

    } // grouping conf-svc-vprn-ospf

}
