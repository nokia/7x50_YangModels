submodule nokia-state-system-security-tls {

    yang-version "1.1";

    belongs-to nokia-state { prefix "state"; }

    import nokia-sros-yang-extensions     { prefix "sros-ext"; }
    import nokia-types-sros               { prefix "types-sros"; }

    include nokia-state-system;
    include nokia-state-system-security;
    include nokia-state-system-security-pki;

    sros-ext:sros-major-release "rel25";
    organization "Nokia";
    contact
        "Nokia SR OS Support
         Web: <http://www.nokia.com>";
    description
        "Nokia YANG Data model with operational state for system security tls parameters. on SR OS based routers.

         Copyright 2016 Nokia. All rights reserved. Reproduction of this document
         is authorized on the condition that the foregoing copyright notice is included.

         This nokia-state-system-security-tls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping state-system-security-tls {
        container tls {
            description "Enter the tls context";

            list cert-profile {
                key "cert-profile-name";
                description "Enter the cert-profile list instance";

                leaf cert-profile-name {
                    type types-sros:named-item;
                    description "TLS Certificate profile name.";
                }

                leaf down-reasons {
                    type bits {
                        bit profile-admin-down             { position 0; }
                        bit invalid-cert-file              { position 1; }
                        bit invalid-key-file               { position 2; }
                        bit invalid-cert-key-combo         { position 3; }
                        bit ca-profile-oper-down           { position 4; }
                        bit invalid-ca-prof-entry          { position 5; }
                    }
                    description "Operational condition of this certificate profile.";
                }

                leaf oper-state {
                    type types-sros:oper-state;
                    description "Operational state.";
                }

                list entry {
                    key "entry-id";
                    description "Enter the entry list instance";

                    leaf entry-id {
                        type int32 {
                            range "1..8";
                        }
                        description "Certificate profile entry identifier.";
                    }

                    leaf computed-chain-state {
                        type enumeration {
                            enum not-available                  { value 0; }
                            enum partial                        { value 1; }
                            enum complete                       { value 2; }
                        }
                        description "Status of computed chain for this TLS certificate profile.";
                    }

                    leaf down-reasons {
                        type bits {
                            bit profile-admin-down             { position 0; }
                            bit invalid-cert-file              { position 1; }
                            bit invalid-key-file               { position 2; }
                            bit invalid-cert-key-combo         { position 3; }
                            bit ca-profile-oper-down           { position 4; }
                            bit invalid-ca-prof-entry          { position 5; }
                        }
                        description "Operational condition of this certificate profile.";
                    }

                    container computed-chain {
                        description "Enter the computed-chain context";

                        leaf-list ca-profiles {
                            type leafref {
                                path "../../../../../pki/ca-profile/ca-profile-name";
                            }
                            description "Specifies certificate profile entry computed chain information.";
                        }

                    } // container computed-chain

                } // list entry

            } // list cert-profile

            list client-tls-profile {
                key "client-profile-name";
                description "Enter the client-tls-profile list instance";

                leaf client-profile-name {
                    type types-sros:named-item;
                    description "Name of TLS client profile.";
                }

                leaf oper-state {
                    type types-sros:oper-state;
                    description "Operational state.";
                }

            } // list client-tls-profile

            list server-tls-profile {
                key "server-profile-name";
                description "Enter the server-tls-profile list instance";

                leaf server-profile-name {
                    type types-sros:named-item;
                    description "Name of TLS server profile.";
                }

                leaf oper-state {
                    type types-sros:oper-state;
                    description "Operational state.";
                }

            } // list server-tls-profile

            list trust-anchor-profile {
                key "trust-anchor-profile-name";
                description "Enter the trust-anchor-profile list instance";

                leaf trust-anchor-profile-name {
                    type types-sros:named-item;
                    description "Name of TLS trust anchor profile.";
                }

                leaf ca-profile-down {
                    type uint32 {
                        range "0..8";
                    }
                    description "Total number of trusted ca-profiles not operational in the trust-anchor-profile.";
                }

                list trust-anchor {
                    key "ca-profile-name";
                    description "Enter the trust-anchor list instance";

                    leaf ca-profile-name {
                        type leafref {
                            path "../../../../pki/ca-profile/ca-profile-name";
                        }
                        description "Trusted certificate authority profile.";
                    }

                    leaf oper-state {
                        type types-sros:oper-state;
                        description "Operational state.";
                    }

                } // list trust-anchor

            } // list trust-anchor-profile

        } // container tls

    } // grouping state-system-security-tls

}
