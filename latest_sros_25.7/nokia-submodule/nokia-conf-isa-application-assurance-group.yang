submodule nokia-conf-isa-application-assurance-group {

    yang-version "1.1";

    belongs-to nokia-conf { prefix "conf"; }

    import nokia-sros-yang-extensions     { prefix "sros-ext"; }
    import nokia-types-application-assurance { prefix "types-aa"; }
    import nokia-types-esa                { prefix "types-esa"; }
    import nokia-types-isa                { prefix "types-isa"; }
    import nokia-types-sros               { prefix "types-sros"; }

    include nokia-conf-groups;
    include nokia-conf-log;
    include nokia-conf-qos;

    sros-ext:sros-major-release "rel25";
    organization "Nokia";
    contact
        "Nokia SR OS Support
         Web: <http://www.nokia.com>";
    description
        "Nokia YANG Data model to configure ISA Application Assurance group configuration on SR OS based routers.

         Copyright 2016 Nokia. All rights reserved. Reproduction of this document
         is authorized on the condition that the foregoing copyright notice is included.

         This nokia-conf-isa-application-assurance-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-isa-application-assurance-group {
        list application-assurance-group {
            key "aa-group-id";
            max-elements 7;
            description "Enter the application-assurance-group list instance";

            leaf aa-group-id {
                type types-aa:isa-aa-grp-id;
                description "AA group identifier";
            }

            leaf admin-state {
                type types-sros:admin-state;
                default "disable";
                description "Administrative state of this AA group";
            }

            leaf description {
                type types-sros:description;
                description "Text description";
            }

            leaf aa-sub-scale {
                type types-aa:isa-aa-group-subscale;
                sros-ext:immutable;
                default "residential";
                description "AA group sub-scale";
            }

            leaf minimum-isa-generation {
                type types-aa:isa-generation-for-aa-grp;
                description "Minimum ISA generation for this AA group";
            }

            leaf http-enrich-max-packet-size {
                type uint32 {
                    range "576..9212";
                }
                units "octets";
                default "1500";
                description "Maximum HTTP enriched packet size";
            }

            leaf overload-cut-through {
                type boolean;
                default "false";
                description "Enable cut-through of traffic if ISA is in overload";
            }

            leaf failure-mode {
                type types-aa:isa-fail-to-mode;
                description "Mode of operation when no ISA-AA cards are available";
            }

            leaf isa-capacity-cost-low-threshold {
                type uint32 {
                    range "1..4294967295";
                }
                description "Capacity cost low threshold for the ISA-AA group";
            }

            leaf isa-capacity-cost-high-threshold {
                type uint32 {
                    range "0..4294967294";
                }
                description "Capacity cost high threshold for the ISA-AA group";
            }

            leaf-list divert-fc {
                type types-sros:fc-name;
                max-elements 8;
                description "Diverted traffic forwarding class";
            }

            leaf vm-traffic-distribute-by-ip {
                type boolean;
                sros-ext:auto-restart-to-modify;
                default "false";
                description "Allow packet distribution by IP address for virtual AA";
            }

            leaf vm-traffic-distribute-by-teid {
                type boolean;
                sros-ext:auto-restart-to-modify;
                default "false";
                description "Enable load balancing of the traffic using TEID";
            }

            leaf aa-sub-distribute-traffic-by-ip {
                type boolean;
                default "false";
                description "Allow application assurance to divert traffic";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container overload-sub-quarantine {
                description "Enter the overload-sub-quarantine context";

                leaf admin-state {
                    type types-sros:admin-state;
                    default "disable";
                    description "Administrative state of overload subscriber quarantine";
                }

            } // container overload-sub-quarantine

            list flow-attribute {
                key "flow-attribute-name";
                description "Add a list entry for flow-attribute";

                leaf flow-attribute-name {
                    type types-sros:named-item;
                    description "Flow attribute name";
                }

            } // list flow-attribute

            container shared-resources {
                description "Enter the shared-resources context";

                leaf gtp-tunnel-database {
                    type uint32 {
                        range "1..100";
                    }
                    sros-ext:auto-restart-to-modify;
                    description "Percentage of allocated memory resources";
                }

                leaf tcp-advanced-functions {
                    type uint32 {
                        range "1..100";
                    }
                    sros-ext:auto-restart-to-modify;
                    description "Allocation of resources for TCP advanced functions";
                }

                leaf url-filter-web-service-cache {
                    type uint32 {
                        range "1..100";
                    }
                    sros-ext:auto-restart-to-modify;
                    description "Amount of shared memory as a percentage";
                }

            } // container shared-resources

            container primary {
                description "Enter the primary context";

                list esa {
                    key "esa-id vm";
                    description "Add a list entry for esa";

                    leaf esa-id {
                        type types-esa:esa-id;
                        description "ESA ID";
                    }

                    leaf vm {
                        type types-esa:vm-id;
                        description "VM ID within the ESA";
                    }

                } // list esa

                list isa {
                    key "mda-id";
                    description "Add a list entry for isa";

                    leaf mda-id {
                        type types-isa:slot-mda;
                        description "MDA/ISA ID";
                    }

                } // list isa

            } // container primary

            container backup {
                description "Enter the backup context";

                list esa {
                    key "esa-id vm";
                    max-elements 4;
                    description "Add a list entry for esa";

                    leaf esa-id {
                        type types-esa:esa-id;
                        description "ESA ID";
                    }

                    leaf vm {
                        type types-esa:vm-id;
                        description "VM ID within the ESA";
                    }

                } // list esa

                list isa {
                    key "mda-id";
                    max-elements 1;
                    description "Add a list entry for isa";

                    leaf mda-id {
                        type types-isa:slot-mda;
                        description "MDA/ISA ID";
                    }

                } // list isa

            } // container backup

            container transit-prefix-limits {
                description "Enter the transit-prefix-limits context";

                leaf ipv4-entries {
                    type uint32 {
                        range "1..16383";
                    }
                    description "Limit of transit prefix IPv4 entries per AA group";
                }

                leaf ipv6-entries {
                    type uint32 {
                        range "1..8191";
                    }
                    description "Limit of transit prefix IPv6 entries per AA group";
                }

                leaf ipv4-remote-entries {
                    status obsolete;
                    type uint32 {
                        range "1..2047";
                    }
                    description "Limit of transit prefix IPv4 remote entries per group";
                }

                leaf ipv6-remote-entries {
                    status obsolete;
                    type uint32 {
                        range "1..1023";
                    }
                    description "Limit of transit prefix IPv6 remote entries per group";
                }

            } // container transit-prefix-limits

            container statistics {
                description "Enter the statistics context";

                list stats-type {
                    key "isa-aa-group-stats-type";
                    description "Enter the stats-type list instance";

                    leaf isa-aa-group-stats-type {
                        type types-aa:isa-aa-grp-stats-type;
                        description "Group performance statistics type";
                    }

                    leaf collect-stats {
                        type boolean;
                        default "false";
                        description "Enable the collection of statistics";
                    }

                    leaf accounting-policy {
                        type leafref {
                            path "../../../../../log/accounting-policy/policy-id";
                        }
                        description "Accounting policy ID used by AA";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list stats-type

            } // container statistics

            container qos {
                description "Enter the qos context";

                container egress {
                    description "Enter the egress context";

                    container from-subscriber {
                        description "Enter the from-subscriber context";

                        leaf port-scheduler-policy {
                            type leafref {
                                path "../../../../../../qos/port-scheduler-policy/name";
                            }
                            description "Port scheduler policy name";
                        }

                        leaf queue-policy {
                            type leafref {
                                path "../../../../../../qos/network-queue/network-queue-policy";
                            }
                            description "Queue policy name";
                        }

                        leaf wa-shared-low-wmark {
                            type types-aa:wa-shared-buffer-utilization-low;
                            default "0";
                            description "Low watermark for the weighted average utilization";
                        }

                        leaf wa-shared-high-wmark {
                            type types-aa:wa-shared-buffer-utilization-high;
                            default "max";
                            description "High watermark for weighted average utilization";
                        }

                        container buffer-pool {
                            description "Enter the buffer-pool context";

                            leaf name {
                                type types-sros:named-item;
                                sros-ext:immutable;
                                default "default";
                                description "Name of the buffer pool used for this ISA group";
                            }

                            leaf resv-cbs {
                                type types-aa:buffer-pool-reserved-percentage;
                                description "Reserved CBS for this ISA group";
                            }

                            leaf slope-policy {
                                type leafref {
                                    path "../../../../../../../qos/slope-policy/slope-policy-name";
                                }
                                description "Slope policy name";
                            }

                        } // container buffer-pool

                    } // container from-subscriber

                    container to-subscriber {
                        description "Enter the to-subscriber context";

                        leaf port-scheduler-policy {
                            type leafref {
                                path "../../../../../../qos/port-scheduler-policy/name";
                            }
                            description "Port scheduler policy name";
                        }

                        leaf queue-policy {
                            type leafref {
                                path "../../../../../../qos/network-queue/network-queue-policy";
                            }
                            description "Queue policy name";
                        }

                        leaf wa-shared-low-wmark {
                            type types-aa:wa-shared-buffer-utilization-low;
                            default "0";
                            description "Low watermark for the weighted average utilization";
                        }

                        leaf wa-shared-high-wmark {
                            type types-aa:wa-shared-buffer-utilization-high;
                            default "max";
                            description "High watermark for weighted average utilization";
                        }

                        container buffer-pool {
                            description "Enter the buffer-pool context";

                            leaf name {
                                type types-sros:named-item;
                                sros-ext:immutable;
                                default "default";
                                description "Name of the buffer pool used for this ISA group";
                            }

                            leaf resv-cbs {
                                type types-aa:buffer-pool-reserved-percentage;
                                description "Reserved CBS for this ISA group";
                            }

                            leaf slope-policy {
                                type leafref {
                                    path "../../../../../../../qos/slope-policy/slope-policy-name";
                                }
                                description "Slope policy name";
                            }

                        } // container buffer-pool

                    } // container to-subscriber

                } // container egress

            } // container qos

        } // list application-assurance-group

    } // grouping conf-isa-application-assurance-group

}
