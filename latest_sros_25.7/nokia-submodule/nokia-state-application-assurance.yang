submodule nokia-state-application-assurance {

    yang-version "1.1";

    belongs-to nokia-state { prefix "state"; }

    import ietf-yang-types                { prefix "yang"; }
    import nokia-sros-yang-extensions     { prefix "sros-ext"; }
    import nokia-types-application-assurance { prefix "types-aa"; }
    import nokia-types-esa                { prefix "types-esa"; }
    import nokia-types-isa                { prefix "types-isa"; }
    import nokia-types-services           { prefix "types-services"; }
    import nokia-types-sros               { prefix "types-sros"; }

    include nokia-state-aa-group;

    sros-ext:sros-major-release "rel25";
    organization "Nokia";
    contact
        "Nokia SR OS Support
         Web: <http://www.nokia.com>";
    description
        "Nokia YANG Data model with operational state for application assurance components on SR OS based routers.

         Copyright 2016 Nokia. All rights reserved. Reproduction of this document
         is authorized on the condition that the foregoing copyright notice is included.

         This nokia-state-application-assurance YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-application-assurance {
        container application-assurance {
            description "Enter the application-assurance context";

            list aarp {
                key "aarp-id";
                description "Enter the aarp list instance";

                leaf aarp-id {
                    type types-services:bsx-aarp-id;
                    description "Specifies an identifier that uniquely identifies an AARP instance within AA.";
                }

                leaf oper-state {
                    type types-sros:oper-state;
                    description
                        "The operational state of the AARP instance.
                         When the value is 'down' the AARP instance is not
                         performing asymmetry removal.";
                }

                leaf local-state {
                    type types-aa:aarp-state;
                    description "The state of the AARP instance.";
                }

                leaf local-flags {
                    type types-aa:aarp-oper-flags;
                    description "The conditions that affect the operating status of the AARP instance.";
                }

                leaf peer-state {
                    type types-aa:aarp-state;
                    description "The state advertised by the AARP instance peer.";
                }

                leaf peer-flags {
                    type types-aa:aarp-oper-flags;
                    description "The conditions that affect the operating status of the peer of this AARP instance.";
                }

                leaf peer-priority {
                    type uint32 {
                        range "0..255";
                    }
                    description "The priority advertised by the AARP instance peer.";
                }

                leaf peer-sub-ref-type {
                    type enumeration {
                        enum unknown                        { value 0; }
                        enum sap                            { value 2; }
                        enum spoke-sdp                      { value 3; }
                    }
                    description
                        "The type of the subscriber which the peer of this AARP instance
                         references with a service type of 'dualHomed'";
                }

                list role {
                    key "aarp-role endpoint-type endpoint";
                    description "Enter the role list instance";

                    leaf aarp-role {
                        type types-aa:aarp-svc-point-role;
                        description "The role of the AARP instance service point.";
                    }

                    leaf endpoint-type {
                        type types-aa:aarp-svc-point-type;
                        description "Specifies the AARP service endpoint type.";
                    }

                    leaf endpoint {
                        type union {
                            type types-sros:sap;
                            type types-services:sdp-bind-id;
                        }
                        description "Specifies the AARP service endpoint name.";
                    }

                } // list role

            } // list aarp

            container cflowd {
                description "Enter the cflowd context";

                list field {
                    key "field-name";
                    description "Enter the field list instance";

                    leaf field-name {
                        type types-sros:named-item;
                        description "Specifies the name of a cflowd record field.";
                    }

                    leaf id {
                        type uint32;
                        description "Specifies the id of the cflowd record field.";
                    }

                    leaf description {
                        type types-sros:display-string-or-empty {
                            length "0..80";
                        }
                        description "Specifies the description of the cflowd record field.";
                    }

                    leaf size {
                        type uint32;
                        description "Specifies the size (in bytes) of the cflowd record field.";
                    }

                    leaf encryption {
                        type types-aa:cflowd-field-encryption-type;
                        description "Specifies the encryption applied the cflowd record field.";
                    }

                    leaf encryption-group {
                        type types-aa:cflowd-field-encryption-group;
                        description "Specifies the encryption-group associated with the cflowd record field.";
                    }

                    container applicability {
                        description "Enter the applicability context";

                        container aa-sub-scale {
                            description "Enter the aa-sub-scale context";

                            leaf lightweight-internet {
                                type boolean;
                                description "Specifies whether the cflowd record field is applicable in aa-sub-scale lightweight-internet.";
                            }

                            leaf mobile-gateway {
                                type boolean;
                                description "Specifies whether the cflowd record field is applicable in aa-sub-scale mobile-gateway.";
                            }

                            leaf residential {
                                type boolean;
                                description "Specifies whether the cflowd record field is applicable in aa-sub-scale residential.";
                            }

                            leaf vpn {
                                type boolean;
                                description "Specifies whether the cflowd record field is applicable in aa-sub-scale vpn.";
                            }

                        } // container aa-sub-scale

                        container export-type {
                            description "Enter the export-type context";

                            leaf volume {
                                type types-aa:cflowd-field-inclusion;
                                description "Specifies the applicability of the cflowd field for volume records.";
                            }

                            leaf tcp-performance {
                                type types-aa:cflowd-field-inclusion;
                                description "Specifies the applicability of the cflowd field for tcp-performance records.";
                            }

                            leaf rtp-performance-voice {
                                status obsolete;
                                type types-aa:cflowd-field-inclusion;
                                description "Specifies the applicability of the cflowd field for rtp-performance voice records.";
                            }

                            leaf rtp-performance-video {
                                status obsolete;
                                type types-aa:cflowd-field-inclusion;
                                description "Specifies the applicability of the cflowd field for rtp-performance video records.";
                            }

                            leaf rtp-performance-audio {
                                status obsolete;
                                type types-aa:cflowd-field-inclusion;
                                description "Specifies the applicability of the cflowd field for rtp-performance audio records.";
                            }

                            leaf comprehensive {
                                type types-aa:cflowd-field-inclusion;
                                description "Specifies the applicability of the cflowd field for comprehensive records.";
                            }

                            leaf pgw-edr {
                                type types-aa:cflowd-field-inclusion;
                                description "Specifies the applicability of the cflowd field for pgw edr records.";
                            }

                        } // container export-type

                    } // container applicability

                } // list field

            } // container cflowd

            container flow-attribute {
                description "Enter the flow-attribute context";

                list attribute {
                    key "attribute-name";
                    description "Enter the attribute list instance";

                    leaf attribute-name {
                        type types-sros:named-item;
                        description "Specifies the flow-attribute attribute name.";
                    }

                    leaf id {
                        type uint32;
                        description "Specifies the id of the flow-attribute.";
                    }

                    leaf description {
                        type types-sros:display-string-or-empty {
                            length "0..80";
                        }
                        description "Specifies the description of the flow-attribute.";
                    }

                } // list attribute

            } // container flow-attribute

            container http-enrich {
                description "Enter the http-enrich context";

                list field {
                    key "field-name";
                    description "Enter the field list instance";

                    leaf field-name {
                        type types-sros:named-item;
                        description "Specifies the http-enrich field name.";
                    }

                    leaf id {
                        type uint32;
                        description "Specifies the id of the http-enrich field.";
                    }

                    leaf description {
                        type types-sros:display-string-or-empty {
                            length "0..80";
                        }
                        description "Specifies the description of the http-enrich field.";
                    }

                    leaf antispoof {
                        type boolean;
                        description "Specifies whether the http-enrich field supports antispoof.";
                    }

                    leaf antispoof-calling-line-id {
                        type boolean;
                        description "Specifies whether the http-enrich field supports antispoof of x-calling-line-id string.";
                    }

                    leaf tls-extension {
                        type boolean;
                        description "Specifies whether the http-enrich field has a tls-extension for enrichment of HTTPS.";
                    }

                    container applicability {
                        description "Enter the applicability context";

                        container aa-sub-scale {
                            description "Enter the aa-sub-scale context";

                            leaf lightweight-internet {
                                type boolean;
                                description "Specifies whether the http-enrich field is applicable in aa-sub-scale lightweight-internet.";
                            }

                            leaf mobile-gateway {
                                type boolean;
                                description "Specifies whether the http-enrich field is applicable in aa-sub-scale mobile-gateway.";
                            }

                            leaf residential {
                                type boolean;
                                description "Specifies whether the http-enrich field is applicable in aa-sub-scale residential.";
                            }

                            leaf vpn {
                                type boolean;
                                description "Specifies whether the http-enrich field is applicable in aa-sub-scale vpn.";
                            }

                        } // container aa-sub-scale

                    } // container applicability

                } // list field

            } // container http-enrich

            container http-error-redirect {
                description "Enter the http-error-redirect context";

                list error-code {
                    key "error-code-number";
                    description "Enter the error-code list instance";

                    leaf error-code-number {
                        type uint32 {
                            range "400..999";
                        }
                        description "Specifies the http-error-redirect error-code number.";
                    }

                    leaf description {
                        type types-sros:display-string-or-empty {
                            length "0..80";
                        }
                        description "Specifies the description of the http-error-redirect error-code.";
                    }

                    leaf default-message-size {
                        type uint32;
                        description "Specifies the http-error-redirect default maximum message size for this error-code.";
                    }

                } // list error-code

                list template {
                    key "template-id";
                    description "Enter the template list instance";

                    leaf template-id {
                        type uint32;
                        description "Specifies the http-error-redirect template ID.";
                    }

                    leaf description {
                        type types-sros:display-string-or-empty {
                            length "0..80";
                        }
                        description "Specifies the description of the http-error-redirect template.";
                    }

                } // list template

            } // container http-error-redirect

            container http-notification {
                description "Enter the http-notification context";

                list template {
                    key "template-id";
                    description "Enter the template list instance";

                    leaf template-id {
                        type uint32;
                        description "Specifies the http-notification template ID.";
                    }

                    leaf description {
                        type types-sros:display-string-or-empty {
                            length "0..80";
                        }
                        description "Specifies the description of the http-notification template.";
                    }

                } // list template

            } // container http-notification

            container http-redirect {
                description "Enter the http-redirect context";

                list macro-keyword {
                    key "macro-keyword-id";
                    description "Enter the macro-keyword list instance";

                    leaf macro-keyword-id {
                        type uint32;
                        description "Specifies the http-redirect macro keyword id.";
                    }

                    leaf keyword {
                        type types-sros:named-item;
                        description "Specifies the http-redirect macro-keyword.";
                    }

                    leaf description {
                        type types-sros:display-string-or-empty {
                            length "0..80";
                        }
                        description "Specifies the description of the http-redirect macro keyword.";
                    }

                } // list macro-keyword

                list template {
                    key "template-id";
                    description "Enter the template list instance";

                    leaf template-id {
                        type uint32;
                        description "Specifies the http-redirect template ID.";
                    }

                    leaf description {
                        type types-sros:display-string-or-empty {
                            length "0..80";
                        }
                        description "Specifies the description of the http-redirect template.";
                    }

                    leaf macro-support {
                        type boolean;
                        description "Specifies whether the http-redirect template supports macro substitution.";
                    }

                } // list template

            } // container http-redirect

            list protocol {
                key "protocol-name";
                description "Enter the protocol list instance";

                leaf protocol-name {
                    type types-sros:named-item;
                    description "Specifies the protocol name.";
                }

                leaf description {
                    type types-sros:display-string-or-empty {
                        length "0..80";
                    }
                    description "Specifies the protocol description.";
                }

                leaf obsolete {
                    type boolean;
                    description "Specifies whether or not the protocol is obsolete.  Obsolete protocols are not detected by AA.";
                }

                leaf parent-protocol {
                    type types-sros:named-item-or-empty;
                    description "Specifies the parent protocol name.";
                }

            } // list protocol

            list radius-accounting-policy {
                key "rad-acct-plcy-name";
                description "Enter the radius-accounting-policy list instance";

                leaf rad-acct-plcy-name {
                    type types-sros:named-item;
                    description "AA RADIUS accounting policy.";
                }

                container statistics {
                    description "Enter the statistics context";

                    leaf received-responses {
                        type yang:counter32;
                        description "The number of RADIUS accounting responses received for this policy.";
                    }

                    leaf request-timeouts {
                        type yang:counter32;
                        description "The number of RADIUS accounting requests which have timed out for this policy.";
                    }

                    leaf transmitted-failed {
                        type yang:counter32;
                        description "The number of RADIUS accounting requests failed because the packet could not be sent.";
                    }

                    leaf transmitted-requests {
                        type yang:counter32;
                        description "The number of RADIUS accounting requests transmitted for this policy.";
                    }

                    leaf transmitted-retries {
                        type yang:counter32;
                        description
                            "The number of retries to a different server for a single RADIUS accounting request
                             for this policy.";
                    }

                } // container statistics

                container radius-accounting-server {
                    description "Enter the radius-accounting-server context";

                    list server {
                        key "server-index";
                        description "Enter the server list instance";

                        leaf server-index {
                            type uint32 {
                                range "1..5";
                            }
                            description "An identifier that uniquely identifies a radius accounting server instance within an AA accounting policy.";
                        }

                        leaf oper-state {
                            type types-sros:oper-state;
                            description "The operational state of the RADIUS server.";
                        }

                        container statistics {
                            description "Enter the statistics context";

                            leaf received-responses {
                                type yang:counter32;
                                description "The number of RADIUS accounting responses received for this server.";
                            }

                            leaf request-timeouts {
                                type yang:counter32;
                                description "The number of RADIUS accounting requests that have timed out for this server.";
                            }

                            leaf transmitted-failed {
                                type yang:counter32;
                                description "The number of RADIUS accounting requests that failed because the packet could not be sent.";
                            }

                            leaf transmitted-requests {
                                type yang:counter32;
                                description "The number of RADIUS accounting requests transmitted for this server.";
                            }

                        } // container statistics

                    } // list server

                } // container radius-accounting-server

            } // list radius-accounting-policy

            container url-filter {
                description "Enter the url-filter context";

                container web-service {
                    description "Enter the web-service context";

                    list category-set {
                        key "category-set-id";
                        description "Enter the category-set list instance";

                        leaf category-set-id {
                            type uint32 {
                                range "1..65535";
                            }
                            description "Specifies the web service category Id.";
                        }

                        list category {
                            key "category-id";
                            description "Enter the category list instance";

                            leaf category-id {
                                type uint32 {
                                    range "1..65535";
                                }
                                description "Specifies a web service profile category ID.";
                            }

                            leaf category-name {
                                type types-aa:web-serv-category-name;
                                description "Specifies the name of the category.";
                            }

                            leaf description {
                                type types-sros:display-string-or-empty {
                                    length "0..80";
                                }
                                description "Specifies the description of the category.";
                            }

                        } // list category

                        list classifier {
                            key "classifier-id";
                            description "Enter the classifier list instance";

                            leaf classifier-id {
                                type types-aa:web-serv-classifier-id;
                                description "Specifies the web service classifier Id.";
                            }

                            leaf description {
                                type types-sros:description;
                                description "Specifies the description of the classifier.";
                            }

                        } // list classifier

                    } // list category-set

                } // container web-service

            } // container url-filter

            container version {
                description "Enter the version context";

                container control-processor {
                    description "Enter the control-processor context";

                    leaf software-version {
                        type types-sros:display-string-or-empty;
                        description "Indicates the software version of the isa-aa.tim file in use by the control processor.";
                    }

                } // container control-processor

                list esa {
                    key "esa-id vm";
                    description "Enter the esa list instance";

                    leaf esa-id {
                        type types-esa:esa-id;
                        description "Specifies an ESA identifier.";
                    }

                    leaf vm {
                        type types-esa:vm-id;
                        description "Specifies the VM identifier within the ESA.";
                    }

                    leaf software-version {
                        type types-sros:display-string-or-empty;
                        description "Indicates the software version of the isa-aa.tim file in use by the ESA-VMs.";
                    }

                } // list esa

                list isa {
                    key "mda-id";
                    description "Enter the isa list instance";

                    leaf mda-id {
                        type types-isa:slot-mda;
                        description "Specifies an MDA/ISA identifier <card slot number>/<mda slot number>";
                    }

                    leaf software-version {
                        type types-sros:display-string-or-empty;
                        description "Indicates the software version of the isa-aa.tim file in use by the ISAs.";
                    }

                } // list isa

            } // container version

            uses state-aa-group;
        } // container application-assurance

    } // grouping state-application-assurance

}
