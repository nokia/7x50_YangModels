submodule nokia-state-service {

    yang-version "1.1";

    belongs-to nokia-state { prefix "state"; }

    import ietf-yang-types                { prefix "yang"; }
    import nokia-sros-yang-extensions     { prefix "sros-ext"; }
    import nokia-types-services           { prefix "types-services"; }
    import nokia-types-sros               { prefix "types-sros"; }

    include nokia-state-svc-cpipe;
    include nokia-state-svc-epipe;
    include nokia-state-svc-ies;
    include nokia-state-svc-ipipe;
    include nokia-state-svc-nat;
    include nokia-state-svc-sdp;
    include nokia-state-svc-vpls;
    include nokia-state-svc-vprn;

    sros-ext:sros-major-release "rel25";
    organization "Nokia";
    contact
        "Nokia SR OS Support
         Web: <http://www.nokia.com>";
    description
        "Nokia YANG Data model with operational state for services on SR OS based routers.

         Copyright 2016 Nokia. All rights reserved. Reproduction of this document
         is authorized on the condition that the foregoing copyright notice is included.

         This nokia-state-service YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping state-service {
        container service {
            description "Enter the service context";

            list customer {
                key "customer-name";
                description "Enter the customer list instance";

                leaf customer-name {
                    type types-services:customer-name;
                    description "Specify customer name for a service";
                }

                leaf oper-customer-id {
                    type types-services:customer-id;
                    description "Operational value of customer identifier in use";
                }

                list multi-service-site {
                    key "multi-service-site-name";
                    description "Enter the multi-service-site list instance";

                    leaf multi-service-site-name {
                        type types-sros:named-item;
                        description "Service customer multi-service site name";
                    }

                    container ingress {
                        description "Enter the ingress context";

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list scheduler

                        } // container scheduler-policy

                        list arbiter {
                            key "arbiter-name";
                            description "Enter the arbiter list instance";

                            leaf arbiter-name {
                                type types-sros:named-item;
                                description "Specifies the arbiter name.";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list arbiter

                    } // container ingress

                    container egress {
                        description "Enter the egress context";

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list scheduler

                        } // container scheduler-policy

                        list arbiter {
                            key "arbiter-name";
                            description "Enter the arbiter list instance";

                            leaf arbiter-name {
                                type types-sros:named-item;
                                description "Specifies the arbiter name.";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list arbiter

                    } // container egress

                } // list multi-service-site

            } // list customer

            list oper-group {
                key "name";
                description "Enter the oper-group list instance";

                leaf name {
                    type types-sros:named-item;
                    description "Service operational group name";
                }

                leaf oper-state {
                    type types-sros:oper-state;
                    description "Operational state.";
                }

                leaf num-members {
                    type uint32;
                    description "Number of members";
                }

                leaf num-monitoring {
                    type uint32;
                    description "Number of objects monitoring this group";
                }

                container hold-time {
                    description "Enter the hold-time context";

                    leaf down-remain {
                        type uint32;
                        units "seconds";
                        description "Number of seconds remaining in down time";
                    }

                    leaf up-remain {
                        type uint32;
                        units "seconds";
                        description "Number of seconds remaining in up time";
                    }

                } // container hold-time

                container bfd-liveness {
                    description "Enter the bfd-liveness context";

                    leaf oper-state {
                        type enumeration {
                            enum unknown                        { value 1; }
                            enum connected                      { value 2; }
                            enum broken                         { value 3; }
                            enum peer-detects-down              { value 4; }
                            enum not-configured                 { value 5; }
                            enum no-resources                   { value 6; }
                        }
                        description "Operational state of the BFD session";
                    }

                    leaf source-ip {
                        type types-sros:ip-address;
                        description "Source ip-address of the interface running BFD";
                    }

                } // container bfd-liveness

            } // list oper-group

            container upnp {
                description "Enter the upnp context";

                list policy {
                    key "name";
                    description "Enter the policy list instance";

                    leaf name {
                        type types-sros:external-named-item;
                        description "UPnP policy name";
                    }

                    leaf active-mappings {
                        type yang:gauge32;
                        description "Number of active UPnP mappings, associated with this server";
                    }

                    leaf mapped-subscribers {
                        type yang:gauge32;
                        description "Number of subscribers with UPnP mappings, associated with this server";
                    }

                    leaf associated-subscribers {
                        type yang:gauge32;
                        description "Total number of subscribers associated with specified upnp-policy";
                    }

                    list statistics {
                        key "counter-id";
                        description "Enter the statistics list instance";

                        leaf counter-id {
                            type uint32;
                            description "The counter";
                        }

                        leaf description {
                            type string {
                                length "0..64";
                            }
                            description "The human-readable identifier of the statistic.";
                        }

                        leaf value {
                            type yang:counter64;
                            description "The counter value";
                        }

                    } // list statistics

                } // list policy

            } // container upnp

            list pw-template {
                key "pw-template-name";
                description "Enter the pw-template list instance";

                leaf pw-template-name {
                    type types-services:pw-template-name;
                    description "The name of this pw-template.";
                }

                leaf oper-pw-template-id {
                    type types-services:pw-template-id;
                    description "Operational value of PW template identifier in use";
                }

            } // list pw-template

            container system {
                description "Enter the system context";

                container fdb {
                    description "Enter the fdb context";

                    leaf table-usage-above-95-percent {
                        type boolean;
                        description "Set to 'true' when the system FDB table usage exceeds 95% of the size of the system FDB table and 'false' when it drops below 90% of the size of the system FDB table.";
                    }

                    leaf pbb-backbone-mac-address-limit-reached {
                        type boolean;
                        description "Set to 'true' when the number of system Backbone MAC address indices reaches the limit and 'false' when it is below the limit.";
                    }

                    container usage {
                        description "Enter the usage context";

                        leaf allocated {
                            type yang:counter32;
                            description "The total number of FDB entries that are currently allocated on this system.";
                        }

                        leaf global {
                            type yang:counter32;
                            description "The total number of non-selective FDB entries that are currently reserved on this system.";
                        }

                        container rvpls {
                            description "Enter the rvpls context";

                            leaf in-use {
                                type yang:counter32;
                                description "The total number of resources that are in-use on this system.";
                            }

                            leaf allocated {
                                type yang:counter32;
                                description "The total number of resources that are currently allocated on this system.";
                            }

                        } // container rvpls

                        container es-bmac {
                            description "Enter the es-bmac context";

                            leaf in-use {
                                type yang:counter32;
                                description "The total number of resources that are in-use on this system.";
                            }

                            leaf allocated {
                                type yang:counter32;
                                description "The total number of resources that are currently allocated on this system.";
                            }

                        } // container es-bmac

                    } // container usage

                } // container fdb

                container bgp {
                    description "Enter the bgp context";

                    container evpn {
                        description "Enter the evpn context";

                        leaf oper-route-distinguisher {
                            type string;
                            description "Indicates Operational route-distinguisher used for ethernet segment (ES) routes";
                        }

                        leaf oper-route-distinguisher-type {
                            type types-services:route-distinguisher-type;
                            description "Indicates type of operational route-distinguisher.";
                        }

                        leaf oper-etree-leaf-label {
                            type uint32;
                            description "Indicates the label allocated and signaled to the far end PEs for etree leaf traffic.";
                        }

                        list ethernet-segment {
                            key "ethernet-segment-name";
                            description "Enter the ethernet-segment list instance";

                            leaf ethernet-segment-name {
                                type types-sros:named-item;
                                description "Specify name for Ethernet segment";
                            }

                            leaf oper-esi {
                                type types-services:ethernet-segment-id;
                                description "LACP derived ethernet segment identifier";
                            }

                            leaf oper-state {
                                type types-sros:oper-state;
                                description "Indicates the operational state of the ethernet segment entry.";
                            }

                            leaf split-horizon-label {
                                type int32;
                                description "Indicates the split horizon group label advertised for the ethernet segment.";
                            }

                            leaf split-horizon-argument-value {
                                type int32;
                                description "Split horizon group argument value.";
                            }

                            leaf oper-service-carving-mode {
                                type enumeration {
                                    enum auto                           { value 1; }
                                    enum manual                         { value 2; }
                                    enum off                            { value 3; }
                                }
                                description "Indicates the operational service carving mode for the ethernet segment entry.";
                            }

                            leaf configured-ranges-df-alg-type {
                                type enumeration {
                                    enum primary                        { value 1; }
                                    enum lowest-preference              { value 2; }
                                }
                                description "Indicates the mode that the configured evi or isid ranges are in for this ethernet segment entry.";
                            }

                            leaf multi-homing-oper-state {
                                type enumeration {
                                    enum none                           { value 0; }
                                    enum single-active                  { value 1; }
                                    enum single-active-no-esi-label     { value 2; }
                                    enum all-active                     { value 3; }
                                    enum all-active-no-esi-label        { value 4; }
                                }
                                description "Indicates the operational state of multi-homing of the ethernet segment entry.";
                            }

                            leaf local-bias-limit-exceeded {
                                type boolean;
                                description
                                    "Local-bias status when the system limit of three local bias peers per ethernet-segment
                                     is exceeded while enabling local bias for a VTEP address.";
                            }

                            leaf esi-conflict {
                                type types-services:ethernet-segment-id;
                                description "ESI conflict status";
                            }

                            leaf last-changed {
                                type types-sros:date-time;
                                description "Indicates the sysUpTime at the time of the last modification of Designated Forwarder.";
                            }

                            container df-election {
                                description "Enter the df-election context";

                                container manual {
                                    description "Enter the manual context";

                                    container preference {
                                        description "Enter the preference context";

                                        leaf operational-preference-value {
                                            type uint32;
                                            description "Indicates the operational preference value assigned while electing the designated forwarder.";
                                        }

                                        leaf do-not-preempt-status {
                                            type boolean;
                                            description "Indicates the status of the don't peempt bit used in electing the next designated forwarder.";
                                        }

                                    } // container preference

                                } // container manual

                            } // container df-election

                            container pbb {
                                description "Enter the pbb context";

                                leaf bmac-table-entries {
                                    type int32;
                                    description "Indicates the size of BMAC table used for this ethernet segment.";
                                }

                                list service-name {
                                    key "service-name";
                                    description "Enter the service-name list instance";

                                    leaf service-name {
                                        type types-services:service-name;
                                        description "Name of the service.";
                                    }

                                    leaf backbone-mac-address {
                                        type yang:mac-address;
                                        description "Indicates the backbone MAC address.";
                                    }

                                } // list service-name

                            } // container pbb

                            list evi {
                                key "id";
                                description "Enter the evi list instance";

                                leaf id {
                                    type int32 {
                                        range "1..16777215";
                                    }
                                    description "EVPN indetifier";
                                }

                                leaf df {
                                    type boolean;
                                    description "Indicates if the ethernet segment EVI entry is a designated forwarder.";
                                }

                                leaf remaining-activation-time {
                                    type int32;
                                    units "seconds";
                                    description "Indicates the value of the remaining activation timer for this entry.";
                                }

                                leaf service-name {
                                    type types-services:service-name;
                                    description "Indicates service Name for this entry.";
                                }

                                leaf df-last-changed {
                                    type types-sros:date-time;
                                    description "Indicates the sysUpTime at the time of the last modification of Designated Forwarder.";
                                }

                                leaf oper-route-distinguisher {
                                    type string;
                                    description "Indicates operational route-distinguisher value in use by the system for this entry.";
                                }

                                container df-candidates {
                                    description "Enter the df-candidates context";

                                    list ip-address {
                                        key "ip-address";
                                        description "Enter the ip-address list instance";

                                        leaf ip-address {
                                            type types-sros:ip-address;
                                            description "EVI candidate PE IP address.";
                                        }

                                        leaf time-added {
                                            type types-sros:date-time;
                                            description "Indicates the time at which this entry was added in the DF candidate list.";
                                        }

                                        leaf operational-preference-value {
                                            type uint32;
                                            description "Indicates the operational preference value assigned while electing the designated forwarder.";
                                        }

                                        leaf do-not-preempt-status {
                                            type boolean;
                                            description "Indicates the status of the don't peempt bit used in electing the next designated forwarder.";
                                        }

                                    } // list ip-address

                                } // container df-candidates

                            } // list evi

                            list isid {
                                key "id";
                                description "Enter the isid list instance";

                                leaf id {
                                    type int32 {
                                        range "1..16777215";
                                    }
                                    description "Service instance identifier.";
                                }

                                leaf df {
                                    type boolean;
                                    description "Indicates if the ethernet segment EVI entry is a designated forwarder.";
                                }

                                leaf remaining-activation-time {
                                    type int32;
                                    units "seconds";
                                    description "Indicates the value of the remaining activation timer for this entry.";
                                }

                                leaf service-name {
                                    type types-services:service-name;
                                    description "Indicates service Name for this entry.";
                                }

                                leaf df-last-changed {
                                    type types-sros:date-time;
                                    description "Indicates the sysUpTime at the time of the last modification of Designated Forwarder.";
                                }

                                container df-candidates {
                                    description "Enter the df-candidates context";

                                    list ip-address {
                                        key "ip-address";
                                        description "Enter the ip-address list instance";

                                        leaf ip-address {
                                            type types-sros:ip-address;
                                            description "ISID candidate PE IP address.";
                                        }

                                        leaf time-added {
                                            type types-sros:date-time;
                                            description "Indicates the time at which this entry was added in the DF candidate list.";
                                        }

                                        leaf operational-preference-value {
                                            type uint32;
                                            description "Indicates the operational preference value assigned while electing the designated forwarder.";
                                        }

                                        leaf do-not-preempt-status {
                                            type boolean;
                                            description "Indicates the status of the don't peempt bit used in electing the next designated forwarder.";
                                        }

                                    } // list ip-address

                                } // container df-candidates

                            } // list isid

                        } // list ethernet-segment

                    } // container evpn

                } // container bgp

            } // container system

            container evpn {
                description "Enter the evpn context";

                container mpls {
                    description "Enter the mpls context";

                    list tep {
                        key "ip-address";
                        description "Enter the tep list instance";

                        leaf ip-address {
                            type types-sros:ip-address;
                            description "IP address of Tunnel Endpoint";
                        }

                        leaf non-ethernet-segment-destinations {
                            type uint32;
                            description "Indicates the number of EVPN destinations.";
                        }

                        leaf ethernet-segment-destinations {
                            type uint32;
                            description "Indicates the number of EVPN destinations.";
                        }

                        leaf ethernet-segment-backbone-mac-destinations {
                            type uint32;
                            description "Indicates the number of backbone MAC destinations.";
                        }

                    } // list tep

                } // container mpls

                container statistics {
                    description "Enter the statistics context";

                    leaf num-mpls-etree-leaf-dests {
                        type uint32;
                        description "Indicates the number of mpls etree leaf dests.";
                    }

                    leaf num-etree-leaf-labels {
                        type uint32;
                        description "Indicates the number of etree leaf labels.";
                    }

                    container num-tep {
                        description "Enter the num-tep context";

                        leaf mpls {
                            type uint32;
                            description "Indicates the number of mpls tep.";
                        }

                        leaf srv6 {
                            type uint32;
                            description "Indicates the number of srv6 tep.";
                        }

                        leaf vxlan {
                            type uint32;
                            description "Indicates the number of vxlan tep.";
                        }

                        leaf in-use {
                            type uint32;
                            description "Indicates the total number of tep in use.";
                        }

                        leaf total {
                            type uint32;
                            description "Indicates the total number of tep on this chassis.";
                        }

                        container peer {
                            description "Enter the peer context";

                            leaf in-use {
                                type uint32;
                                description "Indicates the total number of tep in-use on peer.";
                            }

                            leaf total {
                                type uint32;
                                description "Indicates the total number of tep on peer chassis.";
                            }

                        } // container peer

                    } // container num-tep

                    container num-evpn-dests {
                        description "Enter the num-evpn-dests context";

                        leaf mpls {
                            type uint32;
                            description "Indicates the number of mpls dests.";
                        }

                        leaf srv6 {
                            type uint32;
                            description "Indicates the number of srv6 dests.";
                        }

                        leaf vxlan {
                            type uint32;
                            description "Indicates the number of vxlan dests.";
                        }

                        leaf in-use {
                            type uint32;
                            description "Indicates the total number of dests in use.";
                        }

                        leaf total {
                            type uint32;
                            description "Indicates the total number of dests on this chassis.";
                        }

                    } // container num-evpn-dests

                    container num-es-pbr {
                        description "Enter the num-es-pbr context";

                        leaf in-use {
                            type uint32;
                            description "Indicates the number of ES PBRs in use.";
                        }

                        leaf total {
                            type uint32;
                            description "Indicates the total number of PBRs on this chassis.";
                        }

                    } // container num-es-pbr

                    container num-sdp-bind-and-evpn-dests {
                        description "Enter the num-sdp-bind-and-evpn-dests context";

                        leaf in-use {
                            type uint32;
                            description "Indicates the number of SDP bind and Evpn dests in use.";
                        }

                        leaf total {
                            type uint32;
                            description "Indicated the number of total binds on this chassis.";
                        }

                    } // container num-sdp-bind-and-evpn-dests

                    container num-eth-seg {
                        description "Enter the num-eth-seg context";

                    } // container num-eth-seg

                } // container statistics

            } // container evpn

            container vxlan {
                description "Enter the vxlan context";

                list tep {
                    key "ip-address";
                    description "Enter the tep list instance";

                    leaf ip-address {
                        type types-sros:ip-address;
                        description "IP address of Tunnel Endpoint";
                    }

                    leaf oper-state {
                        type types-sros:oper-state;
                        description "Operational status of EVPN Vxlan tunnel-endpoint";
                    }

                    leaf non-ethernet-segment-destinations {
                        type uint32;
                        description "Number of destinations";
                    }

                    leaf ethernet-segment-destinations {
                        type uint32;
                        description "Number of ethernet segment destinations";
                    }

                    leaf vprn-destination {
                        type boolean;
                        description "Indicates if the VTEP is learned on the VPRN.";
                    }

                    leaf local-bias-limit-exceeded {
                        type boolean;
                        description "Local-bias fail status due to system limits";
                    }

                } // list tep

            } // container vxlan

            container segment-routing-v6 {
                description "Enter the segment-routing-v6 context";

                list tep {
                    key "ip-address";
                    description "Enter the tep list instance";

                    leaf ip-address {
                        type types-sros:ip-address;
                        description "Ip-address";
                    }

                    leaf non-ethernet-segment-destinations {
                        type uint32;
                        description "Indicates the number of EVPN destinations.";
                    }

                    leaf ethernet-segment-destinations {
                        type uint32;
                        description "Indicates the number of EVPN destinations.";
                    }

                } // list tep

            } // container segment-routing-v6



            container statistics {
                description "Enter the statistics context";



            } // container statistics

            uses state-svc-cpipe;
            uses state-svc-epipe;
            uses state-svc-ies;
            uses state-svc-ipipe;
            uses state-svc-nat;
            uses state-svc-sdp;
            uses state-svc-vpls;
            uses state-svc-vprn;
        } // container service

    } // grouping state-service

}
