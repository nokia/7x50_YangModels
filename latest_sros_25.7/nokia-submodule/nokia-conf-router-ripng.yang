submodule nokia-conf-router-ripng {

    yang-version "1.1";

    belongs-to nokia-conf { prefix "conf"; }

    import nokia-sros-yang-extensions     { prefix "sros-ext"; }
    import nokia-types-ripng              { prefix "types-ripng"; }
    import nokia-types-sros               { prefix "types-sros"; }

    include nokia-conf-groups;
    include nokia-conf-policy-options;

    sros-ext:sros-major-release "rel25";
    organization "Nokia";
    contact
        "Nokia SR OS Support
         Web: <http://www.nokia.com>";
    description
        "Nokia YANG Data model to configure router ripng protocol attributes on SR OS based routers.

         Copyright 2016 Nokia. All rights reserved. Reproduction of this document
         is authorized on the condition that the foregoing copyright notice is included.

         This nokia-conf-router-ripng YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-09-03";

    grouping conf-router-ripng {
        container ripng {
            presence "Enable the ripng context";
            description "Enable the ripng context";

            leaf admin-state {
                type types-sros:admin-state;
                default "enable";
                description "Administrative state of the RIPng instance";
            }

            leaf description {
                type types-sros:description;
                description "Text description";
            }

            leaf bfd-liveness {
                type boolean;
                default "false";
                description "Enable BFD to control the state of protocol adjacency";
            }

            leaf check-zero {
                type boolean;
                default "false";
                description "Enable checking of mandatory zero fields";
            }

            leaf-list export-policy {
                type leafref {
                    path "../../../policy-options/policy-statement/name";
                }
                max-elements 5;
                ordered-by user;
                description "Policies to determine exported routes";
            }

            leaf-list import-policy {
                type leafref {
                    path "../../../policy-options/policy-statement/name";
                }
                max-elements 5;
                ordered-by user;
                description "Import policies to decide routes for routing table";
            }

            leaf message-size {
                type types-ripng:message-size;
                default "25";
                description "Maximum number of routes in the message";
            }

            leaf metric-in {
                type types-ripng:metric;
                default "1";
                description "Metric added to routes received from the neighbor";
            }

            leaf metric-out {
                type types-ripng:metric;
                default "1";
                description "Metric added to routes exported into RIPng";
            }

            leaf preference {
                type types-ripng:preference;
                default "100";
                description "Route preference";
            }

            leaf receive {
                type types-ripng:receive;
                default "ripng";
                description "Accepted version on received packets";
            }

            leaf send {
                type enumeration {
                    enum none                           { value 1; }
                    enum ripng                          { value 5; }
                }
                default "ripng";
                description "RIPng version and method used to send RIPng updates";
            }

            leaf split-horizon {
                type boolean;
                default "true";
                description "Enable split horizon and poison reverse";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container export-limit {
                presence "Enable the export-limit context";
                description "Enable the export-limit context";

                leaf number {
                    type uint32 {
                        range "1..max";
                    }
                    mandatory true;
                    description "Maximum routes or prefixes exported from route table";
                }

                leaf log-percent {
                    type uint32 {
                        range "1..100";
                    }
                    description "Export limit before warning and SNMP notification sent";
                }

            } // container export-limit

            container timers {
                presence "Enable the timers context";
                description "Enable the timers context";

                leaf update {
                    type types-ripng:timer-update;
                    mandatory true;
                    description "Timer that controls the frequency of updates";
                }

                leaf timeout {
                    type types-ripng:timer-timeout;
                    mandatory true;
                    description "RIP timeout timer";
                }

                leaf flush {
                    type types-ripng:timer-flush;
                    mandatory true;
                    description "RIP flush timer";
                }

            } // container timers

            list group {
                key "group-name";
                description "Enter the group list instance";

                leaf group-name {
                    type types-sros:named-item;
                    description "RIP group name";
                }

                leaf admin-state {
                    type types-sros:admin-state;
                    default "enable";
                    description "Administrative state of RIPng neighbor interface group";
                }

                leaf description {
                    type types-sros:description;
                    description "Text description";
                }

                leaf-list export-policy {
                    type leafref {
                        path "../../../../policy-options/policy-statement/name";
                    }
                    max-elements 5;
                    ordered-by user;
                    description "Policies used to rule which routes are exported to RIP";
                }

                leaf-list import-policy {
                    type leafref {
                        path "../../../../policy-options/policy-statement/name";
                    }
                    max-elements 5;
                    ordered-by user;
                    description "Policies to decide routes accepted from RIP neighbors";
                }

                leaf bfd-liveness {
                    type boolean;
                    description "Enable BFD to control the state of protocol adjacency";
                }

                leaf check-zero {
                    type boolean;
                    description "Enable checking of mandatory zero fields";
                }

                leaf message-size {
                    type types-ripng:message-size;
                    description "Maximum number of routes in the message";
                }

                leaf metric-in {
                    type types-ripng:metric;
                    description "Metric added to routes received from the neighbor";
                }

                leaf metric-out {
                    type types-ripng:metric;
                    description "Metric added to routes exported into RIPng";
                }

                leaf preference {
                    type types-ripng:preference;
                    description "Route preference";
                }

                leaf receive {
                    type types-ripng:receive;
                    description "Accepted version on received packets";
                }

                leaf split-horizon {
                    type boolean;
                    description "Enable split horizon and poison reverse";
                }

                leaf send {
                    type enumeration {
                        enum none                           { value 1; }
                        enum ripng                          { value 5; }
                    }
                    description "RIPng version and method used to send RIPng updates";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container timers {
                    presence "Enable the timers context";
                    description "Enable the timers context";

                    leaf update {
                        type types-ripng:timer-update;
                        mandatory true;
                        description "Timer that controls the frequency of updates";
                    }

                    leaf timeout {
                        type types-ripng:timer-timeout;
                        mandatory true;
                        description "RIP timeout timer";
                    }

                    leaf flush {
                        type types-ripng:timer-flush;
                        mandatory true;
                        description "RIP flush timer";
                    }

                } // container timers

                list neighbor {
                    key "interface-name";
                    description "Enter the neighbor list instance";

                    leaf interface-name {
                        type types-sros:interface-name;
                        description "Neighbor added to the RIPng group through the interface";
                    }

                    leaf admin-state {
                        type types-sros:admin-state;
                        default "enable";
                        description "Administrative state of the RIPng neighbor";
                    }

                    leaf description {
                        type types-sros:description;
                        description "Text description";
                    }

                    leaf-list export-policy {
                        type leafref {
                            path "../../../../../policy-options/policy-statement/name";
                        }
                        max-elements 5;
                        ordered-by user;
                        description "Policies used to rule which routes are exported to RIP";
                    }

                    leaf-list import-policy {
                        type leafref {
                            path "../../../../../policy-options/policy-statement/name";
                        }
                        max-elements 5;
                        ordered-by user;
                        description "Policies to decide routes accepted from RIP neighbors";
                    }

                    leaf bfd-liveness {
                        type boolean;
                        description "Enable BFD to control the state of protocol adjacency";
                    }

                    leaf check-zero {
                        type boolean;
                        description "Enable checking of mandatory zero fields";
                    }

                    leaf message-size {
                        type types-ripng:message-size;
                        description "Maximum number of routes in the message";
                    }

                    leaf metric-in {
                        type types-ripng:metric;
                        description "Metric added to routes received from the neighbor";
                    }

                    leaf metric-out {
                        type types-ripng:metric;
                        description "Metric added to routes exported into RIPng";
                    }

                    leaf preference {
                        type types-ripng:preference;
                        description "Route preference";
                    }

                    leaf receive {
                        type types-ripng:receive;
                        description "Accepted version on received packets";
                    }

                    leaf split-horizon {
                        type boolean;
                        description "Enable split horizon and poison reverse";
                    }

                    leaf send {
                        type enumeration {
                            enum none                           { value 1; }
                            enum ripng                          { value 5; }
                            enum unicast                        { value 6; }
                        }
                        description "RIPng version and method used to send RIPng updates";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container timers {
                        presence "Enable the timers context";
                        description "Enable the timers context";

                        leaf update {
                            type types-ripng:timer-update;
                            mandatory true;
                            description "Timer that controls the frequency of updates";
                        }

                        leaf timeout {
                            type types-ripng:timer-timeout;
                            mandatory true;
                            description "RIP timeout timer";
                        }

                        leaf flush {
                            type types-ripng:timer-flush;
                            mandatory true;
                            description "RIP flush timer";
                        }

                    } // container timers

                    list unicast-address {
                        key "address";
                        description "Add a list entry for unicast-address";

                        leaf address {
                            type types-sros:ipv6-unicast-address;
                            description "Unicast address for the neighbor";
                        }

                    } // list unicast-address

                } // list neighbor

            } // list group

        } // container ripng

    } // grouping conf-router-ripng

}
