module nokia-sr-ietf-netconf-monitoring-deviations {

    yang-version "1.1";

    namespace "urn:nokia.com:sros:ns:yang:sr:ietf-netconf-monitoring-deviations";

    prefix "nokia-ncm-devs";

    import ietf-inet-types                { prefix "inet"; }
    import ietf-netconf-monitoring        { prefix "ncm"; }
    import nokia-sros-yang-extensions     { prefix "sros-ext"; }

    sros-ext:sros-major-release "rel25";
    organization "Nokia";
    contact
        "Nokia SR OS Support
         Web: <http://www.nokia.com>";
    description
        "This module contains the list of deviations against the ietf-netconf-monitoring
         module for the Nokia SR OS based routers.

         Copyright 2016 Nokia. All rights reserved. Reproduction of this document
         is authorized on the condition that the foregoing copyright notice is included.

         This nokia-sr-ietf-netconf-monitoring-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    typedef sr-netconf-datastore-type {
        type enumeration {
            enum running                        { value 0; }
            enum candidate                      { value 1; }
            enum startup                        { value 2; }
            enum intended                       { value 3; }
            enum operational                    { value 4; }
            enum configure-running              { value 5; }
            enum configure-candidate            { value 6; }
            enum configure-startup              { value 7; }
            enum configure-intended             { value 8; }
            enum configure-operational          { value 9; }
            enum li-running                     { value 10; }
            enum li-candidate                   { value 11; }
            enum li-startup                     { value 12; }
            enum li-intended                    { value 13; }
            enum bof-running                    { value 14; }
            enum bof-candidate                  { value 15; }
            enum bof-startup                    { value 16; }
            enum bof-intended                   { value 17; }
            enum debug-running                  { value 18; }
            enum debug-candidate                { value 19; }
        }
        description
            "Enumeration of possible NETCONF datastore types based on netconf-datastore-type
             extended with proprietary datastores.";
    }

    deviation /ncm:netconf-state/ncm:capabilities/ncm:capability {
        description "Maximum number of capabilities is 256.";
        deviate add {
            max-elements 256;
        }
    }

    deviation /ncm:netconf-state/ncm:datastores/ncm:datastore/ncm:name {
        description "Type of name is sr-netconf-datastore-type.";
        deviate replace {
            type nokia-ncm-devs:sr-netconf-datastore-type;
        }
    }

    deviation /ncm:netconf-state/ncm:datastores/ncm:datastore/ncm:locks/ncm:lock-type/ncm:partial-lock {
        description "partial-lock subtree is not supported.";
        deviate not-supported;
    }

    deviation /ncm:netconf-state/ncm:schemas/ncm:schema/ncm:identifier {
        description "Maximum length of identifier is 64 characters.";
        deviate replace {
            type string {
                length "0..64";
            }
        }
    }

    deviation /ncm:netconf-state/ncm:schemas/ncm:schema/ncm:version {
        description "Maximum length of version is 16 characters.";
        deviate replace {
            type string {
                length "0..16";
            }
        }
    }

    deviation /ncm:netconf-state/ncm:schemas/ncm:schema/ncm:namespace {
        description "Maximum length of namespace is 96 characters.";
        deviate replace {
            type inet:uri {
                length "0..96";
            }
        }
    }

    deviation /ncm:netconf-state/ncm:sessions/ncm:session/ncm:username {
        description "Maximum length of username is 32 characters.";
        deviate replace {
            type string {
                length "0..32";
            }
        }
    }

}
