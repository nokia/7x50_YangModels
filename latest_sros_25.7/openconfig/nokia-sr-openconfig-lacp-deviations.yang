module nokia-sr-openconfig-lacp-deviations {

    namespace "urn:nokia.com:sros:ns:yang:sr:openconfig-lacp-deviations";

    prefix "nokia-oc-lacp-devs";

    import nokia-sros-yang-extensions     { prefix "sros-ext"; }
    import openconfig-lacp                { prefix "oc-lacp"; }

    sros-ext:sros-major-release "rel25";
    organization "Nokia";
    contact
        "Nokia SR OS Support
         Web: <http://www.nokia.com>";
    description
        "This module contains the list of deviations against the openconfig-lacp
         module for the Nokia SR OS based routers.

         Copyright 2016 Nokia. All rights reserved. Reproduction of this document
         is authorized on the condition that the foregoing copyright notice is included.

         This nokia-sr-openconfig-lacp-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-07-16";

    deviation /oc-lacp:lacp/oc-lacp:config/oc-lacp:system-priority {
        deviate replace {
            type uint16 {
                range "0..65535";
            }
        }
        deviate add {
            default "32768";
        }
    }

    deviation /oc-lacp:lacp/oc-lacp:state/oc-lacp:system-priority {
        deviate replace {
            type uint16 {
                range "0..65535";
            }
        }
        deviate add {
            default "32768";
        }
    }

    deviation /oc-lacp:lacp/oc-lacp:interfaces/oc-lacp:interface/oc-lacp:config/oc-lacp:system-priority {
        deviate replace {
            type uint16 {
                range "0..65535";
            }
        }
        deviate add {
            default "32768";
        }
    }

    deviation /oc-lacp:lacp/oc-lacp:interfaces/oc-lacp:interface/oc-lacp:state/oc-lacp:system-priority {
        deviate replace {
            type uint16 {
                range "0..65535";
            }
        }
        deviate add {
            default "32768";
        }
    }

    deviation /oc-lacp:lacp/oc-lacp:interfaces/oc-lacp:interface/oc-lacp:members/oc-lacp:member/oc-lacp:config/oc-lacp:port-priority {
        deviate replace {
            type uint16 {
                range "0..65535";
            }
        }
        deviate add {
            default "32768";
        }
    }

    deviation /oc-lacp:lacp/oc-lacp:interfaces/oc-lacp:interface/oc-lacp:members/oc-lacp:member/oc-lacp:state/oc-lacp:port-priority {
        deviate replace {
            type uint16 {
                range "0..65535";
            }
        }
        deviate add {
            default "32768";
        }
    }

    deviation /oc-lacp:lacp/oc-lacp:interfaces/oc-lacp:interface/oc-lacp:members/oc-lacp:member/oc-lacp:state/oc-lacp:last-change {
        deviate not-supported;
    }

    deviation /oc-lacp:lacp/oc-lacp:interfaces/oc-lacp:interface/oc-lacp:members/oc-lacp:member/oc-lacp:state/oc-lacp:counters/oc-lacp:lacp-timeout-transitions {
        deviate not-supported;
    }

}
