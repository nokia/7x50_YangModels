module nokia-sr-openconfig-if-ip-ext-deviations {

    namespace "urn:nokia.com:sros:ns:yang:sr:openconfig-if-ip-ext-deviations";

    prefix "nokia-oc-ip-ext-devs";

    import nokia-sros-yang-extensions     { prefix "sros-ext"; }
    import openconfig-if-ip               { prefix "oc-ip"; }
    import openconfig-if-ip-ext           { prefix "oc-ip-ext"; }
    import openconfig-interfaces          { prefix "oc-if"; }

    sros-ext:sros-major-release "rel25";
    organization "Nokia";
    contact
        "Nokia SR OS Support
         Web: <http://www.nokia.com>";
    description
        "This module contains the list of deviations against the openconfig-if-ip-ext
         module for the Nokia SR OS based routers.

         Copyright 2016 Nokia. All rights reserved. Reproduction of this document
         is authorized on the condition that the foregoing copyright notice is included.

         This nokia-sr-openconfig-if-ip-ext-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    deviation /oc-if:interfaces/oc-if:interface/oc-if:subinterfaces/oc-if:subinterface/oc-ip:ipv6/oc-ip-ext:autoconf {
        deviate not-supported;
    }

}
