module nokia-sr-openconfig-platform-fan-deviations {

    namespace "urn:nokia.com:sros:ns:yang:sr:openconfig-platform-fan-deviations";

    prefix "nokia-oc-fan-devs";

    import nokia-sros-yang-extensions     { prefix "sros-ext"; }
    import openconfig-platform            { prefix "oc-platform"; }
    import openconfig-platform-fan        { prefix "oc-fan"; }

    sros-ext:sros-major-release "rel25";
    organization "Nokia";
    contact
        "Nokia SR OS Support
         Web: <http://www.nokia.com>";
    description
        "This module contains the list of deviations against the openconfig-platform-fan
         module for the Nokia SR OS based routers.

         Copyright 2016 Nokia. All rights reserved. Reproduction of this document
         is authorized on the condition that the foregoing copyright notice is included.

         This nokia-sr-openconfig-platform-fan-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    deviation /oc-platform:components/oc-platform:component/oc-platform:fan/oc-platform:state/oc-fan:speed {
        deviate not-supported;
    }

}
