module nokia-types-dms {

    yang-version "1.1";

    namespace "urn:nokia.com:sros:ns:yang:sr:types-dms";

    prefix "types-dms";

    import nokia-sros-yang-extensions     { prefix "sros-ext"; }

    sros-ext:sros-major-release "rel25";
    organization "Nokia";
    contact
        "Nokia SR OS Support
         Web: <http://www.nokia.com>";
    description
        "Common defender mitigation system data types used in the SR OS management system.

         Copyright 2016 Nokia. All rights reserved. Reproduction of this document
         is authorized on the condition that the foregoing copyright notice is included.

         This nokia-types-dms YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-07-16";

    typedef genome-list {
        type enumeration {
            enum botnet {
                value 1;
                description "IP addresses belonging to known botnets";
            }
            enum country-abw {
                value 2;
                description "Country: Aruba";
            }
            enum country-afg {
                value 3;
                description "Country: Afghanistan";
            }
            enum country-ago {
                value 4;
                description "Country: Angola";
            }
            enum country-aia {
                value 5;
                description "Country: Anguilla";
            }
            enum country-ala {
                value 6;
                description "Country: Aland Islands";
            }
            enum country-alb {
                value 7;
                description "Country: Albania";
            }
            enum country-and {
                value 8;
                description "Country: Andorra";
            }
            enum country-are {
                value 9;
                description "Country: United Arab Emirates";
            }
            enum country-arg {
                value 10;
                description "Country: Argentina";
            }
            enum country-arm {
                value 11;
                description "Country: Armenia";
            }
            enum country-asm {
                value 12;
                description "Country: American Samoa";
            }
            enum country-ata {
                value 13;
                description "Country: Antarctica";
            }
            enum country-atf {
                value 14;
                description "Country: French Southern Territories";
            }
            enum country-atg {
                value 15;
                description "Country: Antigua and Barbuda";
            }
            enum country-aus {
                value 16;
                description "Country: Australia";
            }
            enum country-aut {
                value 17;
                description "Country: Austria";
            }
            enum country-aze {
                value 18;
                description "Country: Azerbaijan";
            }
            enum country-bdi {
                value 19;
                description "Country: Burundi";
            }
            enum country-bel {
                value 20;
                description "Country: Belgium";
            }
            enum country-ben {
                value 21;
                description "Country: Benin";
            }
            enum country-bes {
                value 22;
                description "Country: Bonaire, Sint Eustatius and Saba";
            }
            enum country-bfa {
                value 23;
                description "Country: Burkina Faso";
            }
            enum country-bgd {
                value 24;
                description "Country: Bangladesh";
            }
            enum country-bgr {
                value 25;
                description "Country: Bulgaria";
            }
            enum country-bhr {
                value 26;
                description "Country: Bahrain";
            }
            enum country-bhs {
                value 27;
                description "Country: Bahamas";
            }
            enum country-bih {
                value 28;
                description "Country: Bosnia and Herzegovina";
            }
            enum country-blm {
                value 29;
                description "Country: Saint Barthelemy";
            }
            enum country-blr {
                value 30;
                description "Country: Belarus";
            }
            enum country-blz {
                value 31;
                description "Country: Belize";
            }
            enum country-bmu {
                value 32;
                description "Country: Bermuda";
            }
            enum country-bol {
                value 33;
                description "Country: Bolivia, Plurinational State of";
            }
            enum country-bra {
                value 34;
                description "Country: Brazil";
            }
            enum country-brb {
                value 35;
                description "Country: Barbados";
            }
            enum country-brn {
                value 36;
                description "Country: Brunei Darussalam";
            }
            enum country-btn {
                value 37;
                description "Country: Bhutan";
            }
            enum country-bwa {
                value 38;
                description "Country: Botswana";
            }
            enum country-caf {
                value 39;
                description "Country: Central African Republic";
            }
            enum country-can {
                value 40;
                description "Country: Canada";
            }
            enum country-cck {
                value 41;
                description "Country: Cocos (Keeling) Islands";
            }
            enum country-che {
                value 42;
                description "Country: Switzerland";
            }
            enum country-chl {
                value 43;
                description "Country: Chile";
            }
            enum country-chn {
                value 44;
                description "Country: China";
            }
            enum country-civ {
                value 45;
                description "Country: Cote dIvoire";
            }
            enum country-cmr {
                value 46;
                description "Country: Cameroon";
            }
            enum country-cod {
                value 47;
                description "Country: Congo, Democratic Republic of the (Kinshasa)";
            }
            enum country-cog {
                value 48;
                description "Country: Congo (Brazzaville)";
            }
            enum country-cok {
                value 49;
                description "Country: Cook Islands";
            }
            enum country-col {
                value 50;
                description "Country: Colombia";
            }
            enum country-com {
                value 51;
                description "Country: Comoros";
            }
            enum country-cpv {
                value 52;
                description "Country: Cabo Verde";
            }
            enum country-cri {
                value 53;
                description "Country: Costa Rica";
            }
            enum country-cub {
                value 54;
                description "Country: Cuba";
            }
            enum country-cuw {
                value 55;
                description "Country: Curacao";
            }
            enum country-cxr {
                value 56;
                description "Country: Christmas Island";
            }
            enum country-cym {
                value 57;
                description "Country: Cayman Islands";
            }
            enum country-cyp {
                value 58;
                description "Country: Cyprus";
            }
            enum country-cze {
                value 59;
                description "Country: Czech Republic (Czechia)";
            }
            enum country-deu {
                value 60;
                description "Country: Germany";
            }
            enum country-dji {
                value 61;
                description "Country: Djibouti";
            }
            enum country-dma {
                value 62;
                description "Country: Dominica";
            }
            enum country-dnk {
                value 63;
                description "Country: Denmark";
            }
            enum country-dom {
                value 64;
                description "Country: Dominican Republic";
            }
            enum country-dza {
                value 65;
                description "Country: Algeria";
            }
            enum country-ecu {
                value 66;
                description "Country: Ecuador";
            }
            enum country-egy {
                value 67;
                description "Country: Egypt";
            }
            enum country-eri {
                value 68;
                description "Country: Eritrea";
            }
            enum country-esp {
                value 69;
                description "Country: Spain";
            }
            enum country-est {
                value 70;
                description "Country: Estonia";
            }
            enum country-eth {
                value 71;
                description "Country: Ethiopia";
            }
            enum country-fin {
                value 72;
                description "Country: Finland";
            }
            enum country-fji {
                value 73;
                description "Country: Fiji";
            }
            enum country-flk {
                value 74;
                description "Country: Falkland Islands (Malvinas)";
            }
            enum country-fra {
                value 75;
                description "Country: France";
            }
            enum country-fro {
                value 76;
                description "Country: Faroe Islands";
            }
            enum country-fsm {
                value 77;
                description "Country: Micronesia, Federated States of";
            }
            enum country-gab {
                value 78;
                description "Country: Gabon";
            }
            enum country-gbr {
                value 79;
                description "Country: United Kingdom of Great Britain and Northern Ireland";
            }
            enum country-geo {
                value 80;
                description "Country: Georgia";
            }
            enum country-ggy {
                value 81;
                description "Country: Guernsey";
            }
            enum country-gha {
                value 82;
                description "Country: Ghana";
            }
            enum country-gib {
                value 83;
                description "Country: Gibraltar";
            }
            enum country-gin {
                value 84;
                description "Country: Guinea";
            }
            enum country-glp {
                value 85;
                description "Country: Guadeloupe";
            }
            enum country-gmb {
                value 86;
                description "Country: Gambia";
            }
            enum country-gnb {
                value 87;
                description "Country: Guinea-Bissau";
            }
            enum country-gnq {
                value 88;
                description "Country: Equatorial Guinea";
            }
            enum country-grc {
                value 89;
                description "Country: Greece";
            }
            enum country-grd {
                value 90;
                description "Country: Grenada";
            }
            enum country-grl {
                value 91;
                description "Country: Greenland";
            }
            enum country-gtm {
                value 92;
                description "Country: Guatemala";
            }
            enum country-guf {
                value 93;
                description "Country: French Guiana";
            }
            enum country-gum {
                value 94;
                description "Country: Guam";
            }
            enum country-guy {
                value 95;
                description "Country: Guyana";
            }
            enum country-hkg {
                value 96;
                description "Country: Hong Kong (SAR China)";
            }
            enum country-hnd {
                value 97;
                description "Country: Honduras";
            }
            enum country-hrv {
                value 98;
                description "Country: Croatia";
            }
            enum country-hti {
                value 99;
                description "Country: Haiti";
            }
            enum country-hun {
                value 100;
                description "Country: Hungary";
            }
            enum country-idn {
                value 101;
                description "Country: Indonesia";
            }
            enum country-imn {
                value 102;
                description "Country: Isle of Man";
            }
            enum country-ind {
                value 103;
                description "Country: India";
            }
            enum country-iot {
                value 104;
                description "Country: British Indian Ocean Territory";
            }
            enum country-irl {
                value 105;
                description "Country: Ireland";
            }
            enum country-irn {
                value 106;
                description "Country: Iran, Islamic Republic of";
            }
            enum country-irq {
                value 107;
                description "Country: Iraq";
            }
            enum country-isl {
                value 108;
                description "Country: Iceland";
            }
            enum country-isr {
                value 109;
                description "Country: Israel";
            }
            enum country-ita {
                value 110;
                description "Country: Italy";
            }
            enum country-jam {
                value 111;
                description "Country: Jamaica";
            }
            enum country-jey {
                value 112;
                description "Country: Jersey";
            }
            enum country-jor {
                value 113;
                description "Country: Jordan";
            }
            enum country-jpn {
                value 114;
                description "Country: Japan";
            }
            enum country-kaz {
                value 115;
                description "Country: Kazakhstan";
            }
            enum country-ken {
                value 116;
                description "Country: Kenya";
            }
            enum country-kgz {
                value 117;
                description "Country: Kyrgyzstan";
            }
            enum country-khm {
                value 118;
                description "Country: Cambodia";
            }
            enum country-kir {
                value 119;
                description "Country: Kiribati";
            }
            enum country-kna {
                value 120;
                description "Country: Saint Kitts and Nevis";
            }
            enum country-kor {
                value 121;
                description "Country: Korea, Republic of (South)";
            }
            enum country-kwt {
                value 122;
                description "Country: Kuwait";
            }
            enum country-lao {
                value 123;
                description "Country: Lao Peoples Democratic Republic";
            }
            enum country-lbn {
                value 124;
                description "Country: Lebanon";
            }
            enum country-lbr {
                value 125;
                description "Country: Liberia";
            }
            enum country-lby {
                value 126;
                description "Country: Libya";
            }
            enum country-lca {
                value 127;
                description "Country: Saint Lucia";
            }
            enum country-lie {
                value 128;
                description "Country: Liechtenstein";
            }
            enum country-lka {
                value 129;
                description "Country: Sri Lanka";
            }
            enum country-lso {
                value 130;
                description "Country: Lesotho";
            }
            enum country-ltu {
                value 131;
                description "Country: Lithuania";
            }
            enum country-lux {
                value 132;
                description "Country: Luxembourg";
            }
            enum country-lva {
                value 133;
                description "Country: Latvia";
            }
            enum country-mac {
                value 134;
                description "Country: Macao, SAR China";
            }
            enum country-maf {
                value 135;
                description "Country: Saint-Martin (French part)";
            }
            enum country-mar {
                value 136;
                description "Country: Morocco";
            }
            enum country-mco {
                value 137;
                description "Country: Monaco";
            }
            enum country-mda {
                value 138;
                description "Country: Moldova, Republic of";
            }
            enum country-mdg {
                value 139;
                description "Country: Madagascar";
            }
            enum country-mdv {
                value 140;
                description "Country: Maldives";
            }
            enum country-mex {
                value 141;
                description "Country: Mexico";
            }
            enum country-mhl {
                value 142;
                description "Country: Marshall Islands";
            }
            enum country-mkd {
                value 143;
                description "Country: North Macedonia, Republic of";
            }
            enum country-mli {
                value 144;
                description "Country: Mali";
            }
            enum country-mlt {
                value 145;
                description "Country: Malta";
            }
            enum country-mmr {
                value 146;
                description "Country: Myanmar";
            }
            enum country-mne {
                value 147;
                description "Country: Montenegro";
            }
            enum country-mng {
                value 148;
                description "Country: Mongolia";
            }
            enum country-mnp {
                value 149;
                description "Country: Northern Mariana Islands";
            }
            enum country-moz {
                value 150;
                description "Country: Mozambique";
            }
            enum country-mrt {
                value 151;
                description "Country: Mauritania";
            }
            enum country-msr {
                value 152;
                description "Country: Montserrat";
            }
            enum country-mtq {
                value 153;
                description "Country: Martinique";
            }
            enum country-mus {
                value 154;
                description "Country: Mauritius";
            }
            enum country-mwi {
                value 155;
                description "Country: Malawi";
            }
            enum country-mys {
                value 156;
                description "Country: Malaysia";
            }
            enum country-myt {
                value 157;
                description "Country: Mayotte";
            }
            enum country-nam {
                value 158;
                description "Country: Namibia";
            }
            enum country-ncl {
                value 159;
                description "Country: New Caledonia";
            }
            enum country-ner {
                value 160;
                description "Country: Niger";
            }
            enum country-nfk {
                value 161;
                description "Country: Norfolk Island";
            }
            enum country-nga {
                value 162;
                description "Country: Nigeria";
            }
            enum country-nic {
                value 163;
                description "Country: Nicaragua";
            }
            enum country-niu {
                value 164;
                description "Country: Niue";
            }
            enum country-nld {
                value 165;
                description "Country: Netherlands, Kingdom of the";
            }
            enum country-nor {
                value 166;
                description "Country: Norway";
            }
            enum country-npl {
                value 167;
                description "Country: Nepal";
            }
            enum country-nru {
                value 168;
                description "Country: Nauru";
            }
            enum country-nzl {
                value 169;
                description "Country: New Zealand";
            }
            enum country-omn {
                value 170;
                description "Country: Oman";
            }
            enum country-pak {
                value 171;
                description "Country: Pakistan";
            }
            enum country-pan {
                value 172;
                description "Country: Panama";
            }
            enum country-pcn {
                value 173;
                description "Country: Pitcairn";
            }
            enum country-per {
                value 174;
                description "Country: Peru";
            }
            enum country-phl {
                value 175;
                description "Country: Philippines";
            }
            enum country-plw {
                value 176;
                description "Country: Palau";
            }
            enum country-png {
                value 177;
                description "Country: Papua New Guinea";
            }
            enum country-pol {
                value 178;
                description "Country: Poland";
            }
            enum country-pri {
                value 179;
                description "Country: Puerto Rico";
            }
            enum country-prk {
                value 180;
                description "Country: Korea, Democratic Peoples Republic of (North)";
            }
            enum country-prt {
                value 181;
                description "Country: Portugal";
            }
            enum country-pry {
                value 182;
                description "Country: Paraguay";
            }
            enum country-pse {
                value 183;
                description "Country: Palestine, State of";
            }
            enum country-pyf {
                value 184;
                description "Country: French Polynesia";
            }
            enum country-qat {
                value 185;
                description "Country: Qatar";
            }
            enum country-reu {
                value 186;
                description "Country: Reunion";
            }
            enum country-rou {
                value 187;
                description "Country: Romania";
            }
            enum country-rus {
                value 188;
                description "Country: Russian Federation";
            }
            enum country-rwa {
                value 189;
                description "Country: Rwanda";
            }
            enum country-sau {
                value 190;
                description "Country: Saudi Arabia";
            }
            enum country-sdn {
                value 191;
                description "Country: Sudan";
            }
            enum country-sen {
                value 192;
                description "Country: Senegal";
            }
            enum country-sgp {
                value 193;
                description "Country: Singapore";
            }
            enum country-sgs {
                value 194;
                description "Country: South Georgia and the South Sandwich Islands";
            }
            enum country-shn {
                value 195;
                description "Country: Saint Helena, Ascension and Tristan da Cunha";
            }
            enum country-sjm {
                value 196;
                description "Country: Svalbard and Jan Mayen";
            }
            enum country-slb {
                value 197;
                description "Country: Solomon Islands";
            }
            enum country-sle {
                value 198;
                description "Country: Sierra Leone";
            }
            enum country-slv {
                value 199;
                description "Country: El Salvador";
            }
            enum country-smr {
                value 200;
                description "Country: San Marino";
            }
            enum country-som {
                value 201;
                description "Country: Somalia";
            }
            enum country-spm {
                value 202;
                description "Country: Saint Pierre and Miquelon";
            }
            enum country-srb {
                value 203;
                description "Country: Serbia";
            }
            enum country-ssd {
                value 204;
                description "Country: South Sudan";
            }
            enum country-stp {
                value 205;
                description "Country: Sao Tome and Principe";
            }
            enum country-sur {
                value 206;
                description "Country: Suriname";
            }
            enum country-svk {
                value 207;
                description "Country: Slovakia";
            }
            enum country-svn {
                value 208;
                description "Country: Slovenia";
            }
            enum country-swe {
                value 209;
                description "Country: Sweden";
            }
            enum country-swz {
                value 210;
                description "Country: Eswatini (Swaziland)";
            }
            enum country-sxm {
                value 211;
                description "Country: Sint Maarten (Dutch part)";
            }
            enum country-syc {
                value 212;
                description "Country: Seychelles";
            }
            enum country-syr {
                value 213;
                description "Country: Syrian Arab Republic (Syria)";
            }
            enum country-tca {
                value 214;
                description "Country: Turks and Caicos Islands";
            }
            enum country-tcd {
                value 215;
                description "Country: Chad";
            }
            enum country-tgo {
                value 216;
                description "Country: Togo";
            }
            enum country-tha {
                value 217;
                description "Country: Thailand";
            }
            enum country-tjk {
                value 218;
                description "Country: Tajikistan";
            }
            enum country-tkl {
                value 219;
                description "Country: Tokelau";
            }
            enum country-tkm {
                value 220;
                description "Country: Turkmenistan";
            }
            enum country-tls {
                value 221;
                description "Country: Timor-Leste";
            }
            enum country-ton {
                value 222;
                description "Country: Tonga";
            }
            enum country-tto {
                value 223;
                description "Country: Trinidad and Tobago";
            }
            enum country-tun {
                value 224;
                description "Country: Tunisia";
            }
            enum country-tur {
                value 225;
                description "Country: Turkiye, Republic of (Turkey)";
            }
            enum country-tuv {
                value 226;
                description "Country: Tuvalu";
            }
            enum country-twn {
                value 227;
                description "Country: Taiwan, Republic of China";
            }
            enum country-tza {
                value 228;
                description "Country: Tanzania, United Republic of";
            }
            enum country-uga {
                value 229;
                description "Country: Uganda";
            }
            enum country-ukr {
                value 230;
                description "Country: Ukraine";
            }
            enum country-umi {
                value 231;
                description "Country: United States Minor Outlying Islands";
            }
            enum country-ury {
                value 232;
                description "Country: Uruguay";
            }
            enum country-usa {
                value 233;
                description "Country: United States of America";
            }
            enum country-uzb {
                value 234;
                description "Country: Uzbekistan";
            }
            enum country-vat {
                value 235;
                description "Country: Holy See (Vatican City)";
            }
            enum country-vct {
                value 236;
                description "Country: Saint Vincent and the Grenadines";
            }
            enum country-ven {
                value 237;
                description "Country: Venezuela, Bolivarian Republic of";
            }
            enum country-vgb {
                value 238;
                description "Country: Virgin Islands (British)";
            }
            enum country-vir {
                value 239;
                description "Country: Virgin Islands of the United States";
            }
            enum country-vnm {
                value 240;
                description "Country: Viet Nam";
            }
            enum country-vut {
                value 241;
                description "Country: Vanuatu";
            }
            enum country-wlf {
                value 242;
                description "Country: Wallis and Futuna Islands, Territory of the";
            }
            enum country-wsm {
                value 243;
                description "Country: Samoa";
            }
            enum country-yem {
                value 244;
                description "Country: Yemen";
            }
            enum country-zaf {
                value 245;
                description "Country: South Africa";
            }
            enum country-zmb {
                value 246;
                description "Country: Zambia";
            }
            enum country-zwe {
                value 247;
                description "Country: Zimbabwe";
            }
            enum cdn-akamai {
                value 248;
                description "CDN: akamai";
            }
            enum cdn-google {
                value 249;
                description "CDN: google";
            }
            enum cdn-cloudfront {
                value 250;
                description "CDN: cloudfront";
            }
            enum cdn-netflix {
                value 251;
                description "CDN: netflix";
            }
            enum cdn-fastly {
                value 252;
                description "CDN: fastly";
            }
            enum cdn-facebook {
                value 253;
                description "CDN: facebook";
            }
            enum cdn-apple {
                value 254;
                description "CDN: apple";
            }
            enum cdn-edgio {
                value 255;
                description "CDN: edgio";
            }
            enum cdn-disney {
                value 256;
                description "CDN: disney";
            }
            enum cdn-bytedance {
                value 257;
                description "CDN: bytedance";
            }
            enum cdn-cloudflare {
                value 258;
                description "CDN: cloudflare";
            }
            enum cdn-cdn77 {
                value 259;
                description "CDN: cdn77";
            }
            enum cdn-qwilt {
                value 260;
                description "CDN: qwilt";
            }
            enum cdn-microsoft {
                value 261;
                description "CDN: microsoft";
            }
            enum cdn-cachefly {
                value 262;
                description "CDN: cachefly";
            }
            enum cdn-alibaba {
                value 263;
                description "CDN: alibaba";
            }
        }
        description "DMS protected object genome lists.";
    }

    typedef dms-deployment-model {
        type enumeration {
            enum off-ramp                       { value 0; }
            enum inline                         { value 1; }
        }
        description "DMS advanced counter-measures group network deployment model.";
    }

    typedef esa-vm-oper-flags-type {
        type bits {
            bit esa-vm-down                    { position 0; }
            bit group-admin-down               { position 1; }
            bit config-in-progress             { position 2; }
            bit pxc-down                       { position 3; }
        }
        description "DMS advanced counter-measures group esa-vm failure types.";
    }

    typedef genome-list-import-conditions-type {
        type bits {
            bit admin-down                     { position 0; }
            bit http-client-prof-error         { position 1; }
            bit http-client-url-open-failed    { position 2; }
            bit http-client-read-failed        { position 3; }
            bit json-parsing-error             { position 4; }
            bit json-version-error             { position 5; }
            bit json-tags-error                { position 6; }
            bit json-no-extracted-ips          { position 7; }
            bit ipv4-prefix-limit-exceeded     { position 8; }
            bit ipv6-prefix-limit-exceeded     { position 9; }
            bit ipv4-addr-limit-exceeded       { position 10; }
            bit http-client-file-too-large     { position 11; }
            bit ipv6-addr-limit-exceeded       { position 12; }
        }
        description "Genome list import condition types.";
    }

    typedef match-operator {
        type enumeration {
            enum eq                             { value 1; }
            enum neq                            { value 2; }
        }
    }

    typedef pre-filter-action {
        type enumeration {
            enum deny {
                value 1;
                description "Drop all traffic from the source IPs in the list";
            }
            enum bypass {
                value 2;
                description "Admit traffic and bypass mitigation rules";
            }
        }
        description "Actions to take during DMS pre-filtering";
    }

    typedef policer-event-count {
        type union {
            type int32 {
                range "1..8000000";
            }
            type enumeration {
                enum max {
                    value -1;
                    description "Disable the event count limit";
                }
            }
        }
        default "max";
        description "DMS policer event count limit. The value 'max' means unbounded.";
    }

    typedef policer-event-burst-size {
        type int32 {
            range "0..131071";
        }
        units "packets";
        default "0";
        description "The amount of event burst capacity assigned to a policer.";
    }

    typedef policer-event-rate {
        type union {
            type int32 {
                range "1..262143";
            }
            type enumeration {
                enum max {
                    value -1;
                    description "Disable the event rate limit";
                }
            }
        }
        units "packets per second";
        default "max";
        description "DMS policer event rate in event per seconds. The value 'max' means unbounded.";
    }

    typedef policer-flow-count {
        type union {
            type int32 {
                range "1..8000000";
            }
            type enumeration {
                enum max {
                    value -1;
                    description "Disable the flow count limit";
                }
            }
        }
        units "flows";
        default "max";
        description "DMS policer flow count limit. The value 'max' means unbounded.";
    }

    typedef policer-flow-setup-rate {
        type union {
            type int32 {
                range "1..262143";
            }
            type enumeration {
                enum max {
                    value -1;
                    description "Disable the flow-setup-rate limit";
                }
            }
        }
        units "flows per second";
        default "max";
        description "DMS policer flow setup rate in flows per seconds. The value 'max' means unbounded.";
    }

    typedef policer-flow-burst-size {
        type int32 {
            range "0..131071";
        }
        units "flows";
        default "0";
        description "The amount of flow burst capacity assigned to a policer.";
    }

    typedef user-list-import-conditions-type {
        type bits {
            bit admin-down                     { position 0; }
            bit http-client-prof-error         { position 1; }
            bit http-client-url-open-failed    { position 2; }
            bit http-client-read-failed        { position 3; }
            bit json-parsing-error             { position 4; }
            bit json-version-error             { position 5; }
            bit json-tags-error                { position 6; }
            bit json-no-extracted-lists        { position 7; }
            bit http-client-file-too-large     { position 8; }
            bit too-many-lists                 { position 9; }
            bit too-many-strings               { position 10; }
            bit too-many-strings-per-list      { position 11; }
            bit dns-list-name-length-invalid   { position 12; }
            bit query-string-too-long          { position 13; }
            bit query-string-invalid           { position 14; }
            bit no-strings-in-list             { position 15; }
        }
        description "User list import condition types.";
    }

    typedef dns-filter-oper-flags-type {
        type bits {
            bit admin-down                     { position 0; }
            bit changes-in-progress            { position 1; }
            bit dns-list-exceeded-resources    { position 2; }
            bit dns-list-nested-wildcard       { position 3; }
            bit dns-list-not-found             { position 4; }
            bit dns-list-repeated-fqdn         { position 5; }
        }
        description "DNS filter operating status condition types.";
    }

    typedef resource-usage-status-type {
        type enumeration {
            enum unknown                        { value 0; }
            enum normal                         { value 1; }
            enum warning {
                value 2;
                description "resource records in-use have exceeded the warning threshold.";
            }
            enum severe {
                value 3;
                description "resource records in-use have exceeded the severe threshold.";
            }
        }
        description "The levels of resource records in use.";
    }

    typedef dns-record-type {
        type union {
            type int32 {
                range "1..65534";
            }
            type enumeration {
                enum a                              { value 1; }
                enum ns                             { value 2; }
                enum cname                          { value 5; }
                enum soa                            { value 6; }
                enum wks                            { value 11; }
                enum ptr                            { value 12; }
                enum hinfo                          { value 13; }
                enum minfo                          { value 14; }
                enum mx                             { value 15; }
                enum txt                            { value 16; }
                enum rp                             { value 17; }
                enum afsdb                          { value 18; }
                enum x25                            { value 19; }
                enum isdn                           { value 20; }
                enum rt                             { value 21; }
                enum sig                            { value 24; }
                enum key                            { value 25; }
                enum px                             { value 26; }
                enum gpos                           { value 27; }
                enum aaaa                           { value 28; }
                enum loc                            { value 29; }
                enum eid                            { value 31; }
                enum nimloc                         { value 32; }
                enum srv                            { value 33; }
                enum naptr                          { value 35; }
                enum kx                             { value 36; }
                enum cert                           { value 37; }
                enum dname                          { value 39; }
                enum sink                           { value 40; }
                enum opt                            { value 41; }
                enum apl                            { value 42; }
                enum ds                             { value 43; }
                enum sshfp                          { value 44; }
                enum ipseckey                       { value 45; }
                enum rrsig                          { value 46; }
                enum nsec                           { value 47; }
                enum dnskey                         { value 48; }
                enum dhcid                          { value 49; }
                enum nsec3                          { value 50; }
                enum nsec3param                     { value 51; }
                enum tlsa                           { value 52; }
                enum smimea                         { value 53; }
                enum hip                            { value 55; }
                enum cds                            { value 59; }
                enum cdnskey                        { value 60; }
                enum openpgpkey                     { value 61; }
                enum csync                          { value 62; }
                enum zonemd                         { value 63; }
                enum svcb                           { value 64; }
                enum https                          { value 65; }
                enum spf                            { value 99; }
                enum nid                            { value 104; }
                enum l32                            { value 105; }
                enum l64                            { value 106; }
                enum lp                             { value 107; }
                enum eui48                          { value 108; }
                enum eui64                          { value 109; }
                enum tkey                           { value 249; }
                enum tsig                           { value 250; }
                enum ixfr                           { value 251; }
                enum axfr                           { value 252; }
                enum mailb                          { value 253; }
                enum maila                          { value 254; }
                enum uri                            { value 256; }
                enum caa                            { value 257; }
                enum ta                             { value 32768; }
                enum dlv                            { value 32769; }
            }
        }
        description
            "DNS query record type. Well known record types include A(1),
             AAAA(28), MX(15).";
    }

}
