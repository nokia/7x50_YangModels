submodule nokia-state-router-wpp {

    yang-version "1.1";

    belongs-to nokia-state { prefix "state"; }

    import ietf-inet-types                { prefix "inet"; }
    import ietf-yang-types                { prefix "yang"; }
    import nokia-sros-yang-extensions     { prefix "sros-ext"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for wpp on SR OS based routers.

         Copyright 2016 Nokia. All rights reserved. Reproduction of this document
         is authorized on the condition that the foregoing copyright notice is included.

         This nokia-state-router-wpp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-router-wpp {
        container wpp {
            description "Enable the wpp context";

            list portal {
                key "name";
                description "Enter the portal list instance";

                leaf name {
                    type types-sros:named-item;
                    description "Web portal name";
                }

                leaf controlled-router {
                    type types-sros:router-instance;
                    description "The router controlled by this portal.";
                }

                leaf enabled-interfaces {
                    type uint32;
                    description
                        "The number of interfaces that are associated with this portal
                         and adminstrative enabled.";
                }

                leaf triggered-hosts {
                    type boolean;
                    description "Indicates if triggered hosts are enabled or disabled on this portal.";
                }

                list statistics {
                    key "type id";
                    description "Enter the statistics list instance";

                    leaf type {
                        type enumeration {
                            enum event                          { value 1; }
                            enum dropped                        { value 2; }
                            enum accepted                       { value 3; }
                            enum original-transmitted           { value 4; }
                            enum retransmitted                  { value 5; }
                            enum forwarded-to-peer              { value 6; }
                            enum received-from-peer             { value 7; }
                        }
                        description "Indicates the statistics type.";
                    }

                    leaf id {
                        type uint32 {
                            range "0..40";
                        }
                        description "The counter id.";
                    }

                    leaf description {
                        type types-sros:display-string {
                            length "1..64";
                        }
                        description "Describes the statistic.";
                    }

                    leaf value {
                        type yang:counter32;
                        description "The value of the counter.";
                    }

                } // list statistics

                list host {
                    key "address";
                    description "Enter the host list instance";

                    leaf address {
                        type types-sros:ipv4-unicast-address;
                        description "The address of the WPP host.";
                    }

                    leaf state {
                        type enumeration {
                            enum idle                           { value 1; }
                            enum challenged                     { value 2; }
                            enum authenticating                 { value 3; }
                            enum authenticated                  { value 4; }
                            enum established                    { value 5; }
                            enum logging-out                    { value 6; }
                        }
                        description "The state of the WPP host.";
                    }

                    leaf serial-number {
                        type uint32 {
                            range "1..4294967295";
                        }
                        description "The serial number of the WPP host.";
                    }

                    leaf request-id {
                        type uint32 {
                            range "1..4294967295";
                        }
                        description "The request-id of the WPP host.";
                    }

                    leaf remote-port {
                        type inet:port-number;
                        description "The UDP source port used by the portal while sending a message for this host.";
                    }

                    leaf local-address {
                        type types-sros:ipv4-unicast-address;
                        description "The destination address used by the portal while sending a message for this host.";
                    }

                    leaf user-name {
                        type types-sros:display-string;
                        description "The WPP user name of this WPP host.";
                    }

                    leaf service {
                        type types-services:service-name;
                        description "The service to which the WPP host belongs.";
                    }

                    leaf mac-address {
                        type yang:mac-address;
                        description "The mac-address of the WPP host.";
                    }

                    leaf is-triggered {
                        type boolean;
                        description "True if the creation of the host was triggered by the portal, false otherwise.";
                    }

                    leaf track-srrp-instance {
                        type uint32;
                        description
                            "The SRRP instance whose state is tracked by this WPP host to determine if
                             it is on the MCS master or backup node.";
                    }

                    leaf is-mcs-backup {
                        type boolean;
                        description "True if the WPP host is on the MCS backup node, false otherwise.";
                    }

                } // list host

                list session {
                    key "id";
                    description "Enter the session list instance";

                    leaf id {
                        type uint32;
                        description "The unique identifier of this session.";
                    }

                    leaf state {
                        type enumeration {
                            enum idle                           { value 1; }
                            enum challenged                     { value 2; }
                            enum authenticating                 { value 3; }
                            enum authenticated                  { value 4; }
                            enum established                    { value 5; }
                            enum logging-out                    { value 6; }
                        }
                        description "The state of the WPP session.";
                    }

                    leaf serial-number {
                        type uint32 {
                            range "1..4294967295";
                        }
                        description "The serial number of the WPP session.";
                    }

                    leaf request-id {
                        type uint32 {
                            range "1..4294967295";
                        }
                        description "The request-id of the WPP session.";
                    }

                    leaf remote-port {
                        type inet:port-number;
                        description "The UDP source port used by the portal while sending a message for this session.";
                    }

                    leaf local-address {
                        type types-sros:ipv4-unicast-address;
                        description "The destination address used by the portal while sending a message for this session.";
                    }

                    leaf user-name {
                        type types-sros:display-string;
                        description "The WPP user name of this WPP session.";
                    }

                    leaf service {
                        type types-services:service-name;
                        description "The service to which the WPP session belongs.";
                    }

                    leaf mac-address {
                        type yang:mac-address;
                        description "The mac-address of the WPP session.";
                    }

                    leaf is-triggered {
                        type boolean;
                        description "True if the creation of the session was triggered by the portal, false otherwise.";
                    }

                    leaf track-srrp-instance {
                        type uint32;
                        description
                            "The SRRP instance whose state is tracked by this WPP session to determine if
                             it is on the MCS master or backup node.";
                    }

                    leaf is-mcs-backup {
                        type boolean;
                        description "True if the WPP session is on the MCS backup node, false otherwise.";
                    }

                    leaf client-address {
                        type types-sros:ip-address;
                        description "The source address the client used to contact the WPP portal.";
                    }

                    container ipoe-session {
                        description "Enter the ipoe-session context";

                        leaf sap-id {
                            type types-sros:sap;
                            description "Indicates the SAP used by this session.";
                        }

                        leaf mac-address {
                            type yang:mac-address;
                            description "Indicates the MAC address of this session.";
                        }

                        leaf remote-id {
                            type binary {
                                length "0..256";
                            }
                            description "Indicates the value of the remote-id sub-option.";
                        }

                        leaf circuit-id {
                            type binary {
                                length "0..256";
                            }
                            description "Indicates the value of the circuit-id sub-option.";
                        }

                    } // container ipoe-session

                } // list session

            } // list portal

            list statistics {
                key "type id";
                description "Enter the statistics list instance";

                leaf type {
                    type enumeration {
                        enum event                          { value 1; }
                        enum dropped                        { value 2; }
                        enum accepted                       { value 3; }
                        enum original-transmitted           { value 4; }
                        enum retransmitted                  { value 5; }
                        enum forwarded-to-peer              { value 6; }
                        enum received-from-peer             { value 7; }
                    }
                    description "Indicates the statistics type.";
                }

                leaf id {
                    type uint32 {
                        range "0..40";
                    }
                    description "The counter id.";
                }

                leaf description {
                    type types-sros:display-string {
                        length "1..64";
                    }
                    description "Describes the statistic.";
                }

                leaf value {
                    type yang:counter32;
                    description "The value of the counter.";
                }

            } // list statistics

        } // container wpp

    } // grouping state-router-wpp

}
