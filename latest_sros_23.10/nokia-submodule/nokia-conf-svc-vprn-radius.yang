submodule nokia-conf-svc-vprn-radius {

    yang-version "1.1";

    belongs-to nokia-conf { prefix "conf"; }

    import nokia-sros-yang-extensions     { prefix "sros-ext"; }
    import nokia-types-radius             { prefix "types-radius"; }
    import nokia-types-sros               { prefix "types-sros"; }

    include nokia-conf-groups;
    include nokia-conf-isa;
    include nokia-conf-python;
    include nokia-conf-service;
    include nokia-conf-svc-vprn;

    sros-ext:sros-major-release "rel23";
    organization "Nokia";
    contact
        "Nokia SR OS Support
         Web: <http://www.nokia.com>";
    description
        "Nokia YANG Data model to configure RADIUS on SR OS based routers.

         Copyright 2016 Nokia. All rights reserved. Reproduction of this document
         is authorized on the condition that the foregoing copyright notice is included.

         This nokia-conf-svc-vprn-radius YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping conf-svc-vprn-radius {
        container radius {
            description "Enter the radius context";

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            list server {
                key "name";
                max-elements 64;
                description "Enter the server list instance";

                leaf name {
                    type types-sros:named-item;
                    description "External RADIUS server name";
                }

                leaf description {
                    type types-sros:description;
                    description "Text description";
                }

                leaf address {
                    type types-sros:ip-unicast-address;
                    mandatory true;
                    description "IP address of the RADIUS server";
                }

                leaf secret {
                    type types-sros:encrypted-leaf {
                        length "1..115";
                    }
                    mandatory true;
                    description "Secret key associated with this RADIUS server";
                }

                leaf accept-coa {
                    type boolean;
                    default "false";
                    description "Process Change of Authorization (CoA) messages";
                }

                leaf acct-port {
                    type types-sros:tcp-udp-port-non-zero;
                    default "1813";
                    description "UDP port number of the RADIUS for accounting events";
                }

                leaf auth-port {
                    type types-sros:tcp-udp-port-non-zero;
                    default "1812";
                    description "UDP port number of the RADIUS to be used as match criteria";
                }

                leaf pending-requests-limit {
                    type uint32 {
                        range "1..4096";
                    }
                    default "4096";
                    description "Limit of the number for pending RADIUS requests";
                }

                leaf python-policy {
                    type leafref {
                        path "../../../../../python/python-policy/name";
                    }
                    description "Python script policy to modify CoA messages";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list server

            list proxy {
                key "name";
                max-elements 8;
                description "Enter the proxy list instance";

                leaf name {
                    type types-sros:named-item;
                    description "RADIUS proxy name";
                }

                leaf admin-state {
                    type types-sros:admin-state;
                    default "disable";
                    description "Administrative state of RADIUS proxy";
                }

                leaf description {
                    type types-sros:description;
                    description "Text description";
                }

                leaf purpose {
                    type enumeration {
                        enum accounting                     { value 1; }
                        enum authentication                 { value 2; }
                        enum accounting-authentication      { value 3; }
                    }
                    sros-ext:immutable;
                    mandatory true;
                    description "Purpose of the RADIUS proxy";
                }

                leaf wlan-gw-group {
                    type leafref {
                        path "../../../../../isa/wlan-gw-group/id";
                    }
                    sros-ext:immutable;
                    description "ISA WLAN gateway group";
                }

                leaf secret {
                    type types-sros:encrypted-leaf {
                        length "1..115";
                    }
                    description "Format of the secret key to access the RADIUS proxy server";
                }

                leaf send-accounting-response {
                    type boolean;
                    default "false";
                    description "Allow RADIUS proxy server to respond to Accounting-Response messages";
                }

                leaf python-policy {
                    type leafref {
                        path "../../../../../python/python-policy/name";
                    }
                    description "Python policy";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container load-balance-key {
                    description "Enter the load-balance-key context";

                    choice load-balance-key {
                        case source-ip-udp {

                            leaf source-ip-udp {
                                type empty;
                                description "Key to consist of the source IP address and source UDP port of the RADIUS message";
                            }

                        }
                        case attributes {

                            container attribute-1 {
                                description "Enter the attribute-1 context";

                                leaf type {
                                    type types-radius:radius-attribute-type;
                                    description "Attribute type to cache for this RADIUS Proxy server";
                                }

                                leaf vendor {
                                    type types-radius:radius-vendor-id;
                                    description "Vendor-Id attribute";
                                }

                            } // container attribute-1

                            container attribute-2 {
                                description "Enter the attribute-2 context";

                                leaf type {
                                    type types-radius:radius-attribute-type;
                                    description "Attribute type to cache for this RADIUS Proxy server";
                                }

                                leaf vendor {
                                    type types-radius:radius-vendor-id;
                                    description "Vendor-Id attribute";
                                }

                            } // container attribute-2

                            container attribute-3 {
                                description "Enter the attribute-3 context";

                                leaf type {
                                    type types-radius:radius-attribute-type;
                                    description "Attribute type to cache for this RADIUS Proxy server";
                                }

                                leaf vendor {
                                    type types-radius:radius-vendor-id;
                                    description "Vendor-Id attribute";
                                }

                            } // container attribute-3

                            container attribute-4 {
                                description "Enter the attribute-4 context";

                                leaf type {
                                    type types-radius:radius-attribute-type;
                                    description "Attribute type to cache for this RADIUS Proxy server";
                                }

                                leaf vendor {
                                    type types-radius:radius-vendor-id;
                                    description "Vendor-Id attribute";
                                }

                            } // container attribute-4

                            container attribute-5 {
                                description "Enter the attribute-5 context";

                                leaf type {
                                    type types-radius:radius-attribute-type;
                                    description "Attribute type to cache for this RADIUS Proxy server";
                                }

                                leaf vendor {
                                    type types-radius:radius-vendor-id;
                                    description "Vendor-Id attribute";
                                }

                            } // container attribute-5

                        }
                    }
                } // container load-balance-key

                container cache {
                    description "Enter the cache context";

                    leaf admin-state {
                        type types-sros:admin-state;
                        default "disable";
                        description "Administrative state of the RADIUS proxy cache";
                    }

                    leaf track-delete-hold-time {
                        type types-sros:time-duration {
                            range "0..6000";
                        }
                        default "0";
                        description "Delete hold time";
                    }

                    leaf timeout {
                        type types-sros:time-duration {
                            range "60..3600";
                        }
                        default "300";
                        description "Idle timeout value";
                    }

                    container key {
                        presence "Enable the key context";
                        description "Enable the key context";

                        leaf packet-type {
                            type enumeration {
                                enum access-request                 { value 1; }
                                enum access-accept                  { value 2; }
                            }
                            mandatory true;
                            description "Packet type of the RADIUS messages";
                        }

                        leaf attribute-type {
                            type types-radius:radius-attribute-type;
                            mandatory true;
                            description "RADIUS attribute type to cache for this RADIUS proxy server";
                        }

                        leaf vendor {
                            type types-radius:radius-vendor-id;
                            description "RADIUS Vendor ID";
                        }

                    } // container key

                    container track-accounting {
                        description "Enter the track-accounting context";

                        leaf start {
                            type boolean;
                            default "false";
                            description "Update host with client that generated accounting-start";
                        }

                        leaf stop {
                            type boolean;
                            default "false";
                            description "Remove ESM host and forward accounting-stop packet";
                        }

                        leaf interim-update {
                            type boolean;
                            default "false";
                            description "Update the ESM host with the RADIUS client that generated the interim update";
                        }

                        leaf accounting-on {
                            when "not(../../../wlan-gw-group)" {
                                description "disabled when WLAN Gateway ISA group ID is configured in proxy";
                            }
                            type boolean;
                            default "false";
                            description "Remove all ESM hosts associated with the RADIUS client";
                        }

                        leaf accounting-off {
                            when "not(../../../wlan-gw-group)" {
                                description "disabled when WLAN Gateway ISA group ID is configured in proxy";
                            }
                            type boolean;
                            default "false";
                            description "Remove all ESM hosts associated with the RADIUS client";
                        }

                    } // container track-accounting

                    container track-authentication {
                        description "Enter the track-authentication context";

                        leaf accept {
                            type boolean;
                            default "true";
                            description "Track Access-Accept message for mobility";
                        }

                    } // container track-authentication

                } // container cache

                container attribute-matching {
                    description "Enter the attribute-matching context";

                    leaf type {
                        type types-radius:radius-attribute-type;
                        description "Matching attribute type to RADIUS server policy";
                    }

                    leaf vendor {
                        type types-radius:radius-vendor-id;
                        description "Matching Vendor ID to RADIUS server policy";
                    }

                    list entry {
                        key "index";
                        description "Enter the entry list instance";

                        leaf index {
                            type uint32 {
                                range "1..32";
                            }
                            description "Index of this entry";
                        }

                        leaf prefix-string {
                            type types-sros:display-string {
                                length "1..128";
                            }
                            description "Prefix string";
                        }

                        leaf suffix-string {
                            type types-sros:display-string {
                                length "1..128";
                            }
                            description "Prefix string";
                        }

                        leaf accounting-server-policy {
                            type types-sros:named-item;
                            description "Accounting server policy";
                        }

                        leaf authentication-server-policy {
                            type types-sros:named-item;
                            description "Authentication server policy";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list entry

                } // container attribute-matching

                container wlan-gw {
                    when "../wlan-gw-group" {
                        description "disabled when no ISA group ID is configured in proxy";
                    }
                    description "Enter the wlan-gw context";

                    leaf address {
                        type types-sros:ipv4-unicast-address;
                        description "IPv4 address of the distributed RADIUS proxy server";
                    }

                    leaf ipv6-address {
                        type types-sros:ipv6-unicast-without-local-address;
                        description "IPv6 address of the distributed RADIUS proxy server";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // container wlan-gw

                container defaults {
                    description "Enter the defaults context";

                    leaf authentication-server-policy {
                        type types-sros:named-item;
                        description "Default authentication RADIUS server policy";
                    }

                    leaf accounting-server-policy {
                        type types-sros:named-item;
                        description "Default accounting RADIUS server policy";
                    }

                } // container defaults

                list interface {
                    when "not(../wlan-gw-group)" {
                        description "disabled when WLAN Gateway ISA group ID is configured in proxy";
                    }
                    key "interface-name";
                    description "Add a list entry for interface";

                    leaf interface-name {
                        type leafref {
                            path "../../../../interface/interface-name";
                        }
                        description "IP interface name";
                    }

                } // list interface

            } // list proxy

        } // container radius

    } // grouping conf-svc-vprn-radius

}
