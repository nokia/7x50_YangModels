submodule nokia-conf-svc-vpls {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-igmp               { prefix "types-igmp"; }
    import nokia-types-isa                { prefix "types-isa"; }
    import nokia-types-mcast-cac          { prefix "types-mcast-cac"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }

    include nokia-conf-aa-group;
    include nokia-conf-application-assurance;
    include nokia-conf-bfd;
    include nokia-conf-eth-cfm;
    include nokia-conf-filter;
    include nokia-conf-groups;
    include nokia-conf-isa;
    include nokia-conf-log;
    include nokia-conf-mcast-cac;
    include nokia-conf-mcast-mgmt;
    include nokia-conf-policy-options;
    include nokia-conf-port;
    include nokia-conf-port-eth-access;
    include nokia-conf-port-ethernet;
    include nokia-conf-pxc;
    include nokia-conf-python;
    include nokia-conf-qos;
    include nokia-conf-redundancy;
    include nokia-conf-router;
    include nokia-conf-router-mpls;
    include nokia-conf-router-segment-routing;
    include nokia-conf-service;
    include nokia-conf-submgt-local-user-db;
    include nokia-conf-subscriber-mgmt;
    include nokia-conf-system;
    include nokia-conf-system-security;

    sros-ext:sros-major-release "rel23";
    organization "Nokia";
    contact
        "Nokia SR OS Support
         Web: <http://www.nokia.com>";
    description
        "Nokia YANG Data model to configure vpls services on SR OS based routers.

         Copyright 2016 Nokia. All rights reserved. Reproduction of this document
         is authorized on the condition that the foregoing copyright notice is included.

         This nokia-conf-svc-vpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-06-27";

    grouping conf-svc-vpls {
        list vpls {
            key "service-name";
            description "Enter the vpls list instance";

            leaf service-name {
                type types-services:service-name;
                description "Administrative service name";
            }

            leaf service-id {
                type types-services:external-service-id;
                sros-ext:immutable;
                description "Service ID";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the service";
            }

            leaf vpn-id {
                type types-services:vpn-id;
                sros-ext:immutable;
                description "VPN identifier for the service";
            }

            leaf service-mtu {
                type int32 {
                    range "1..9782";
                }
                description "MTU size";
            }

            leaf etree {
                type boolean;
                sros-ext:immutable;
                default "false";
                description "Use VPLS service as an E-Tree VPLS";
            }

            leaf m-vpls {
                type boolean;
                sros-ext:immutable;
                default "false";
                description "Specify whether this is a management VPLS";
            }

            leaf pbb-type {
                type types-services:pbb-type;
                sros-ext:immutable;
                description "PBB VPLS type";
            }

            leaf mcast-ipv6-snooping-scope {
                type enumeration {
                    enum sg-based                       { value 1; }
                    enum mac-based                      { value 2; }
                }
                default "mac-based";
                description "IPv6 multicast snooping scope";
            }

            leaf multicast-info-policy {
                type leafref {
                    path "../../../multicast-management/multicast-info-policy/policy-name";
                }
                description "Multicast information policy";
            }

            leaf shcv-policy-ipv4 {
                type leafref {
                    path "../../../subscriber-mgmt/shcv-policy/name";
                }
                description "Subscriber host connectivity verification policy for IPv4";
            }

            leaf temp-flooding {
                type int32 {
                    range "3..600";
                }
                units "seconds";
                description "Temporary flooding";
            }

            leaf ignore-l2vpn-mtu-mismatch {
                type boolean;
                default "false";
                description "Ignore the L2 VPN MTU mismatch with local service MTU";
            }

            leaf tunnel-elmi {
                type boolean;
                default "false";
                description "Allow E-LMI tunneling";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container fdb {
                description "Enter the fdb context";

                leaf discard-unknown {
                    type boolean;
                    default "false";
                    description "Discard packets with unknown destination MAC addresses";
                }

                leaf mac-subnet-length {
                    when "not(../../pbb-type)" {
                        description "VPLS PBB type must be 'none'";
                    }
                    type int32 {
                        range "24..48";
                    }
                    default "48";
                    description "Number of bits performing MAC learning or MAC switching";
                }

                leaf selective-learning {
                    when "not(../../pbb-type = 'b-vpls')" {
                        description "VPLS PBB type must not be 'b-vpls'";
                    }
                    type boolean;
                    default "false";
                    description "Allocate FDB entries on selectively learned line cards";
                }

                container table {
                    description "Enter the table context";

                    leaf high-wmark {
                        type int32 {
                            range "0..100";
                        }
                        default "95";
                        description "High watermark for the FDB table";
                    }

                    leaf low-wmark {
                        type int32 {
                            range "0..100";
                        }
                        default "90";
                        description "Low watermark for the FDB table";
                    }

                    leaf size {
                        type int32 {
                            range "1..511999";
                        }
                        default "250";
                        description "Maximum MAC entries in the FDB";
                    }

                } // container table

                container mac-learning {
                    description "Enter the mac-learning context";

                    leaf learning {
                        type boolean;
                        default "true";
                        description "Enable learning of new MAC addresses";
                    }

                    leaf aging {
                        type boolean;
                        default "true";
                        description "Enable aging of MAC addresses";
                    }

                    leaf local-age-time {
                        type int32 {
                            range "60..86400";
                        }
                        default "300";
                        description "Aging time for locally learned MAC addresses";
                    }

                    leaf remote-age-time {
                        type int32 {
                            range "60..86400";
                        }
                        default "900";
                        description "Aging time for remotely learned MAC addresses";
                    }

                } // container mac-learning

                container mac-move {
                    description "Enter the mac-move context";

                    leaf admin-state {
                        type types-sros:admin-state;
                        default "disable";
                        description "Administrative state of MAC move";
                    }

                    leaf move-frequency {
                        type uint32 {
                            range "1..10";
                        }
                        default "2";
                        description "Maximum rate MACs can be re-learned in the VPLS service";
                    }

                    leaf retry-count {
                        type union {
                            type uint32 {
                                range "1..255";
                            }
                            type enumeration {
                                enum unlimited                      { value 0; }
                            }
                        }
                        default "3";
                        description "Number of retries for re-enabling the SAP or SDP";
                    }

                    leaf hold-down-time {
                        type uint32 {
                            range "0..600";
                        }
                        units "seconds";
                        default "10";
                        description "Wait time before re-enabling disabled SAP";
                    }

                    leaf primary-cumulative-factor {
                        type uint32 {
                            range "3..10";
                        }
                        default "3";
                        description "Factor for MAC-relearn periods for MAC-relearn rate";
                    }

                    leaf secondary-cumulative-factor {
                        type uint32 {
                            range "2..9";
                        }
                        default "2";
                        description "Number of periods to measure mac-relearn rate";
                    }

                    list sap {
                        key "sap-id";
                        description "Enter the sap list instance";

                        leaf sap-id {
                            type leafref {
                                path "../../../../sap/sap-id";
                            }
                            description "SAP identifier";
                        }

                        leaf level {
                            type enumeration {
                                enum primary                        { value 1; }
                                enum secondary                      { value 2; }
                            }
                            mandatory true;
                            description "Primary or secondary port level";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sap

                    list spoke-sdp {
                        key "sdp-bind-id";
                        description "Enter the spoke-sdp list instance";

                        leaf sdp-bind-id {
                            type leafref {
                                path "../../../../spoke-sdp/sdp-bind-id";
                            }
                            description "SDP binding ID";
                        }

                        leaf level {
                            type enumeration {
                                enum primary                        { value 1; }
                                enum secondary                      { value 2; }
                            }
                            mandatory true;
                            description "Primary or secondary port level";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list spoke-sdp

                } // container mac-move

                container static-mac {
                    description "Enter the static-mac context";

                    list mac {
                        key "mac-address";
                        description "Enter the mac list instance";

                        leaf mac-address {
                            type types-sros:mac-unicast-address-no-zero;
                            description "Static MAC address to SAP/SDP-binding or black-hole";
                        }

                        leaf monitor {
                            type enumeration {
                                enum none                           { value 0; }
                                enum forward-status                 { value 1; }
                            }
                            sros-ext:immutable;
                            default "none";
                            description "Entity to be monitored to decide whether this entry can be installed in the FDB";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        choice destination {
                            mandatory true;
                            case spoke-sdp {

                                leaf spoke-sdp {
                                    type leafref {
                                        path "../../../../spoke-sdp/sdp-bind-id";
                                    }
                                    sros-ext:immutable;
                                    description "Spoke SDP bind associated with this MAC";
                                }

                            }
                            case mesh-sdp {

                                leaf mesh-sdp {
                                    type leafref {
                                        path "../../../../mesh-sdp/sdp-bind-id";
                                    }
                                    sros-ext:immutable;
                                    description "Mesh SDP bind associated with this MAC";
                                }

                            }
                            case sap {

                                leaf sap {
                                    type leafref {
                                        path "../../../../sap/sap-id";
                                    }
                                    sros-ext:immutable;
                                    description "SAP associated with this MAC";
                                }

                            }
                            case blackhole {

                                leaf blackhole {
                                    type empty;
                                    sros-ext:immutable;
                                    description "Create a static FDB entry for the MAC address to black-hole traffic";
                                }

                            }
                            case endpoint {

                                leaf endpoint {
                                    type leafref {
                                        path "../../../../endpoint/name";
                                    }
                                    sros-ext:immutable;
                                    description "Endpoint associated with the MAC";
                                }

                            }
                        }
                    } // list mac

                } // container static-mac

            } // container fdb

            container mfib {
                description "Enter the mfib context";

                container table {
                    description "Enter the table context";

                    leaf high-wmark {
                        type int32 {
                            range "0..100";
                        }
                        default "95";
                        description "High watermark for the MFIB table";
                    }

                    leaf low-wmark {
                        type int32 {
                            range "0..100";
                        }
                        default "90";
                        description "Low watermark for the MFIB table";
                    }

                    leaf size {
                        type int32 {
                            range "1..40959";
                        }
                        description "Maximum SG entries in the MFIB";
                    }

                } // container table

            } // container mfib

            container mac-flush {
                description "Enter the mac-flush context";

                container tldp {
                    description "Enter the tldp context";

                    leaf propagate {
                        type boolean;
                        default "false";
                        description "Propagate MAC flush messages received from the T-LDP";
                    }

                    leaf send-on-failure {
                        type boolean;
                        default "false";
                        description "Send MAC withdraw message on SAP/Spoke-SDP failure";
                    }

                } // container tldp

            } // container mac-flush

            container vxlan {
                when "not(../pbb-type)" {
                    description "VPLS PBB type must be 'none'";
                }
                description "Enter the vxlan context";

                leaf source-vtep {
                    type types-sros:ip-unicast-address;
                    description "Vxlan source virtual tunnel endpoint information";
                }

                list instance {
                    when "../../etree = 'false' and ../../m-vpls = 'false'" {
                        description "etree or m-vpls must be unset";
                    }
                    key "vxlan-instance";
                    description "Enter the instance list instance";

                    leaf vxlan-instance {
                        type uint32 {
                            range "1..2";
                        }
                        description "VXLAN instance";
                    }

                    leaf vni {
                        type types-services:vxlan-vni;
                        sros-ext:immutable;
                        mandatory true;
                        description "VNI of the VXLAN";
                    }

                    leaf source-vtep-security {
                        type boolean;
                        default "false";
                        description "Enable/disable source vtep security";
                    }

                    leaf rx-discard-on-ndf {
                        type enumeration {
                            enum bm                             { value 0; }
                            enum bum                            { value 1; }
                            enum none                           { value 2; }
                        }
                        default "bm";
                        description "Received multicast traffic type discarded on NDF";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container assisted-replication {
                        description "Enter the assisted-replication context";

                        choice role {
                            case leaf {

                                container leaf {
                                    presence "Enable the leaf context";
                                    description "Enable the leaf context";

                                    leaf acttime {
                                        type uint32 {
                                            range "1..255";
                                        }
                                        units "seconds";
                                        description "Time for the leaf to wait before sending traffic to a new replicator";
                                    }

                                } // container leaf

                            }
                            case replicator {

                                leaf replicator {
                                    type empty;
                                    description "AR role as replicator";
                                }

                            }
                        }
                    } // container assisted-replication

                    container network {
                        description "Enter the network context";

                        container ingress {
                            description "Enter the ingress context";

                            container qos {
                                description "Enter the qos context";

                                container network {
                                    description "Enter the network context";

                                    leaf policy-name {
                                        type leafref {
                                            path "../../../../../../../../../qos/network/network-policy-name";
                                        }
                                        description "Ingress network policy name applied to this SDP binding";
                                    }

                                    container fp-redirect-group {
                                        description "Enter the fp-redirect-group context";

                                        leaf group-name {
                                            type leafref {
                                                path "../../../../../../../../../../qos/queue-group-templates/ingress/queue-group/ingress-queue-group-name";
                                            }
                                            description "Name of the forwarding plane queue group template";
                                        }

                                        leaf instance {
                                            type types-services:qos-qgrp-instance-id;
                                            description "Instance of the forwarding-plane ingress Queue Group for this SDP binding";
                                        }

                                    } // container fp-redirect-group

                                } // container network

                            } // container qos

                        } // container ingress

                    } // container network

                    list egress-vtep {
                        key "ip-address";
                        description "Add a list entry for egress-vtep";

                        leaf ip-address {
                            type types-sros:ip-unicast-address;
                            description "VTEP IP address used when originating VXLAN packets";
                        }

                    } // list egress-vtep

                    container fdb {
                        description "Enter the fdb context";

                        leaf discard-unknown-source {
                            type boolean;
                            default "false";
                            description "Discard frames with unknown source";
                        }

                        leaf maximum-mac-addresses {
                            type types-services:max-mac-addr;
                            description "Maximum number of MAC entries in the FDB from this vxlan instance";
                        }

                        leaf protected-src-mac-violation-action {
                            type types-services:protected-src-mac-violation-df-action;
                            description "Action for a relearn request for a protected MAC";
                        }

                        container mac-learning {
                            description "Enter the mac-learning context";

                            leaf learning {
                                type boolean;
                                default "false";
                                description "Enable learning of new MAC addresses";
                            }

                            leaf aging {
                                type boolean;
                                default "false";
                                description "Enable/disable aging of MAC addresses";
                            }

                        } // container mac-learning

                    } // container fdb

                    container igmp-snooping {
                        description "Enter the igmp-snooping context";

                        leaf mrouter-port {
                            type boolean;
                            default "false";
                            description "Enable VXLAN binds as multicast router ports";
                        }

                    } // container igmp-snooping

                    container mld-snooping {
                        description "Enter the mld-snooping context";

                        leaf mrouter-port {
                            type boolean;
                            default "false";
                            description "Enable VXLAN binds as multicast router ports";
                        }

                    } // container mld-snooping

                } // list instance

            } // container vxlan

            container proxy-arp {
                when "not(../pbb-type) and not(../m-vpls = 'true')" {
                    description "VPLS PBB type must be 'none' or m-vpls must be unset";
                }
                presence "Enable the proxy-arp context";
                description "Enable the proxy-arp context";

                leaf admin-state {
                    type types-sros:admin-state;
                    default "disable";
                    description "Administrative state of the proxy";
                }

                leaf dynamic-populate {
                    type boolean;
                    default "false";
                    description "Populate proxy ARP entries from snooped GARP/ARP/ND messages on SAPs/SDP-bindings";
                }

                leaf age-time {
                    type union {
                        type int32 {
                            range "60..86400";
                        }
                        type enumeration {
                            enum never                          { value 0; }
                        }
                    }
                    units "seconds";
                    default "never";
                    description "Aging timer for proxy entries, where entries are flushed upon timer expiry";
                }

                leaf send-refresh {
                    type union {
                        type int32 {
                            range "120..86400";
                        }
                        type enumeration {
                            enum never                          { value 0; }
                        }
                    }
                    default "never";
                    description "Time at which to send a refresh message";
                }

                leaf table-size {
                    type int32 {
                        range "1..16383";
                    }
                    default "250";
                    description "Maximum number of learned and static entries allowed in the proxy table of this service";
                }

                leaf process-arp-probes {
                    type boolean;
                    default "true";
                    description "Enable replies to DAD ARP probes";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container evpn {
                    description "Enter the evpn context";

                    leaf route-tag {
                        type int32 {
                            range "0|1..255";
                        }
                        sros-ext:auto-restart-to-modify;
                        default "0";
                        description "Route tag used on export policies to match MAC/IP routes generated by proxy-ARP or proxy-ND module";
                    }

                    container flood {
                        description "Enter the flood context";

                        leaf unknown-arp-req {
                            type boolean;
                            default "true";
                            description "Flood ARP-requests (with source squelching) if there is no active proxy-ARP entry for requested IP";
                        }

                        leaf gratuitous-arp {
                            type boolean;
                            default "true";
                            description "Flood GARP-requests/GARP-replies to the EVPN";
                        }

                    } // container flood

                } // container evpn

                container duplicate-detect {
                    description "Enter the duplicate-detect context";

                    leaf anti-spoof-mac {
                        type types-sros:mac-unicast-address-no-zero;
                        sros-ext:auto-restart-to-modify;
                        description "MAC address to replace the proxy-ARP/ND offending entry's MAC";
                    }

                    leaf window {
                        type int32 {
                            range "1..15";
                        }
                        units "minutes";
                        default "3";
                        description "Time to monitor the MAC address in the anti-spoofing mechanism";
                    }

                    leaf num-moves {
                        type int32 {
                            range "3..10";
                        }
                        default "5";
                        description "Number of moves required to declare a duplicate entry";
                    }

                    leaf hold-down-time {
                        type union {
                            type uint32 {
                                range "2..60";
                            }
                            type enumeration {
                                enum max                            { value -1; }
                            }
                        }
                        units "minutes";
                        default "9";
                        description "Hold down time for a duplicate entry";
                    }

                    leaf static-blackhole {
                        type boolean;
                        sros-ext:auto-restart-to-modify;
                        default "false";
                        description "Consider anti-spoof MAC as black-hole static MAC in FDB";
                    }

                } // container duplicate-detect

                container static-arp {
                    description "Enter the static-arp context";

                    list ip-address {
                        key "ipv4-address";
                        description "Enter the ip-address list instance";

                        leaf ipv4-address {
                            type types-sros:ipv4-unicast-address;
                            description "Proxy ARP IPv4 address";
                        }

                        leaf mac {
                            type types-sros:mac-unicast-address-no-zero;
                            mandatory true;
                            description "Proxy ARP MAC address for static entry";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list ip-address

                } // container static-arp

                container dynamic-arp {
                    description "Enter the dynamic-arp context";

                    list ip-address {
                        key "ipv4-address";
                        description "Enter the ip-address list instance";

                        leaf ipv4-address {
                            type types-sros:ipv4-unicast-address;
                            description "Proxy ARP IPv4 address";
                        }

                        leaf mac-list {
                            type leafref {
                                path "../../../../../proxy-arp-nd/mac-list/list/list-name";
                            }
                            description "MAC list for the dynamic entry";
                        }

                        leaf resolve-retry-time {
                            type int32 {
                                range "1..60";
                            }
                            units "minutes";
                            default "5";
                            description "Frequency at which the resolve messages are sent";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list ip-address

                } // container dynamic-arp

            } // container proxy-arp

            container proxy-nd {
                when "not(../pbb-type) and not(../m-vpls = 'true')" {
                    description "VPLS PBB type must be 'none' or m-vpls must be unset";
                }
                presence "Enable the proxy-nd context";
                description "Enable the proxy-nd context";

                leaf admin-state {
                    type types-sros:admin-state;
                    default "disable";
                    description "Administrative state of the proxy";
                }

                leaf dynamic-populate {
                    type boolean;
                    default "false";
                    description "Populate proxy ARP entries from snooped GARP/ARP/ND messages on SAPs/SDP-bindings";
                }

                leaf age-time {
                    type union {
                        type int32 {
                            range "60..86400";
                        }
                        type enumeration {
                            enum never                          { value 0; }
                        }
                    }
                    units "seconds";
                    default "never";
                    description "Aging timer for proxy entries, where entries are flushed upon timer expiry";
                }

                leaf send-refresh {
                    type union {
                        type int32 {
                            range "120..86400";
                        }
                        type enumeration {
                            enum never                          { value 0; }
                        }
                    }
                    default "never";
                    description "Time at which to send a refresh message";
                }

                leaf table-size {
                    type int32 {
                        range "1..16383";
                    }
                    default "250";
                    description "Maximum number of learned and static entries allowed in the proxy table of this service";
                }

                leaf process-dad-neighbor-solicitations {
                    type boolean;
                    default "true";
                    description "Enable replies to DAD neighbor solicitations";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container evpn {
                    description "Enter the evpn context";

                    leaf route-tag {
                        type int32 {
                            range "0|1..255";
                        }
                        sros-ext:auto-restart-to-modify;
                        default "0";
                        description "Route tag used on export policies to match MAC/IP routes generated by proxy-ARP or proxy-ND module";
                    }

                    leaf advertise-neighbor-type {
                        type enumeration {
                            enum router                         { value 1; }
                            enum host                           { value 2; }
                            enum router-host                    { value 3; }
                        }
                        sros-ext:auto-restart-to-modify;
                        default "router";
                        description "Advertisement type of static or dynamic entries in EVPN";
                    }

                    container flood {
                        description "Enter the flood context";

                        leaf unknown-neighbor-solicitation {
                            type boolean;
                            default "true";
                            description "Flood unsolicited Neighbor Solicitation messages (with source squelching) into EVPN network";
                        }

                        leaf unknown-neighbor-advertise-router {
                            type boolean;
                            sros-ext:auto-restart-to-modify;
                            default "true";
                            description "Flood router unsolicited Neighbor Advertisement (NA) replies to EVPN";
                        }

                        leaf unknown-neighbor-advertise-host {
                            type boolean;
                            default "true";
                            description "Flood host unsolicited Neighbor Advertisement (NA) replies to EVPN";
                        }

                    } // container flood

                } // container evpn

                container duplicate-detect {
                    description "Enter the duplicate-detect context";

                    leaf anti-spoof-mac {
                        type types-sros:mac-unicast-address-no-zero;
                        sros-ext:auto-restart-to-modify;
                        description "MAC address to replace the proxy-ARP/ND offending entry's MAC";
                    }

                    leaf window {
                        type int32 {
                            range "1..15";
                        }
                        units "minutes";
                        default "3";
                        description "Time to monitor the MAC address in the anti-spoofing mechanism";
                    }

                    leaf num-moves {
                        type int32 {
                            range "3..10";
                        }
                        default "5";
                        description "Number of moves required to declare a duplicate entry";
                    }

                    leaf hold-down-time {
                        type union {
                            type uint32 {
                                range "2..60";
                            }
                            type enumeration {
                                enum max                            { value -1; }
                            }
                        }
                        units "minutes";
                        default "9";
                        description "Hold down time for a duplicate entry";
                    }

                    leaf static-blackhole {
                        type boolean;
                        sros-ext:auto-restart-to-modify;
                        default "false";
                        description "Consider anti-spoof MAC as black-hole static MAC in FDB";
                    }

                } // container duplicate-detect

                container static-neighbor {
                    description "Enter the static-neighbor context";

                    list ip-address {
                        key "ipv6-address";
                        description "Enter the ip-address list instance";

                        leaf ipv6-address {
                            type types-sros:ipv6-address;
                            description "Proxy ND IPv6 address";
                        }

                        leaf mac {
                            type types-sros:mac-unicast-address-no-zero;
                            mandatory true;
                            description "Proxy ARP MAC address for static entry";
                        }

                        leaf type {
                            type enumeration {
                                enum host                           { value 0; }
                                enum router                         { value 1; }
                            }
                            default "router";
                            description "Entry type";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list ip-address

                } // container static-neighbor

                container dynamic-neighbor {
                    description "Enter the dynamic-neighbor context";

                    list ip-address {
                        key "ipv6-address";
                        description "Enter the ip-address list instance";

                        leaf ipv6-address {
                            type types-sros:ipv6-address;
                            description "Proxy ND IPv6 address";
                        }

                        leaf mac-list {
                            type leafref {
                                path "../../../../../proxy-arp-nd/mac-list/list/list-name";
                            }
                            description "MAC list for the dynamic entry";
                        }

                        leaf resolve-retry-time {
                            type int32 {
                                range "1..60";
                            }
                            units "minutes";
                            default "5";
                            description "Frequency at which the resolve messages are sent";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list ip-address

                } // container dynamic-neighbor

            } // container proxy-nd

            container routed-vpls {
                when "not(../pbb-type = 'b-vpls') and not(../m-vpls = 'true')" {
                    description "not supported on pbb-type 'b-vpls' or when m-vpls is set";
                }
                presence "Enable the routed-vpls context";
                description "Enable the routed-vpls context";

                leaf vxlan-ipv4-tep-ecmp {
                    type boolean;
                    default "false";
                    description "Use ECMP on VXLAN IPv4 destinations for R-VPLS services";
                }

                leaf evpn-mpls-ecmp {
                    type boolean;
                    default "false";
                    description "Enable ECMP behavior on R-VPLS services";
                }

                container multicast {
                    description "Enter the multicast context";

                    leaf ip-multicast-ecmp {
                        type boolean;
                        default "false";
                        description "ECMP behaviour for multicast traffic on bgp-evpn mpls and vxlan";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ipv4 {
                        description "Enter the ipv4 context";

                        leaf forward-to-ip-interface {
                            type boolean;
                            default "false";
                            description "Forward IPv4 multicast from RVPLS to L3 interface";
                        }

                        container igmp-snooping {
                            description "Enter the igmp-snooping context";

                            leaf mrouter-port {
                                type boolean;
                                default "false";
                                description "Operate VPLS L3 interface as a multicast router port";
                            }

                        } // container igmp-snooping

                    } // container ipv4

                    container ipv6 {
                        description "Enter the ipv6 context";

                        leaf forward-to-ip-interface {
                            type boolean;
                            default "false";
                            description "Forward IPv6 multicast from RVPLS to L3 interface";
                        }

                        container mld-snooping {
                            description "Enter the mld-snooping context";

                            leaf mrouter-port {
                                type boolean;
                                default "false";
                                description "Operate VPLS L3 interface as a multicast router port";
                            }

                        } // container mld-snooping

                    } // container ipv6

                    container evpn-gateway {
                        presence "Enable the evpn-gateway context";
                        description "Enable the evpn-gateway context";

                        leaf admin-state {
                            type types-sros:admin-state;
                            default "disable";
                            description "Administrative state of the multicast EVPN gateway";
                        }

                        leaf advertise {
                            type enumeration {
                                enum mvpn-pim                       { value 0; }
                                enum mvpn-only                      { value 1; }
                                enum pim-only                       { value 2; }
                            }
                            sros-ext:auto-restart-to-modify;
                            default "mvpn-pim";
                            description "Type of the multicast EVPN gateway";
                        }

                        leaf dr-activation-timer {
                            type uint32 {
                                range "0..100";
                            }
                            units "seconds";
                            sros-ext:auto-restart-to-modify;
                            default "3";
                            description "DR activation timer for the EVPN gateway";
                        }

                        leaf non-dr-attract-traffic {
                            type enumeration {
                                enum none                           { value 0; }
                                enum from-evpn                      { value 1; }
                                enum from-pim-mvpn                  { value 2; }
                                enum from-evpn-pim-mvpn             { value 3; }
                            }
                            sros-ext:auto-restart-to-modify;
                            default "from-pim-mvpn";
                            description "Multicast traffic attraction option on non-DR router GW";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container evpn-gateway

                } // container multicast

            } // container routed-vpls

            container load-balancing {
                description "Enter the load-balancing context";

                leaf per-service-hashing {
                    type boolean;
                    default "false";
                    description "Enable per-service hashing for Ethernet services";
                }

                leaf spi-load-balancing {
                    when "not(../../pbb-type = 'b-vpls')" {
                        description "VPLS PBB type must not be 'b-vpls'";
                    }
                    type boolean;
                    default "false";
                    description "Allow use of SPI (Security Parameter Index) in hashing for ESP/AH encrypted IPv4/IPv6 traffic";
                }

                leaf teid-load-balancing {
                    when "not(../../pbb-type = 'b-vpls')" {
                        description "VPLS PBB type must not be 'b-vpls'";
                    }
                    type boolean;
                    default "false";
                    description "Include TEID in hashing algorithm for GTP-U/C encapsulated traffic";
                }

                leaf lbl-eth-or-ip-l4-teid {
                    type boolean;
                    default "false";
                    description "Enable hashing of MPLS ethernet and IP packets on SAPs";
                }

            } // container load-balancing

            container mac-protect {
                description "Enter the mac-protect context";

                list mac {
                    key "mac-address";
                    description "Add a list entry for mac";

                    leaf mac-address {
                        type yang:mac-address;
                        description "Protected MAC address";
                    }

                } // list mac

            } // container mac-protect

            container mrp {
                when "../pbb-type = 'b-vpls' or ../m-vpls = 'true'" {
                    description "supported on b-vpls service or m-vpls service only";
                }
                description "Enter the mrp context";

                leaf admin-state {
                    type types-sros:admin-state;
                    default "disable";
                    description "Administrative state of MRP";
                }

                container mmrp {
                    when "../../pbb-type = 'b-vpls' and not(../../m-vpls = 'true')" {
                        description "supported on non managed b-vpls service only";
                    }
                    description "Enter the mmrp context";

                    leaf admin-state {
                        type types-sros:admin-state;
                        description "Administrative state of MMRP";
                    }

                    leaf end-station-only {
                        type boolean;
                        default "false";
                        description "Prevent generation or processing of MMRP messages";
                    }

                    leaf flood-time {
                        type uint32 {
                            range "3..600";
                        }
                        description "Time when traffic is flooded after status change";
                    }

                    container attribute-table {
                        description "Enter the attribute-table context";

                        leaf high-wmark {
                            type int32 {
                                range "0..100";
                            }
                            default "95";
                            description "High watermark for the MMRP attribute table";
                        }

                        leaf low-wmark {
                            type int32 {
                                range "0..100";
                            }
                            default "90";
                            description "Low watermark for the MMRP attribute table";
                        }

                        leaf size {
                            type uint32 {
                                range "1..8192";
                            }
                            default "2048";
                            description "Maximum number of attributes accepted by B-VPLS";
                        }

                    } // container attribute-table

                } // container mmrp


            } // container mrp

            container pbb {
                description "Enter the pbb context";

                leaf force-qtag-forwarding {
                    when "../../pbb-type = 'i-vpls' and not(../../routed-vpls)" {
                        description "VPLS PBB type must be 'i-vpls' and routed VPLS must not be present";
                    }
                    type boolean;
                    default "false";
                    description "Add an IEEE 802.1q tag after C-MAC addresses PBB header";
                }

                list backbone-vpls {
                    when "../../pbb-type = 'i-vpls'" {
                        description "VPLS PBB type must be 'i-vpls'";
                    }
                    key "backbone-vpls-service-name";
                    max-elements 1;
                    description "Enter the backbone-vpls list instance";

                    leaf backbone-vpls-service-name {
                        type leafref {
                            path "../../../../vpls/service-name";
                        }
                        description "Service name";
                    }

                    leaf isid {
                        type types-services:isid;
                        sros-ext:immutable;
                        mandatory true;
                        description "Backbone VPLS ISID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container igmp-snooping {
                        description "Enter the igmp-snooping context";

                        list mrouter-destination {
                            key "mac-reference";
                            description "Add a list entry for mrouter-destination";

                            leaf mac-reference {
                                type leafref {
                                    path "../../../../../../pbb/mac/name";
                                }
                                description "Mac name reference";
                            }

                        } // list mrouter-destination

                    } // container igmp-snooping

                    container mld-snooping {
                        description "Enter the mld-snooping context";

                        list mrouter-destination {
                            key "mac-reference";
                            description "Add a list entry for mrouter-destination";

                            leaf mac-reference {
                                type leafref {
                                    path "../../../../../../pbb/mac/name";
                                }
                                description "Mac name reference";
                            }

                        } // list mrouter-destination

                    } // container mld-snooping

                    list sap {
                        key "sap-id";
                        description "Enter the sap list instance";

                        leaf sap-id {
                            type leafref {
                                path "../../../../../vpls[service-name=current()/../../backbone-vpls-service-name]/sap/sap-id";
                            }
                            description "Backbone VPLS SAP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container igmp-snooping {
                            description "Enter the igmp-snooping context";

                            leaf mrouter-port {
                                type boolean;
                                default "false";
                                description "Operate port as a multicast router port";
                            }

                        } // container igmp-snooping

                        container mld-snooping {
                            description "Enter the mld-snooping context";

                            leaf mrouter-port {
                                type boolean;
                                default "false";
                                description "Operate port as a multicast router port";
                            }

                        } // container mld-snooping

                    } // list sap

                    list spoke-sdp {
                        key "sdp-bind-id";
                        description "Enter the spoke-sdp list instance";

                        leaf sdp-bind-id {
                            type leafref {
                                path "../../../../../vpls[service-name=current()/../../backbone-vpls-service-name]/spoke-sdp/sdp-bind-id";
                            }
                            description "Backbone VPLS SDP Binding ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container igmp-snooping {
                            description "Enter the igmp-snooping context";

                            leaf mrouter-port {
                                type boolean;
                                default "false";
                                description "Operate port as a multicast router port";
                            }

                        } // container igmp-snooping

                        container mld-snooping {
                            description "Enter the mld-snooping context";

                            leaf mrouter-port {
                                type boolean;
                                default "false";
                                description "Operate port as a multicast router port";
                            }

                        } // container mld-snooping

                    } // list spoke-sdp

                    list mesh-sdp {
                        key "sdp-bind-id";
                        description "Enter the mesh-sdp list instance";

                        leaf sdp-bind-id {
                            type leafref {
                                path "../../../../../vpls[service-name=current()/../../backbone-vpls-service-name]/mesh-sdp/sdp-bind-id";
                            }
                            description "Backbone VPLS SDP Binding ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container igmp-snooping {
                            description "Enter the igmp-snooping context";

                            leaf mrouter-port {
                                type boolean;
                                default "false";
                                description "Operate port as a multicast router port";
                            }

                        } // container igmp-snooping

                        container mld-snooping {
                            description "Enter the mld-snooping context";

                            leaf mrouter-port {
                                type boolean;
                                default "false";
                                description "Operate port as a multicast router port";
                            }

                        } // container mld-snooping

                    } // list mesh-sdp

                    container fdb {
                        description "Enter the fdb context";

                        leaf protected-src-mac-violation-action {
                            type types-services:protected-src-mac-violation-df-action;
                            description "Action taken upon a relearn request for protected MAC";
                        }

                    } // container fdb

                } // list backbone-vpls

                container i-vpls-mac-flush {
                    when "../../pbb-type = 'i-vpls'" {
                        description "VPLS PBB type must be 'i-vpls'";
                    }
                    description "Enter the i-vpls-mac-flush context";

                    container tldp {
                        description "Enter the tldp context";

                        leaf send-on-bvpls-failure {
                            type boolean;
                            default "false";
                            description "Send negative flush message (flush-all-from-me) on B-VPLS failure";
                        }

                        leaf propagate-from-bvpls {
                            type boolean;
                            default "false";
                            description "Propagate MAC flush message from B-VPLS into local I-VPLS";
                        }

                        container send-to-bvpls {
                            description "Enter the send-to-bvpls context";

                            leaf all-from-me {
                                type boolean;
                                default "false";
                                description "Generate LDP MAC withdraw all from me message to b-VPLS";
                            }

                            leaf all-but-mine {
                                type boolean;
                                default "false";
                                description "Generate LDP MAC withdraw message to b-VPLS";
                            }

                        } // container send-to-bvpls

                    } // container tldp

                    container bgp-evpn {
                        description "Enter the bgp-evpn context";

                        leaf send-to-bvpls {
                            type boolean;
                            default "false";
                            description "Send b-VPLS EVPN flush";
                        }

                    } // container bgp-evpn

                } // container i-vpls-mac-flush

                container source-bmac {
                    when "../../pbb-type = 'b-vpls'" {
                        description "VPLS PBB type must be 'b-vpls'";
                    }
                    description "Enter the source-bmac context";

                    leaf address {
                        type types-sros:mac-unicast-address-no-zero;
                        description "Base source B-MAC address for the B-VPLS";
                    }

                    leaf use-es-bmac-lsb {
                        type boolean;
                        default "false";
                        description "Use LSB from Ethernet-segment backbone MAC";
                    }

                    leaf use-mclag-bmac-lsb {
                        type boolean;
                        default "false";
                        description "Use MC LAG backbone MAC LSB";
                    }

                } // container source-bmac

                container mac-notification {
                    when "../../pbb-type = 'b-vpls'" {
                        description "VPLS PBB type must be 'b-vpls'";
                    }
                    description "Enter the mac-notification context";

                    leaf admin-state {
                        type types-sros:admin-state;
                        default "disable";
                        description "Administrative state of MAC notification messages";
                    }

                    leaf count {
                        type uint32 {
                            range "1..10";
                        }
                        description "MAC notification messages count";
                    }

                    leaf interval {
                        type uint32 {
                            range "1..100";
                        }
                        units "deciseconds";
                        description "Interval for MAC notification messages";
                    }

                    leaf renotify {
                        type union {
                            type uint32 {
                                range "240..840";
                            }
                            type enumeration {
                                enum none                           { value 0; }
                            }
                        }
                        units "seconds";
                        default "none";
                        description "Re-notify interval for MAC-notification messages";
                    }

                } // container mac-notification

            } // container pbb

            container spb {
                when "../pbb-type = 'b-vpls'" {
                    description "Service is not a b-vpls";
                }
                presence "Enable the spb context";
                description "Enable the spb context";

                leaf isis-instance {
                    type int32 {
                        range "1024..2047";
                    }
                    sros-ext:immutable;
                    default "1024";
                    description "ISIS instance";
                }

                leaf fid {
                    type int32 {
                        range "1..4095";
                    }
                    sros-ext:immutable;
                    default "1";
                    description "FID identifier";
                }

                leaf admin-state {
                    type types-sros:admin-state;
                    default "disable";
                    description "Administrative state of SPB";
                }

                leaf lsp-lifetime {
                    type uint32 {
                        range "350..65535";
                    }
                    default "1200";
                    description "Time LSP is considered valid by other routers";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container lsp-refresh-interval {
                    description "Enter the lsp-refresh-interval context";

                    leaf interval {
                        type uint32 {
                            range "150..65535";
                        }
                        default "600";
                        description "Specify the interval at which LSPs are refreshed";
                    }

                    leaf half-lifetime {
                        type boolean;
                        default "true";
                        description "Refresh LSP interval at half the LSP lifetime";
                    }

                } // container lsp-refresh-interval

                container overload {
                    presence "Enable the overload context";
                    description "Enable the overload context";

                    leaf timeout {
                        type uint32 {
                            range "0|60..1800";
                        }
                        units "seconds";
                        default "0";
                        description "Time the router operates in overloaded state";
                    }

                } // container overload

                container overload-on-boot {
                    presence "Enable the overload-on-boot context";
                    description "Enable the overload-on-boot context";

                    leaf timeout {
                        type uint32 {
                            range "0|60..1800";
                        }
                        units "seconds";
                        default "0";
                        description "Time the router operates in overloaded state";
                    }

                } // container overload-on-boot

                container timers {
                    description "Enter the timers context";

                    container lsp-wait {
                        presence "Enable the lsp-wait context";
                        description "Enable the lsp-wait context";

                        leaf max-wait {
                            type types-services:spb-wait;
                            units "milliseconds";
                            default "5000";
                            description "Max wait time";
                        }

                        leaf initial-wait {
                            type types-services:spb-initial-wait;
                            units "milliseconds";
                            default "10";
                            description "Initial wait";
                        }

                        leaf second-wait {
                            type types-services:spb-second-wait;
                            units "milliseconds";
                            default "1000";
                            description "Second wait";
                        }

                    } // container lsp-wait

                    container spf-wait {
                        presence "Enable the spf-wait context";
                        description "Enable the spf-wait context";

                        leaf max-wait {
                            type types-services:spb-wait;
                            units "milliseconds";
                            default "10000";
                            description "Max wait time";
                        }

                        leaf initial-wait {
                            type types-services:spb-initial-wait;
                            units "milliseconds";
                            default "1000";
                            description "Initial wait";
                        }

                        leaf second-wait {
                            type types-services:spb-second-wait;
                            units "milliseconds";
                            default "1000";
                            description "Second wait";
                        }

                    } // container spf-wait

                } // container timers

                list level {
                    key "id";
                    description "Enter the level list instance";

                    leaf id {
                        type int32 {
                            range "1";
                        }
                        description "Level identifier";
                    }

                    leaf bridge-priority {
                        type int32 {
                            range "0..15";
                        }
                        default "8";
                        description "SPB Bridge priority";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container forwarding-tree {
                        description "Enter the forwarding-tree context";

                        leaf topology {
                            type enumeration {
                                enum spf                            { value 0; }
                                enum st                             { value 1; }
                            }
                            default "spf";
                            description "Topology";
                        }

                    } // container forwarding-tree

                    list ect-high-path-fid {
                        key "fid";
                        description "Add a list entry for ect-high-path-fid";

                        leaf fid {
                            type types-services:spb-fid;
                            description "SPB control vpls FID";
                        }

                    } // list ect-high-path-fid

                } // list level

            } // container spb

            container spbm-control-vpls {
                description "Enter the spbm-control-vpls context";

                leaf service-name {
                    type types-services:service-name;
                    description "SPB control vpls service";
                }

                leaf fid {
                    type types-services:spb-fid;
                    description "SPB control vpls FID";
                }

            } // container spbm-control-vpls

            list segment-routing-v6 {
                when "not(../pbb-type = 'b-vpls') and not(../pbb-type = 'i-vpls') and ../m-vpls = 'false' and ../etree = 'false' and not(../routed-vpls)" {
                    description "not supported on b-vpls/i-vpls/m-vpls, routed-vpls or etree";
                }
                key "instance";
                max-elements 1;
                description "Enter the segment-routing-v6 list instance";

                leaf instance {
                    type types-services:vpls-srv6-instance;
                    description "Segment routing v6 instance";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list locator {
                    key "locator-name";
                    max-elements 1;
                    description "Enter the locator list instance";

                    leaf locator-name {
                        type leafref {
                            path "../../../../../router/segment-routing/segment-routing-v6/locator/locator-name";
                        }
                        description "SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container end-dt2u {
                            presence "Enable the end-dt2u context";
                            description "Enable the end-dt2u context";

                            leaf value {
                                type uint32 {
                                    range "1..1048575";
                                }
                                description "SRv6 function value";
                            }

                        } // container end-dt2u

                        container end-dt2m {
                            presence "Enable the end-dt2m context";
                            description "Enable the end-dt2m context";

                            leaf value {
                                type uint32 {
                                    range "1..1048575";
                                }
                                description "SRv6 function value";
                            }

                        } // container end-dt2m

                    } // container function

                } // list locator

                list micro-segment-locator {
                    key "locator-name";
                    max-elements 1;
                    description "Enter the micro-segment-locator list instance";

                    leaf locator-name {
                        type leafref {
                            path "../../../../../router/segment-routing/segment-routing-v6/micro-segment-locator/locator-name";
                        }
                        description "Micro-segment SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container udt2m {
                            presence "Enable the udt2m context";
                            description "Enable the udt2m context";

                            leaf value {
                                type uint32 {
                                    range "1..1048575";
                                }
                                description "SRv6 function value";
                            }

                        } // container udt2m

                        container udt2u {
                            presence "Enable the udt2u context";
                            description "Enable the udt2u context";

                            leaf value {
                                type uint32 {
                                    range "1..1048575";
                                }
                                description "SRv6 function value";
                            }

                        } // container udt2u

                    } // container function

                } // list micro-segment-locator

            } // list segment-routing-v6

            container stp {
                description "Enter the stp context";

                leaf admin-state {
                    type types-sros:admin-state;
                    default "disable";
                    description "Administrative state of STP";
                }

                leaf forward-delay {
                    type int32 {
                        range "4..30";
                    }
                    default "15";
                    description "Configure forward-delay";
                }

                leaf hello-time {
                    type int32 {
                        range "1..10";
                    }
                    default "2";
                    description "Configure hello-time";
                }

                leaf hold-count {
                    type int32 {
                        range "1..20";
                    }
                    default "6";
                    description "Configure BPDU transmit hold count";
                }

                leaf maximum-age {
                    type int32 {
                        range "6..40";
                    }
                    default "20";
                    description "Configure maximum STP information age";
                }

                leaf mode {
                    type enumeration {
                        enum rstp                           { value 2; }
                        enum comp-dot1w                     { value 3; }
                        enum dot1w                          { value 4; }
                        enum mstp                           { value 5; }
                        enum pmstp                          { value 6; }
                    }
                    default "rstp";
                    description "Configure protocol version";
                }

                leaf mst-maximum-hops {
                    type int32 {
                        range "1..40";
                    }
                    default "20";
                    description "Maximum number of hops in an MSTP region";
                }

                leaf mst-name {
                    type types-sros:named-item;
                    description "MST region name";
                }

                leaf mst-revision {
                    type int32 {
                        range "0..65535";
                    }
                    description "MST configuration revision";
                }

                leaf priority {
                    type int32 {
                        range "0..65535";
                    }
                    default "32768";
                    description "STP bridge priority";
                }

                list mst-instance {
                    when "../../m-vpls = 'true'" {
                        description "supported on managed vpls service";
                    }
                    key "mst-inst-number";
                    description "Enter the mst-instance list instance";

                    leaf mst-inst-number {
                        type uint32 {
                            range "1..4094";
                        }
                        description "Multiple Spanning Tree Instance number";
                    }

                    leaf mst-priority {
                        type int32 {
                            range "0|4096|8192|12288|16384|20480|24576|28672|32768|36864|40960|45056|49152|53248|57344|61440";
                        }
                        default "32768";
                        description "Priority of multiple spanning tree instance";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list vlan-range {
                        key "range";
                        description "Add a list entry for vlan-range";

                        leaf range {
                            type string {
                                pattern "((([1-9]|[1-9][0-9]{1,2}|[1-3][0-9]{3}|40[0-8][0-9]|409[0-4]))(\\.\\.(([1-9]|[1-9][0-9]{1,2}|[1-3][0-9]{3}|40[0-8][0-9]|409[0-4])))?)";
                            }
                            description "Range of VLANs associated with the M-VPLS SAP";
                        }

                    } // list vlan-range

                } // list mst-instance

            } // container stp

            list bgp {
                key "bgp-instance";
                description "Enter the bgp list instance";

                leaf bgp-instance {
                    type int32 {
                        range "1..2";
                    }
                    description "BGP instance";
                }

                leaf route-distinguisher {
                    type types-services:vpn-route-distinguisher-or-auto-rd;
                    description "High-order 6 bytes that are used as string to compose VSI-ID for use in NLRI";
                }

                leaf-list vsi-import {
                    type leafref {
                        path "../../../../policy-options/policy-statement/name";
                    }
                    max-elements 5;
                    ordered-by user;
                    description "VSI import policies";
                }

                leaf-list vsi-export {
                    type leafref {
                        path "../../../../policy-options/policy-statement/name";
                    }
                    max-elements 5;
                    ordered-by user;
                    description "VSI export policies";
                }

                leaf adv-service-mtu {
                    type int32 {
                        range "0..9782";
                    }
                    description "Advertised service MTU value";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container route-target {
                    description "Enter the route-target context";

                    leaf export {
                        type types-services:route-target;
                        description "Extended community name for default import policy";
                    }

                    leaf import {
                        type types-services:route-target;
                        description "Extended community name for default import policy";
                    }

                } // container route-target

                list pw-template-binding {
                    key "pw-template-name";
                    max-elements 100;
                    description "Enter the pw-template-binding list instance";

                    leaf pw-template-name {
                        type leafref {
                            path "../../../../pw-template/pw-template-name";
                        }
                        description "Policy name";
                    }

                    leaf split-horizon-group {
                        type types-sros:named-item;
                        description "Split horizon group";
                    }

                    leaf bfd-template {
                        type leafref {
                            path "../../../../../bfd/bfd-template/name";
                        }
                        description "BFD template name for PW-Template binding";
                    }

                    leaf bfd-liveness {
                        type boolean;
                        default "false";
                        description "Enable BFD";
                    }

                    leaf-list import-rt {
                        type types-services:route-target;
                        max-elements 5;
                        description "Import route-target communities";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice oper-group-association {
                        case oper-group {

                            leaf oper-group {
                                type leafref {
                                    path "../../../../oper-group/name";
                                }
                                description "Operational group";
                            }

                        }
                        case monitor-oper-group {

                            leaf monitor-oper-group {
                                type leafref {
                                    path "../../../../oper-group/name";
                                }
                                description "Operational group to monitor";
                            }

                        }
                    }
                } // list pw-template-binding

            } // list bgp

            container igmp-snooping {
                when "not(../pbb-type = 'b-vpls') and not(../m-vpls = 'true')" {
                    description "not supported on b-vpls or m-vpls";
                }
                description "Enter the igmp-snooping context";

                leaf admin-state {
                    type types-sros:admin-state;
                    default "disable";
                    description "Administrative state of snooping";
                }

                leaf query-interval {
                    type types-sros:time-duration {
                        range "1..65535";
                    }
                    units "seconds";
                    default "125";
                    description "Time between two consecutive host-query messages";
                }

                leaf robust-count {
                    type uint32 {
                        range "1..255";
                    }
                    default "2";
                    description "Number of retries after expected message loss";
                }

                leaf report-source-address {
                    type types-sros:ipv4-address;
                    description "Source IP address used when generating IGMP reports";
                }

                leaf query-source-address {
                    type union {
                        type enumeration {
                            enum system                         { value 1; }
                        }
                        type types-sros:ipv4-address;
                    }
                    default "system";
                    description "Source address for IGMP queries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container mvr {
                    when "not(../../pbb-type = 'i-vpls')" {
                        description "not supported on i-vpls";
                    }
                    description "Enter the mvr context";

                    leaf admin-state {
                        type types-sros:admin-state;
                        default "disable";
                        description "Administrative state of MVR";
                    }

                    leaf group-policy {
                        type types-sros:named-item;
                        description "Policy that applies MVR";
                    }

                    leaf description {
                        type types-sros:description;
                        description "Text description";
                    }

                } // container mvr

                container evpn-proxy {
                    description "Enter the evpn-proxy context";

                    leaf admin-state {
                        type types-sros:admin-state;
                        default "disable";
                        description "Administrative state of EVPN proxy";
                    }

                } // container evpn-proxy

            } // container igmp-snooping

            container mld-snooping {
                when "not(../pbb-type = 'b-vpls') and not(../m-vpls = 'true')" {
                    description "not supported on b-vpls or m-vpls";
                }
                description "Enter the mld-snooping context";

                leaf admin-state {
                    type types-sros:admin-state;
                    default "disable";
                    description "Administrative state of snooping";
                }

                leaf query-interval {
                    type types-sros:time-duration {
                        range "1..65535";
                    }
                    units "seconds";
                    default "125";
                    description "Time between two consecutive host-query messages";
                }

                leaf robust-count {
                    type uint32 {
                        range "1..255";
                    }
                    default "2";
                    description "Number of retries after expected message loss";
                }

                leaf report-source-address {
                    type types-sros:ipv6-address;
                    description "Source IP address used when generating MLD reports";
                }

                leaf query-source-address {
                    type union {
                        type enumeration {
                            enum system                         { value 1; }
                        }
                        type types-sros:ipv6-address;
                    }
                    default "system";
                    description "Source IP address used in MLD queries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container mvr {
                    when "not(../../pbb-type = 'i-vpls')" {
                        description "not supported on i-vpls";
                    }
                    description "Enter the mvr context";

                    leaf admin-state {
                        type types-sros:admin-state;
                        default "disable";
                        description "Administrative state of MVR";
                    }

                    leaf group-policy {
                        type types-sros:named-item;
                        description "Policy that applies MVR";
                    }

                    leaf description {
                        type types-sros:description;
                        description "Text description";
                    }

                } // container mvr

                container evpn-proxy {
                    description "Enter the evpn-proxy context";

                    leaf admin-state {
                        type types-sros:admin-state;
                        default "disable";
                        description "Administrative state of EVPN proxy";
                    }

                } // container evpn-proxy

            } // container mld-snooping

            container pim-snooping {
                when "not(../pbb-type = 'b-vpls') and not(../m-vpls = 'true')" {
                    description "not supported on b-vpls or m-vpls";
                }
                presence "Enable the pim-snooping context";
                description "Enable the pim-snooping context";

                leaf hold-time {
                    type uint32 {
                        range "0..300";
                    }
                    units "seconds";
                    default "90";
                    description "Duration that allows the PIM-snooping switch to snoop all the PIM states in the VPLS";
                }

                leaf-list group-policy {
                    type types-sros:display-string;
                    max-elements 5;
                    ordered-by user;
                    description "Group policy name";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ipv4 {
                    description "Enter the ipv4 context";

                    leaf admin-state {
                        type types-sros:admin-state;
                        description "Administrative state of snooping for multicast traffic";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ipv4

                container ipv6 {
                    when "not(../../pbb-type = 'i-vpls')" {
                        description "VPLS PBB type must not be 'i-vpls'";
                    }
                    description "Enter the ipv6 context";

                    leaf admin-state {
                        type types-sros:admin-state;
                        description "Administrative state of snooping for multicast traffic";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ipv6

            } // container pim-snooping

            container bgp-ad {
                when "not(../pbb-type = 'i-vpls') and ../etree = 'false' and ../m-vpls = 'false'" {
                    description "not supported on i-vpls or m-vpls or etree";
                }
                presence "Enable the bgp-ad context";
                description "Enable the bgp-ad context";

                leaf admin-state {
                    type types-sros:admin-state;
                    default "disable";
                    description "Administrative state of BGP Auto-Discovery";
                }

                leaf vpls-id {
                    type types-services:vpls-id;
                    sros-ext:auto-restart-to-modify;
                    description "VPLS identifier as a 8-byte route distinguisher";
                }

                leaf vsi-id-prefix {
                    type types-sros:ipv4-address;
                    sros-ext:auto-restart-to-modify;
                    description "VSI prefix value";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container bgp-ad

            container bgp-evpn {
                when "not(../pbb-type = 'i-vpls') and not(../m-vpls = 'true')" {
                    description "not supported on i-vpls or m-vpls";
                }
                presence "Enable the bgp-evpn context";
                description "Enable the bgp-evpn context";

                leaf accept-ivpls-evpn-flush {
                    when "../../pbb-type = 'b-vpls'" {
                        description "VPLS PBB type must be 'b-vpls'";
                    }
                    type boolean;
                    default "false";
                    description "Accept and process non-zero ethernet-tag MAC routes";
                }

                leaf evi {
                    type types-services:evi;
                    description "EVPN ID";
                }

                leaf incl-mcast-orig-ip {
                    when "not(../../pbb-type = 'b-vpls')" {
                        description "VPLS PBB type must not be 'b-vpls'";
                    }
                    type types-sros:ipv4-unicast-address;
                    description "Originating IP address";
                }

                leaf ignore-mtu-mismatch {
                    type boolean;
                    default "false";
                    description "Ignore MTU mismatch";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container routes {
                    description "Enter the routes context";

                    container mac-ip {
                        description "Enter the mac-ip context";

                        leaf advertise {
                            type boolean;
                            default "true";
                            description "Status for the BGP-EVPN MAC/IP routes advertisement";
                        }

                        leaf cfm-mac {
                            type boolean;
                            default "false";
                            description "Enable advertisement and withdrawal of MAC address";
                        }

                        leaf unknown-mac {
                            when "not(../../../../pbb-type = 'b-vpls')" {
                                description "VPLS PBB type must not be 'b-vpls'";
                            }
                            type boolean;
                            default "false";
                            description "Enable advertisement of unknown MAC route in BGP";
                        }

                        leaf arp-nd-extended-community {
                            type boolean;
                            default "false";
                            description "Enable ARP/ND extended community";
                        }

                        leaf arp-nd-only-with-fdb-advertisement {
                            type boolean;
                            default "false";
                            description "Advertise ARP/ND entries if local MAC is in the FDB";
                        }

                    } // container mac-ip

                    container ip-prefix {
                        when "../../../routed-vpls" {
                            description "routed VPLS must be present";
                        }
                        description "Enter the ip-prefix context";

                        leaf advertise {
                            type boolean;
                            default "false";
                            description "Status for the IP prefix routes advertisement";
                        }

                        leaf include-direct-interface-host {
                            type boolean;
                            default "false";
                            description "Advertise the interface host address in EVPN";
                        }

                        leaf domain-id {
                            type types-services:domain-id;
                            description "Domain ID of received BGP route before readvertisement";
                        }

                        container link-bandwidth {
                            description "Enter the link-bandwidth context";

                            leaf weighted-ecmp {
                                type boolean;
                                default "false";
                                description "Enable weighted ECMP";
                            }

                            container advertise {
                                presence "Enable the advertise context";
                                description "Enable the advertise context";

                                leaf max-dynamic-weight {
                                    type uint32 {
                                        range "1..128";
                                    }
                                    default "128";
                                    description "Maximum weight of the advertised evpn-iff route";
                                }

                                leaf weight {
                                    type union {
                                        type uint32 {
                                            range "1..128";
                                        }
                                        type enumeration {
                                            enum dynamic                        { value 0; }
                                        }
                                    }
                                    default "dynamic";
                                    description "Weight of the advertised evpn-iff route";
                                }

                            } // container advertise

                        } // container link-bandwidth

                    } // container ip-prefix

                    container incl-mcast {
                        description "Enter the incl-mcast context";

                        leaf advertise-ingress-replication {
                            type boolean;
                            default "true";
                            description "BGP EVPN IMET-IR route advertisement";
                        }

                        leaf advertise-l2-attributes {
                            type boolean;
                            default "false";
                            description "Advertise Layer 2 attributes";
                        }

                    } // container incl-mcast

                    container sel-mcast {
                        description "Enter the sel-mcast context";

                        leaf advertise {
                            type boolean;
                            default "false";
                            description "Advertise Selective Multicast Ethernet Tag routes";
                        }

                    } // container sel-mcast

                } // container routes

                container mac-duplication {
                    description "Enter the mac-duplication context";

                    leaf retry {
                        type union {
                            type uint32 {
                                range "2..60";
                            }
                            type enumeration {
                                enum never                          { value 0; }
                            }
                        }
                        units "minutes";
                        default "9";
                        description "BGP EVPN MAC duplication retry time";
                    }

                    leaf blackhole {
                        when "not(../../../pbb-type = 'b-vpls')" {
                            description "VPLS PBB type must not be 'b-vpls'";
                        }
                        type boolean;
                        default "false";
                        description "Use duplicated MAC as a black-hole MAC";
                    }

                    leaf trusted-mac-time {
                        type uint32 {
                            range "1..15";
                        }
                        units "minutes";
                        default "5";
                        description "Trusted MAC time";
                    }

                    container detect {
                        description "Enter the detect context";

                        leaf num-moves {
                            type uint32 {
                                range "3..10";
                            }
                            default "5";
                            description "BGP EVPN MAC duplication detection number of moves";
                        }

                        leaf window {
                            type uint32 {
                                range "1..15";
                            }
                            units "minutes";
                            default "3";
                            description "BGP EVPN MAC duplication detection window";
                        }

                        leaf trusted-mac-move-factor {
                            type uint32 {
                                range "1..10";
                            }
                            default "1";
                            description "Trusted MAC move factor";
                        }

                    } // container detect

                } // container mac-duplication

                container isid-route-target {
                    description "Enter the isid-route-target context";

                    list range {
                        key "start";
                        max-elements 8192;
                        description "Enter the range list instance";

                        leaf start {
                            type types-sros:svc-isid-non-zero;
                            description "Lower bound of the ISID range";
                        }

                        leaf end {
                            type types-sros:svc-isid-non-zero;
                            mandatory true;
                            description "Upper bound of the ISID range";
                        }

                        leaf type {
                            type enumeration {
                                enum auto                           { value 1; }
                                enum configured                     { value 2; }
                            }
                            sros-ext:immutable;
                            default "auto";
                            description "Method used to support the PBB-EVPN ISID-based route target advertisement";
                        }

                        leaf route-target {
                            when "../type = 'configured'" {
                                description "type must be 'configured'";
                            }
                            type types-services:route-target;
                            sros-ext:immutable;
                            description "Route for the ISID range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list range

                } // container isid-route-target

                list segment-routing-v6 {
                    when "not(../../pbb-type = 'b-vpls') and not(../../pbb-type = 'i-vpls') and ../../m-vpls = 'false' and ../../etree = 'false' and not(../../routed-vpls)" {
                        description "not supported on b-vpls/i-vpls/m-vpls, routed-vpls or etree";
                    }
                    key "bgp-instance";
                    max-elements 1;
                    description "Enter the segment-routing-v6 list instance";

                    leaf bgp-instance {
                        type int32 {
                            range "1..2";
                        }
                        description "BGP instance";
                    }

                    leaf admin-state {
                        type types-sros:admin-state;
                        default "disable";
                        description "Administrative state of segment routing over IPv6";
                    }

                    leaf default-route-tag {
                        type types-services:one-byte-value;
                        sros-ext:auto-restart-to-modify;
                        description "Default route tag";
                    }

                    leaf oper-group {
                        type leafref {
                            path "../../../../oper-group/name";
                        }
                        description "Operational group";
                    }

                    leaf ecmp {
                        type types-services:ecmp-value;
                        default "1";
                        description "Maximum ECMP value configured on the service";
                    }

                    leaf force-vc-forwarding {
                        type enumeration {
                            enum vlan                           { value 1; }
                            enum qinq-c-tag-c-tag               { value 2; }
                            enum qinq-s-tag-c-tag               { value 3; }
                        }
                        description "Datapath forwarding to force vlan-vc-type";
                    }

                    leaf evi-three-byte-auto-rt {
                        type boolean;
                        sros-ext:auto-restart-to-modify;
                        default "false";
                        description "Auto-derive the BGP EVPN route target";
                    }

                    leaf split-horizon-group {
                        type leafref {
                            path "../../../../vpls/split-horizon-group/shg-name";
                        }
                        sros-ext:auto-restart-to-modify;
                        description "Split horizon group";
                    }

                    leaf source-address {
                        type types-sros:ipv6-unicast-address;
                        sros-ext:auto-restart-to-modify;
                        description "Source IPv6 address";
                    }

                    leaf resolution {
                        type types-sros:srv6-route-resolution;
                        default "route-table";
                        description "Resolution options for routes";
                    }

                    leaf mh-mode {
                        type enumeration {
                            enum access                         { value 0; }
                            enum network                        { value 1; }
                        }
                        sros-ext:auto-restart-to-modify;
                        default "network";
                        description "Multihoming mode";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container srv6 {
                        description "Enter the srv6 context";

                        leaf instance {
                            type leafref {
                                path "../../../../segment-routing-v6/instance";
                            }
                            sros-ext:immutable;
                            description "Segment Routing SRv6 instance";
                        }

                        leaf default-locator {
                            type string;
                            sros-ext:immutable;
                            description "Default route locator";
                        }

                    } // container srv6

                    container route-next-hop {
                        description "Enter the route-next-hop context";

                        choice tag {
                            default "ipv4";
                            case ipv4 {

                                leaf system-ipv4 {
                                    type empty;
                                    sros-ext:auto-restart-to-modify;
                                    description "System IPv4 address for service EVPN route next hop";
                                }

                            }
                            case ipv6 {

                                leaf system-ipv6 {
                                    type empty;
                                    sros-ext:auto-restart-to-modify;
                                    description "System IPv6 address for service EVPN route next hop";
                                }

                            }
                            case explicit {

                                leaf ip-address {
                                    type types-sros:ip-address;
                                    sros-ext:auto-restart-to-modify;
                                    description "IP address of the next-hop for the service EVPN route";
                                }

                            }
                        }
                    } // container route-next-hop

                    container fdb {
                        description "Enter the fdb context";

                        leaf protected-src-mac-violation-action {
                            type types-services:protected-src-mac-violation-df-action;
                            description "Relearn request for a protected MAC is received action";
                        }

                    } // container fdb

                } // list segment-routing-v6

                list vxlan {
                    key "bgp-instance";
                    description "Enter the vxlan list instance";

                    leaf bgp-instance {
                        type int32 {
                            range "1..2";
                        }
                        description "BGP instance";
                    }

                    leaf vxlan-instance {
                        type leafref {
                            path "../../../vxlan/instance/vxlan-instance";
                        }
                        sros-ext:immutable;
                        mandatory true;
                        description "VXLAN instance";
                    }

                    leaf admin-state {
                        type types-sros:admin-state;
                        default "disable";
                        description "Administrative state of VXLAN auto-bindings creation";
                    }

                    leaf send-tunnel-encap {
                        type boolean;
                        sros-ext:auto-restart-to-modify;
                        default "true";
                        description "Send VXLAN value in encapsulation extended community";
                    }

                    leaf send-incl-mcast-ir-on-ndf {
                        type boolean;
                        sros-ext:auto-restart-to-modify;
                        default "true";
                        description "Allow IMET-IR on NDF";
                    }

                    leaf default-route-tag {
                        type types-services:one-byte-value;
                        sros-ext:auto-restart-to-modify;
                        description "Default route tag";
                    }

                    leaf ecmp {
                        type types-services:ecmp-value;
                        default "1";
                        description "Number of paths to reach a specified MAC address";
                    }

                    leaf oper-group {
                        type leafref {
                            path "../../../../oper-group/name";
                        }
                        description "Operational group ID";
                    }

                    leaf mh-mode {
                        type enumeration {
                            enum access                         { value 0; }
                            enum network                        { value 1; }
                        }
                        sros-ext:auto-restart-to-modify;
                        default "access";
                        description "Multi-homing mode";
                    }

                    leaf evi-three-byte-auto-rt {
                        type boolean;
                        sros-ext:auto-restart-to-modify;
                        default "false";
                        description "Auto-derive the BGP EVPN route target";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container routes {
                        description "Enter the routes context";

                        container auto-disc {
                            description "Enter the auto-disc context";

                            leaf advertise {
                                type boolean;
                                sros-ext:auto-restart-to-modify;
                                default "false";
                                description "Advertise routes on auto-discovery";
                            }

                        } // container auto-disc

                    } // container routes

                } // list vxlan

                list mpls {
                    key "bgp-instance";
                    description "Enter the mpls list instance";

                    leaf bgp-instance {
                        type int32 {
                            range "1..2";
                        }
                        description "BGP instance";
                    }

                    leaf admin-state {
                        type types-sros:admin-state;
                        default "disable";
                        description "Administrative state of BGP EVPN MPLS";
                    }

                    leaf force-vc-forwarding {
                        when "not(../../../pbb-type = 'b-vpls') and not(../../../routed-vpls)" {
                            description "VPLS PBB type must not be 'b-vpls' and routed VPLS must not be present";
                        }
                        type types-services:bgp-evpn-force-vc-forwarding;
                        description "VC forwarding action";
                    }

                    leaf control-word {
                        type boolean;
                        sros-ext:auto-restart-to-modify;
                        default "false";
                        description "Enable control word support";
                    }

                    leaf split-horizon-group {
                        type leafref {
                            path "../../../split-horizon-group/shg-name";
                        }
                        sros-ext:auto-restart-to-modify;
                        description "Split horizon group";
                    }

                    leaf ingress-replication-bum-label {
                        type boolean;
                        sros-ext:auto-restart-to-modify;
                        default "false";
                        description "Use the same label as the one advertised for unicast traffic";
                    }

                    leaf ecmp {
                        type types-services:ecmp-value;
                        default "1";
                        description "Maximum ECMP routes information";
                    }

                    leaf entropy-label {
                        type boolean;
                        default "false";
                        description "Allow use of entropy labels for spoke SDPs";
                    }

                    leaf default-route-tag {
                        type types-services:one-byte-value;
                        sros-ext:auto-restart-to-modify;
                        description "Default route tag";
                    }

                    leaf oper-group {
                        type leafref {
                            path "../../../../oper-group/name";
                        }
                        description "Operational group ID";
                    }

                    leaf evi-three-byte-auto-rt {
                        type boolean;
                        sros-ext:auto-restart-to-modify;
                        default "false";
                        description "Auto-derive the BGP EVPN route target";
                    }

                    leaf mh-mode {
                        type enumeration {
                            enum access                         { value 0; }
                            enum network                        { value 1; }
                        }
                        sros-ext:auto-restart-to-modify;
                        default "network";
                        description "Multihoming mode";
                    }

                    leaf dynamic-egress-label-limit {
                        type boolean;
                        default "false";
                        description "Enables dynamic egress label limit";
                    }

                    leaf hash-label {
                        type boolean;
                        default "false";
                        description "Default profile when the CP-provided profile is unknown";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container send-tunnel-encap {
                        description "Enter the send-tunnel-encap context";

                        leaf mpls {
                            type boolean;
                            sros-ext:auto-restart-to-modify;
                            default "true";
                            description "Enable MPLS encapsulation";
                        }

                        leaf mpls-over-udp {
                            type boolean;
                            sros-ext:auto-restart-to-modify;
                            default "false";
                            description "Enable MPLS over UDP encapsulation";
                        }

                    } // container send-tunnel-encap

                    container auto-bind-tunnel {
                        description "Enter the auto-bind-tunnel context";

                        leaf resolution {
                            type types-services:resolve-status;
                            default "none";
                            description "Resolution method for tunnel selection";
                        }

                        leaf enforce-strict-tunnel-tagging {
                            type boolean;
                            default "false";
                            description "Enable/disable enforcement of strict tunnel tagging";
                        }

                        leaf ecmp {
                            type types-router:mpls-ecmp;
                            default "1";
                            description "Maximum ECMP routes information";
                        }

                        leaf allow-flex-algo-fallback {
                            type boolean;
                            default "false";
                            description "Enable flexible algorithm fallback";
                        }

                        leaf weighted-ecmp {
                            type boolean;
                            default "false";
                            description "Allow weighted load balancing";
                        }

                        container resolution-filter {
                            description "Enter the resolution-filter context";

                            leaf bgp {
                                type boolean;
                                default "false";
                                description "Use BGP tunneling for next-hop resolution";
                            }

                            leaf ldp {
                                type boolean;
                                default "false";
                                description "Use LDP tunneling for next-hop resolution";
                            }

                            leaf rsvp {
                                type boolean;
                                default "false";
                                description "Use RSVP tunneling for next-hop resolution";
                            }

                            leaf sr-isis {
                                type boolean;
                                default "false";
                                description "Use IS-IS SR tunneling for next-hop resolution";
                            }

                            leaf sr-ospf {
                                type boolean;
                                default "false";
                                description "Use OSPF SR tunneling for next-hop resolution";
                            }

                            leaf sr-te {
                                type boolean;
                                default "false";
                                description "Use SR-TE tunneling for next-hop resolution";
                            }

                            leaf udp {
                                type boolean;
                                default "false";
                                description "Use MPLS over UDP tunneling for next-hop resolution";
                            }

                            leaf mpls-fwd-policy {
                                type boolean;
                                default "false";
                                description "Use MPLS forwarding policy for next-hop resolution";
                            }

                            leaf sr-policy {
                                type boolean;
                                default "false";
                                description "Use SR policies for next-hop resolution";
                            }

                            leaf rib-api {
                                type boolean;
                                default "false";
                                description "Use RIB API gRPC service for next-hop resolution";
                            }

                            leaf sr-ospf3 {
                                type boolean;
                                default "false";
                                description "Use OSPFv3 SR tunneling for next-hop resolution";
                            }

                        } // container resolution-filter

                    } // container auto-bind-tunnel

                    container route-next-hop {
                        description "Enter the route-next-hop context";

                        choice tag {
                            default "ipv4";
                            case ipv4 {

                                leaf system-ipv4 {
                                    type empty;
                                    sros-ext:auto-restart-to-modify;
                                    description "System IPv4 address for service EVPN route next hop";
                                }

                            }
                            case ipv6 {

                                leaf system-ipv6 {
                                    type empty;
                                    sros-ext:auto-restart-to-modify;
                                    description "System IPv6 address for service EVPN route next hop";
                                }

                            }
                            case explicit {

                                leaf ip-address {
                                    type types-sros:ip-address;
                                    sros-ext:auto-restart-to-modify;
                                    description "IP address of the next-hop for the service EVPN route";
                                }

                            }
                        }
                    } // container route-next-hop

                    container fdb {
                        description "Enter the fdb context";

                        leaf protected-src-mac-violation-action {
                            type types-services:protected-src-mac-violation-df-action;
                            description "Relearn request for a protected MAC is received action";
                        }

                    } // container fdb

                } // list mpls


            } // container bgp-evpn

            container bgp-vpls {
                when "not(../pbb-type = 'i-vpls') and ../etree = 'false'" {
                    description "bgp-vpls not supported on i-vpls or etree enabled";
                }
                presence "Enable the bgp-vpls context";
                description "Enable the bgp-vpls context";

                leaf admin-state {
                    type types-sros:admin-state;
                    default "disable";
                    description "Administrative state of the BGP-VPLS instance";
                }

                leaf maximum-ve-id {
                    type types-services:ve-id;
                    description "Maximum vpls-edge id for BGP-VPLS";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ve {
                    description "Enter the ve context";

                    leaf name {
                        type types-sros:named-item;
                        description "VPLS Edge instance name";
                    }

                    leaf id {
                        type types-services:ve-id;
                        description "VPLS edge ID";
                    }

                } // container ve

            } // container bgp-vpls

            list endpoint {
                key "name";
                max-elements 10;
                description "Enter the endpoint list instance";

                leaf name {
                    type types-sros:named-item;
                    description "Service endpoint name";
                }

                leaf description {
                    type types-sros:description;
                    description "Text description";
                }

                leaf revert-time {
                    type types-services:revert-time;
                    default "immediate";
                    description "Time to wait before reverting to primary spoke SDP";
                }

                leaf ignore-standby-signaling {
                    type boolean;
                    default "false";
                    description "Ignore standby-bit received from TLDP peers when performing internal tasks";
                }

                leaf suppress-standby-signaling {
                    type boolean;
                    default "true";
                    description "Do not send pseudowire standby bit to TLDP peer when specified spoke SDP is selected as standby";
                }

                leaf block-on-mesh-failure {
                    type boolean;
                    default "false";
                    description "Enable blocking after the endpoints are in a down state";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container fdb {
                    description "Enter the fdb context";

                    leaf mac-pinning {
                        type boolean;
                        default "false";
                        description "Activate MAC address pinning on this endpoint";
                    }

                    leaf maximum-mac-addresses {
                        type types-services:max-mac-addr;
                        description "Maximum number of MAC address entries in the FDB";
                    }

                    leaf auto-learn-mac-protect {
                        type boolean;
                        default "false";
                        description "Populate automatically MAC protect list with MAC addresses learned on SDP with this endpoint";
                    }

                    leaf protected-src-mac-violation-action {
                        type types-services:sdp-protected-src-mac-violation-action;
                        description "Action when a relearn request for a protected MAC is received on the SDP";
                    }

                } // container fdb

                list mc-endpoint {
                    key "mc-ep-id";
                    max-elements 1;
                    description "Enter the mc-endpoint list instance";

                    leaf mc-ep-id {
                        type uint32 {
                            range "1..4294967295";
                        }
                        description "MC-EP ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mc-ep-peer {
                        description "Enter the mc-ep-peer context";

                        choice peer {
                            case address {

                                leaf peer-address {
                                    type leafref {
                                        path "../../../../../../redundancy/multi-chassis/peer/ip-address";
                                    }
                                    description "IP address of the MC-EP peer";
                                }

                            }
                            case name {

                                leaf name {
                                    type types-sros:named-item;
                                    description "Name of the MC-EP peer";
                                }

                            }
                        }
                    } // container mc-ep-peer

                } // list mc-endpoint

            } // list endpoint

            list split-horizon-group {
                when "not(../m-vpls = 'true')" {
                    description "not supported on m-vpls";
                }
                key "shg-name";
                description "Enter the split-horizon-group list instance";

                leaf shg-name {
                    type types-sros:named-item;
                    description "SHG name to which the SDP belongs";
                }

                leaf description {
                    type types-sros:description;
                    description "Text description";
                }

                leaf residential {
                    when "not(../../pbb-type) and not(../../routed-vpls)" {
                        description "VPLS PBB type must be 'none' and routed VPLS must not be set";
                    }
                    type boolean;
                    sros-ext:immutable;
                    default "false";
                    description "Define as a residential split horizon group";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container fdb {
                    description "Enter the fdb context";

                    container saps {
                        description "Enter the saps context";

                        leaf auto-learn-mac-protect {
                            type boolean;
                            default "false";
                            description "Populate automatically MAC protect list with MAC addresses learned on SDP with split horizon group";
                        }

                        leaf auto-learn-mac-protect-exclude-list {
                            type leafref {
                                path "../../../../../mac-list/name";
                            }
                            description "Referenced MAC protect exclusion list name";
                        }

                        leaf protected-src-mac-violation-action {
                            type types-services:sap-protected-src-mac-violation-action;
                            description "Action to take whenever a relearn request for a protected MAC is received";
                        }

                        leaf discard-unprotected-dest-mac {
                            type boolean;
                            default "false";
                            description "Discard packet with unprotected destination MAC address";
                        }

                    } // container saps

                } // container fdb

            } // list split-horizon-group

            container eth-cfm {
                description "Enter the eth-cfm context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list mep {
                    key "md-admin-name ma-admin-name mep-id";
                    description "Enter the mep list instance";

                    leaf md-admin-name {
                        type leafref {
                            path "../../../../../eth-cfm/domain/md-admin-name";
                        }
                        description "Maintenance Domain (MD) name";
                    }

                    leaf ma-admin-name {
                        type leafref {
                            path "../../../../../eth-cfm/domain[md-admin-name=current()/../md-admin-name]/association/ma-admin-name";
                        }
                        description "Maintenance Association (MA) name";
                    }

                    leaf mep-id {
                        type types-eth-cfm:mep-id-type;
                        description "Maintenance Endpoint (MEP) ID";
                    }

                    leaf admin-state {
                        type types-sros:admin-state;
                        default "disable";
                        description "Administrative state of the MEP";
                    }

                    leaf description {
                        type types-sros:description;
                        description "Text description";
                    }

                    leaf mac-address {
                        type types-sros:mac-unicast-address-no-zero;
                        description "MAC address of the MEP";
                    }

                    leaf cfm-vlan-tag {
                        type types-sros:one-or-two-vlan-tags;
                        description "VLAN tags to apply to CFM PDUs for egress processing";
                    }

                    leaf low-priority-defect {
                        type types-eth-cfm:lowest-alarm-priority;
                        default "mac-rem-err-xcon";
                        description "Lowest priority defect allowed to generate fault alarm";
                    }

                    leaf ccm {
                        type boolean;
                        default "false";
                        description "Generate CCM messages";
                    }

                    leaf ccm-ltm-priority {
                        type types-eth-cfm:frame-priority;
                        default "7";
                        description "Priority of CCM and LTM messages transmitted by the MEP";
                    }

                    leaf ccm-padding-size {
                        type uint32 {
                            range "3..1500";
                        }
                        description "Number of octets of padding to insert in CCM packets";
                    }

                    leaf one-way-delay-threshold {
                        type uint32 {
                            range "0..600";
                        }
                        units "seconds";
                        default "3";
                        description "Threshold time limit for the one-way delay test";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container alarm-notification {
                        description "Enter the alarm-notification context";

                        leaf fng-alarm-time {
                            type int32 {
                                range "250|500|1000";
                            }
                            units "centiseconds";
                            description "Time that must expire before an FNG alarm is raised";
                        }

                        leaf fng-reset-time {
                            type int32 {
                                range "250|500|1000";
                            }
                            units "centiseconds";
                            description "Time that must expire before an FNG alarm is reset";
                        }

                    } // container alarm-notification

                    container eth-test {
                        presence "Enable the eth-test context";
                        description "Enable the eth-test context";

                        leaf bit-error-threshold {
                            type uint32 {
                                range "0..11840";
                            }
                            units "bit errors";
                            default "1";
                            description "Lowest priority defect allowed to generate fault alarm";
                        }

                        container test-pattern {
                            description "Enter the test-pattern context";

                            leaf pattern {
                                type enumeration {
                                    enum all-zeros                      { value 0; }
                                    enum all-ones                       { value 1; }
                                }
                                default "all-zeros";
                                description "Test pattern for Ethernet Test frames";
                            }

                            leaf crc-tlv {
                                type boolean;
                                default "false";
                                description "Generate a CRC checksum";
                            }

                        } // container test-pattern

                    } // container eth-test

                    container grace {
                        description "Enter the grace context";

                        container eth-ed {
                            description "Enter the eth-ed context";

                            leaf max-rx-defect-window {
                                type uint32 {
                                    range "1..86400";
                                }
                                units "seconds";
                                description "Maximum received ETH-ED expected defect window duration";
                            }

                            leaf priority {
                                type int32 {
                                    range "0..7";
                                }
                                description "Transmission priority for ETH-ED PDUs";
                            }

                            leaf rx-eth-ed {
                                type boolean;
                                default "true";
                                description "Receive and process ETH-ED ITU-T Y.1731 PDUs on the MEP";
                            }

                            leaf tx-eth-ed {
                                type boolean;
                                default "false";
                                description "Transmit ETH-ED PDUs from the MEP";
                            }

                        } // container eth-ed

                        container eth-vsm-grace {
                            description "Enter the eth-vsm-grace context";

                            leaf rx-eth-vsm-grace {
                                type boolean;
                                default "true";
                                description "Receive and process Nokia ETH-CFM Grace PDU on the MEP";
                            }

                            leaf tx-eth-vsm-grace {
                                type boolean;
                                default "true";
                                description "Transmit ETH-ED PDUs from the MEP";
                            }

                        } // container eth-vsm-grace

                    } // container grace

                } // list mep

            } // container eth-cfm

            container mcr-default-gtw {
                when "not(../pbb-type)" {
                    description "VPLS PBB type must be 'none'";
                }
                description "Enter the mcr-default-gtw context";

                leaf ip {
                    type types-sros:ipv4-unicast-address;
                    description "Multi-chassis ring default gateway IP address";
                }

                leaf mac {
                    type yang:mac-address;
                    default "00:00:00:00:00:00";
                    description "Multi-chassis ring default gateway MAC address";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container mcr-default-gtw

            list spoke-sdp {
                key "sdp-bind-id";
                description "Enter the spoke-sdp list instance";

                leaf sdp-bind-id {
                    type types-services:sdp-bind-id;
                    description "SDP binding ID";
                }

                leaf description {
                    type types-sros:description;
                    description "Text description";
                }

                leaf admin-state {
                    type types-sros:admin-state;
                    default "enable";
                    description "Administrative state of the SDP binding to the service";
                }

                leaf vlan-vc-tag {
                    type types-services:vlan-vc-tag;
                    description "SDP bind VC tag";
                }

                leaf split-horizon-group {
                    type leafref {
                        path "../../split-horizon-group/shg-name";
                    }
                    sros-ext:immutable;
                    description "Name of the split horizon group where the spoke SDP bind belongs to";
                }

                leaf multicast-source {
                    type boolean;
                    sros-ext:immutable;
                    default "false";
                    description "Enable multicast-source on the spoke SDP bind";
                }

                leaf collect-stats {
                    type boolean;
                    default "false";
                    description "Allow agent to collect accounting statistics";
                }

                leaf accounting-policy {
                    type leafref {
                        path "../../../../log/accounting-policy/policy-id";
                    }
                    description "Policy to collect accounting statistics";
                }

                leaf control-word {
                    type boolean;
                    default "false";
                    description "Use the control word as preferred";
                }

                leaf force-vc-forwarding {
                    type enumeration {
                        enum vlan                           { value 1; }
                        enum qinq-c-tag-c-tag               { value 2; }
                        enum qinq-s-tag-c-tag               { value 3; }
                    }
                    description "VC forwarding action";
                }

                leaf app-profile {
                    type leafref {
                        path "../../../../application-assurance/group/partition/policy/app-profile/app-profile-name";
                    }
                    description "ISA-AA application profile name for this SDP";
                }

                leaf etree-root-leaf-tag {
                    when "../../etree = 'true'" {
                        description "etree must be set";
                    }
                    type boolean;
                    sros-ext:immutable;
                    default "false";
                    description "E-tree root leaf tag status";
                }

                leaf etree-leaf {
                    when "../../etree = 'true'" {
                        description "etree must be set";
                    }
                    type boolean;
                    sros-ext:immutable;
                    default "false";
                    description "Enable etree leaf access-circuit status";
                }

                leaf bfd-template {
                    status obsolete;
                    type leafref {
                        path "../../../../bfd/bfd-template/name";
                    }
                    description "BFD template associated with SDP binding";
                }

                leaf vc-type {
                    type types-services:vpls-sdp-bind-vc-type;
                    sros-ext:auto-restart-to-modify;
                    default "ether";
                    description "Type of virtual circuit (VC) associated with the SDP binding; VPLS not supported";
                }

                leaf bpdu-translation {
                    type types-services:bpdu-translation;
                    description "BPDU format";
                }

                leaf ignore-standby-signaling {
                    type boolean;
                    default "false";
                    description "Ignore standby-bit received from TLDP peers when performing internal tasks";
                }

                leaf block-on-mesh-failure {
                    type boolean;
                    default "false";
                    description "Enable blocking after all SDPs are operationally down";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice label {
                    case entropy {

                        leaf entropy-label {
                            type empty;
                            description "Enable the use of entropy labels for spoke SDPs";
                        }

                    }
                    case hash {

                        container hash-label {
                            presence "Enable the hash-label context";
                            description "Enable the hash-label context";

                            leaf signal-capability {
                                type empty;
                                description "Signal hash label capability to the remote PE";
                            }

                        } // container hash-label

                    }
                }
                choice oper-group-association {
                    case oper-group {

                        leaf oper-group {
                            type leafref {
                                path "../../../oper-group/name";
                            }
                            description "Operational group identifier";
                        }

                    }
                    case monitor-oper-group {

                        leaf monitor-oper-group {
                            type leafref {
                                path "../../../oper-group/name";
                            }
                            description "Operational group that affects state of the SDP bind";
                        }

                    }
                }
                container ingress {
                    description "Enter the ingress context";

                    leaf vc-label {
                        type types-services:ingress-vc-label;
                        sros-ext:auto-restart-to-modify;
                        description "Ingress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container fp-redirect-group {
                                description "Enter the fp-redirect-group context";

                                leaf group-name {
                                    type leafref {
                                        path "../../../../../../../../qos/queue-group-templates/ingress/queue-group/ingress-queue-group-name";
                                    }
                                    description "Name of the forwarding plane queue group template";
                                }

                                leaf instance {
                                    type types-services:qos-qgrp-instance-id;
                                    description "Instance of FP ingress queue group for the SDP binding";
                                }

                            } // container fp-redirect-group

                        } // container network

                    } // container qos

                } // container ingress

                container egress {
                    description "Enter the egress context";

                    leaf vc-label {
                        type types-services:egress-vc-label;
                        sros-ext:auto-restart-to-modify;
                        description "Egress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container port-redirect-group {
                                description "Enter the port-redirect-group context";

                                leaf group-name {
                                    type leafref {
                                        path "../../../../../../../../qos/queue-group-templates/egress/queue-group/egress-queue-group-name";
                                    }
                                    description "Name of the egress port queue group";
                                }

                                leaf instance {
                                    type types-services:qos-qgrp-instance-id;
                                    description "Queue-group instance ID";
                                }

                            } // container port-redirect-group

                        } // container network

                    } // container qos

                    container mfib-allowed-mda-destinations {
                        description "Enter the mfib-allowed-mda-destinations context";

                        list mda {
                            key "mda-id";
                            description "Add a list entry for mda";

                            leaf mda-id {
                                type types-isa:slot-mda;
                                description "MFIB allowed MDA destination";
                            }

                        } // list mda

                    } // container mfib-allowed-mda-destinations

                } // container egress

                container endpoint {
                    description "Enter the endpoint context";

                    leaf name {
                        type leafref {
                            path "../../../../vpls[service-name=current()/../../../service-name]/endpoint/name";
                        }
                        sros-ext:auto-restart-to-modify;
                        description "Name of service endpoint to which SDP bind is attached";
                    }

                    leaf precedence {
                        type types-services:sdp-precedence;
                        default "4";
                        description "Precedence of this SDP bind when there are multiple SDP binds attached to one service endpoint";
                    }

                } // container endpoint

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                        case cfm {

                            container eth-cfm-monitoring {
                                presence "Enable the eth-cfm-monitoring context";
                                description "Enable the eth-cfm-monitoring context";

                                leaf aggregate {
                                    type empty;
                                    description "Apply rate limit to the sum of the per peer packet rates";
                                }

                                leaf car {
                                    type empty;
                                    description "Ignore Ethernet CFM packets when enforcing overall rate";
                                }

                            } // container eth-cfm-monitoring

                        }
                    }
                } // container cpu-protection

                container pw-status {
                    description "Enter the pw-status context";

                    leaf signaling {
                        type boolean;
                        default "true";
                        description "Enable the use of pseudowire status signaling";
                    }

                } // container pw-status

                container bfd-liveness {
                    status obsolete;
                    presence "Enable the bfd-liveness context";
                    description "Enable the bfd-liveness context";

                    leaf encap {
                        status obsolete;
                        type types-services:bfd-encap;
                        default "ipv4";
                        description "BFD encapsulation used on the SDP binding";
                    }

                } // container bfd-liveness

                container bfd {
                    description "Enter the bfd context";

                    leaf bfd-template {
                        type leafref {
                            path "../../../../../bfd/bfd-template/name";
                        }
                        description "BFD template associated with the SDP binding";
                    }

                    leaf failure-action {
                        type types-services:sbind-bfd-fail-action;
                        default "none";
                        description "VCCV BFD action taken on the SDP binding";
                    }

                    leaf wait-for-up-timer {
                        type uint32 {
                            range "1..60";
                        }
                        units "seconds";
                        description "Time waited for BFD up status";
                    }

                    container bfd-liveness {
                        presence "Enable the bfd-liveness context";
                        description "Enable the bfd-liveness context";

                        leaf encap {
                            type types-services:bfd-encap;
                            default "ipv4";
                            description "BFD encapsulation used on the SDP binding";
                        }

                    } // container bfd-liveness

                } // container bfd

                container transit-policy {
                    presence "Enable the transit-policy context";
                    description "Enable the transit-policy context";

                    leaf prefix {
                        type leafref {
                            path "../../../../../application-assurance/group/partition/transit-prefix-policy/prefix-policy-id";
                        }
                        sros-ext:immutable;
                        mandatory true;
                        description "IP prefix policy ID";
                    }

                } // container transit-policy

                container pbb {
                    when "../../pbb-type = 'b-vpls'" {
                        description "supported on b-vpls service";
                    }
                    description "Enter the pbb context";

                    container fault-propagation {
                        description "Enter the fault-propagation context";

                        list backbone-mac-name {
                            key "name";
                            description "Add a list entry for backbone-mac-name";

                            leaf name {
                                type leafref {
                                    path "../../../../../../pbb/mac/name";
                                }
                                description "Backbone MAC address name";
                            }

                        } // list backbone-mac-name

                        list backbone-mac-address {
                            key "address";
                            description "Add a list entry for backbone-mac-address";

                            leaf address {
                                type types-sros:mac-unicast-address-no-zero;
                                description "Backbone MAC address";
                            }

                        } // list backbone-mac-address

                    } // container fault-propagation

                } // container pbb

                container spb {
                    presence "Enable the spb context";
                    description "Enable the spb context";

                    leaf admin-state {
                        type types-sros:admin-state;
                        default "disable";
                        description "Admin state";
                    }

                    leaf lsp-pacing-interval {
                        type uint32 {
                            range "0..65535";
                        }
                        units "milliseconds";
                        default "100";
                        description "Lsp pacing interval";
                    }

                    leaf retransmit-interval {
                        type uint32 {
                            range "1..65535";
                        }
                        units "seconds";
                        default "5";
                        description "Retransmit interval";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list level {
                        key "id";
                        description "Enter the level list instance";

                        leaf id {
                            type int32 {
                                range "1";
                            }
                            description "Level identifier";
                        }

                        leaf hello-interval {
                            type uint32 {
                                range "1..20000";
                            }
                            units "seconds";
                            default "9";
                            description "Hello interval";
                        }

                        leaf hello-multiplier {
                            type int32 {
                                range "2..100";
                            }
                            default "3";
                            description "Hello multiplier";
                        }

                        leaf metric {
                            type uint32 {
                                range "0..16777215";
                            }
                            default "0";
                            description "Metric";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list level

                } // container spb

                container i-vpls-mac-flush {
                    when "../../pbb-type = 'i-vpls'" {
                        description "VPLS PBB type must be 'i-vpls'";
                    }
                    description "Enter the i-vpls-mac-flush context";

                    container bgp-evpn {
                        description "Enter the bgp-evpn context";

                        leaf send-to-bvpls {
                            type boolean;
                            default "true";
                            description "Send B-VPLS EVPN flush";
                        }

                    } // container bgp-evpn

                } // container i-vpls-mac-flush

                container fdb {
                    description "Enter the fdb context";

                    leaf limit-mac-move {
                        type types-services:limit-mac-move;
                        default "blockable";
                        description "MAC move";
                    }

                    leaf discard-unknown-source {
                        type boolean;
                        default "false";
                        description "Discard packets with unknown destination MAC addresses";
                    }

                    leaf mac-pinning {
                        type boolean;
                        default "false";
                        description "MAC address pinning in active status";
                    }

                    leaf maximum-mac-addresses {
                        type types-services:max-mac-addr;
                        description "Maximum number of MAC address entries in the FDB";
                    }

                    leaf auto-learn-mac-protect {
                        type boolean;
                        default "false";
                        description "Populate automatically MAC protect list with source MAC addresses learned on SDP";
                    }

                    leaf auto-learn-mac-protect-exclude-list {
                        type leafref {
                            path "../../../../mac-list/name";
                        }
                        description "Referenced MAC protect exclusion list name";
                    }

                    leaf protected-src-mac-violation-action {
                        type types-services:sdp-protected-src-mac-violation-action;
                        description "Action when a relearn request for a protected MAC is received on the SDP";
                    }

                    container mac-learning {
                        description "Enter the mac-learning context";

                        leaf learning {
                            type boolean;
                            default "true";
                            description "Enable learning of new MAC addresses";
                        }

                        leaf aging {
                            type boolean;
                            default "true";
                            description "Enable aging of MAC addresses";
                        }

                    } // container mac-learning

                } // container fdb

                container stp {
                    description "Enter the stp context";

                    leaf admin-state {
                        type types-sros:admin-state;
                        description "Administrative state of STP";
                    }

                    leaf auto-edge {
                        type boolean;
                        default "true";
                        description "Enable automatic detection of edge port characteristics";
                    }

                    leaf edge-port {
                        type boolean;
                        default "false";
                        description "Designate SAP or SDP as an edge port";
                    }

                    leaf link-type {
                        type types-services:stp-link-type;
                        default "pt-pt";
                        description "Configure STP link-type";
                    }

                    leaf path-cost {
                        type types-services:stp-path-cost;
                        default "10";
                        description "Configure path-cost";
                    }

                    leaf priority {
                        type int32 {
                            range "0..255";
                        }
                        default "128";
                        description "Configure STP priority";
                    }

                    leaf root-guard {
                        type boolean;
                        default "false";
                        description "Enable/disable STP root-guard";
                    }

                    leaf port-num {
                        type types-services:stp-port-num;
                        description "Virtual port number";
                    }

                } // container stp

                container l2pt {
                    description "Enter the l2pt context";

                    container termination {
                        presence "Enable the termination context";
                        description "Enable the termination context";

                        container protocols {
                            description "Enter the protocols context";

                            leaf stp {
                                type boolean;
                                default "true";
                                description "Enable all spanning tree protocols";
                            }

                            leaf cdp {
                                type boolean;
                                default "false";
                                description "Enable Cisco discovery protocol";
                            }

                            leaf vtp {
                                type boolean;
                                default "false";
                                description "Enable virtual trunk protocol";
                            }

                            leaf dtp {
                                type boolean;
                                default "false";
                                description "Enable dynamic trunking protocol";
                            }

                            leaf pagp {
                                type boolean;
                                default "false";
                                description "Enable port aggregation protocol";
                            }

                            leaf udld {
                                type boolean;
                                default "false";
                                description "Enable unidirectional link detection";
                            }

                        } // container protocols

                    } // container termination

                } // container l2pt

                container dhcp {
                    when "not(../../pbb-type)" {
                        description "VPLS PBB type must be 'none'";
                    }
                    description "Enter the dhcp context";

                    leaf description {
                        type types-sros:description;
                        description "Text description";
                    }

                    leaf snoop {
                        type boolean;
                        default "false";
                        description "Allow DHCP snooping of DHCP messages on the SAP or SDP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container dhcp


                container igmp-snooping {
                    when "not(../../pbb-type = 'b-vpls') and not(../../m-vpls = 'true')" {
                        description "not supported on b-vpls or m-vpls";
                    }
                    description "Enter the igmp-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf maximum-number-sources {
                        type uint32 {
                            range "1..1000";
                        }
                        description "Maximum sources that are allowed per group";
                    }

                    leaf maximum-number-group-sources {
                        type uint32 {
                            range "1..32000";
                        }
                        description "Maximum group source combinations";
                    }

                    leaf version {
                        type types-igmp:igmp-version;
                        default "3";
                        description "IGMP protocol version";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group

                    } // container static

                } // container igmp-snooping

                container mld-snooping {
                    when "not(../../pbb-type = 'b-vpls') and not(../../m-vpls = 'true')" {
                        description "not supported on b-vpls or m-vpls";
                    }
                    description "Enter the mld-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf version {
                        type types-igmp:mld-version;
                        default "2";
                        description "Version of MLD running on the SAP or SDP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container static {
                        description "Enter the static context";

                        list group {
                            key "group-address";
                            description "Enter the group list instance";

                            leaf group-address {
                                type types-sros:ipv6-multicast-address;
                                description "Group address of multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv6-unicast-address;
                                            description "Source IP address";
                                        }

                                    } // list source

                                }
                                case starg {

                                    leaf starg {
                                        type empty;
                                        description "any source address (*,G)";
                                    }

                                }
                            }
                        } // list group

                    } // container static

                } // container mld-snooping

                container pim-snooping {
                    when "not(../../pbb-type = 'b-vpls') and not(../../m-vpls = 'true')" {
                        description "not supported on b-vpls or m-vpls";
                    }
                    description "Enter the pim-snooping context";

                    leaf maximum-number-groups {
                        type uint32 {
                            range "1..16000";
                        }
                        description "Maximum groups for this interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container pim-snooping

                container eth-cfm {
                    description "Enter the eth-cfm context";

                    leaf collect-lmm-stats {
                        type boolean;
                        default "false";
                        description "Collect statistics for loss measurement message tests";
                    }

                    leaf-list squelch-ingress-levels {
                        type uint32 {
                            range "0..7";
                        }
                        max-elements 8;
                        description "Levels for which ETH-CFM packets are silently discarded";
                    }

                    leaf-list squelch-ingress-ctag-levels {
                        type uint32 {
                            range "0..7";
                        }
                        max-elements 8;
                        description "Squelch levels using additional VLAN C-Tag space";
                    }

                    leaf vmep-filter {
                        type boolean;
                        default "false";
                        description "Suppress eth-cfm PDUs based on level lower than or equal to configured Virtual MEP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container collect-lmm-fc-stats {
                        description "Enter the collect-lmm-fc-stats context";

                        leaf-list fc {
                            type types-eth-cfm:fc-type;
                            max-elements 8;
                            description "Forwarding class name for profile-unaware counter";
                        }

                        leaf-list fc-in-profile {
                            type types-eth-cfm:fc-type;
                            max-elements 8;
                            description "Forwarding class name for profile-aware counter";
                        }

                    } // container collect-lmm-fc-stats

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf primary-vlan {
                            type boolean;
                            sros-ext:immutable;
                            default "false";
                            description "MEP provisioned using MA primary VLAN ID";
                        }

                        leaf direction {
                            type types-eth-cfm:mp-direction;
                            sros-ext:immutable;
                            description "Direction the MEP faces";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf cfm-vlan-tag {
                            type types-sros:one-or-two-vlan-tags;
                            description "VLAN tags to apply to CFM PDUs for egress processing";
                        }

                        leaf low-priority-defect {
                            type types-eth-cfm:lowest-alarm-priority;
                            default "mac-rem-err-xcon";
                            description "Lowest priority defect allowed to generate fault alarm";
                        }

                        leaf fault-propagation {
                            type types-eth-cfm:fault-propagation-type;
                            description "Fault propagation for the MEP";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container ais {
                            presence "Enable the ais context";
                            description "Enable the ais context";

                            leaf-list client-meg-level {
                                type uint32 {
                                    range "1..7";
                                }
                                max-elements 7;
                                description "Client MEG level for AIS message generation";
                            }

                            leaf interface-support {
                                type boolean;
                                default "false";
                                description "Enable generation of AIS PDUs based on endpoint state";
                            }

                            leaf interval {
                                type uint32 {
                                    range "1|60";
                                }
                                units "seconds";
                                default "1";
                                description "Transmission interval for AIS messages";
                            }

                            leaf low-priority-defect {
                                type enumeration {
                                    enum all-def                        { value 1; }
                                    enum mac-rem-err-xcon               { value 2; }
                                }
                                default "all-def";
                                description "Lowest priority defect allowed to generate fault alarm";
                            }

                            leaf priority {
                                type types-eth-cfm:frame-priority;
                                default "7";
                                description "Priority of the AIS messages generated by the node";
                            }

                        } // container ais

                        container csf {
                            presence "Enable the csf context";
                            description "Enable the csf context";

                            leaf multiplier {
                                type decimal64 {
                                    range "0.0|2.0..30.0";
                                    fraction-digits 1;
                                }
                                default "3.5";
                                description "Multiplication factor used to clear the CSF condition";
                            }

                        } // container csf

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                    list mip {
                        key "primary-vlan";
                        description "Enter the mip list instance";

                        leaf primary-vlan {
                            type types-eth-cfm:vlan-id-or-none;
                            description "VLAN ID to which the MIP is attached";
                        }

                        leaf mac-address {
                            type types-sros:mac-unicast-address-no-zero;
                            description "MAC address of the MIP";
                        }

                        leaf cfm-vlan-tag {
                            type types-sros:one-or-two-vlan-tags;
                            description "VLAN tags to apply to CFM PDUs for egress processing";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mip

                } // container eth-cfm

                container static-isid {
                    description "Enter the static-isid context";

                    list range {
                        when "../../../pbb-type = 'b-vpls'" {
                            description "supported on b-vpls service";
                        }
                        key "range-id";
                        description "Enter the range list instance";

                        leaf range-id {
                            type uint32 {
                                range "1..8191";
                            }
                            description "Range ID for static ISID";
                        }

                        leaf start {
                            type types-services:isid-no-zero;
                            description "Lower bound of the ISID range";
                        }

                        leaf end {
                            type types-services:isid-no-zero;
                            description "Upper bound of the ISID range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list range

                } // container static-isid

                container mrp {
                    when "../../pbb-type = 'b-vpls' and not(../../m-vpls = 'true')" {
                        description "supported on non managed b-vpls service";
                    }
                    description "Enter the mrp context";

                    leaf join-time {
                        type uint32 {
                            range "1..10";
                        }
                        units "deciseconds";
                        default "2";
                        description "Maximum rate for attribute join messages sent on SDP";
                    }

                    leaf leave-time {
                        type uint32 {
                            range "30..60";
                        }
                        units "deciseconds";
                        default "30";
                        description "Time in LV state before transition to MT state";
                    }

                    leaf leave-all-time {
                        type uint32 {
                            range "60..300";
                        }
                        units "deciseconds";
                        default "100";
                        description "Frequency of LeaveAll PDUs by LeaveAll state machine";
                    }

                    leaf periodic-time {
                        type uint32 {
                            range "10..100";
                        }
                        units "deciseconds";
                        default "10";
                        description "Frequency of periodic events generated by state machine";
                    }

                    leaf periodic-timer {
                        type boolean;
                        default "false";
                        description "Enable the Periodic Transmission Timer";
                    }

                    leaf policy {
                        type leafref {
                            path "../../../../mrp/policy/policy-name";
                        }
                        description "MRP policy to control Group B-MAC attributes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container mrp

            } // list spoke-sdp

            list mesh-sdp {
                key "sdp-bind-id";
                description "Enter the mesh-sdp list instance";

                leaf sdp-bind-id {
                    type types-services:sdp-bind-id;
                    description "SDP binding ID";
                }

                leaf description {
                    type types-sros:description;
                    description "Text description";
                }

                leaf admin-state {
                    type types-sros:admin-state;
                    default "enable";
                    description "Administrative state of the SDP binding to the service";
                }

                leaf vlan-vc-tag {
                    type types-services:vlan-vc-tag;
                    description "SDP bind VC tag";
                }

                leaf collect-stats {
                    type boolean;
                    default "false";
                    description "Allow agent to collect accounting statistics";
                }

                leaf accounting-policy {
                    type leafref {
                        path "../../../../log/accounting-policy/policy-id";
                    }
                    description "Policy to collect accounting statistics";
                }

                leaf control-word {
                    type boolean;
                    default "false";
                    description "Use the control word as preferred";
                }

                leaf force-vc-forwarding {
                    type enumeration {
                        enum vlan                           { value 1; }
                        enum qinq-c-tag-c-tag               { value 2; }
                        enum qinq-s-tag-c-tag               { value 3; }
                    }
                    description "VC forwarding action";
                }

                leaf etree-root-leaf-tag {
                    when "../../etree = 'true'" {
                        description "etree must be set";
                    }
                    type boolean;
                    sros-ext:immutable;
                    default "false";
                    description "Status for E-tree root leaf tag";
                }

                leaf etree-leaf {
                    when "../../etree = 'true'" {
                        description "etree must be set";
                    }
                    type boolean;
                    sros-ext:immutable;
                    default "false";
                    description "Enable etree leaf access-circuit status";
                }

                leaf bfd-template {
                    status obsolete;
                    type leafref {
                        path "../../../../bfd/bfd-template/name";
                    }
                    description "BFD template associated with SDP binding";
                }

                leaf vc-type {
                    type types-services:vpls-sdp-bind-vc-type;
                    sros-ext:auto-restart-to-modify;
                    default "ether";
                    description "Type of virtual circuit (VC) associated with the SDP binding; VPLS not supported";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice label {
                    case entropy {

                        leaf entropy-label {
                            type empty;
                            description "Enable the use of entropy labels for spoke SDPs";
                        }

                    }
                    case hash {

                        container hash-label {
                            presence "Enable the hash-label context";
                            description "Enable the hash-label context";

                            leaf signal-capability {
                                type empty;
                                description "Signal hash label capability to the remote PE";
                            }

                        } // container hash-label

                    }
                }
                container ingress {
                    description "Enter the ingress context";

                    leaf vc-label {
                        type types-services:ingress-vc-label;
                        sros-ext:auto-restart-to-modify;
                        description "Ingress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container fp-redirect-group {
                                description "Enter the fp-redirect-group context";

                                leaf group-name {
                                    type leafref {
                                        path "../../../../../../../../qos/queue-group-templates/ingress/queue-group/ingress-queue-group-name";
                                    }
                                    description "Name of the forwarding plane queue group template";
                                }

                                leaf instance {
                                    type types-services:qos-qgrp-instance-id;
                                    description "Instance of FP ingress queue group for the SDP binding";
                                }

                            } // container fp-redirect-group

                        } // container network

                    } // container qos

                } // container ingress

                container egress {
                    description "Enter the egress context";

                    leaf vc-label {
                        type types-services:egress-vc-label;
                        sros-ext:auto-restart-to-modify;
                        description "Egress MPLS VC label to send packets to the far end";
                    }

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container port-redirect-group {
                                description "Enter the port-redirect-group context";

                                leaf group-name {
                                    type leafref {
                                        path "../../../../../../../../qos/queue-group-templates/egress/queue-group/egress-queue-group-name";
                                    }
                                    description "Name of the egress port queue group";
                                }

                                leaf instance {
                                    type types-services:qos-qgrp-instance-id;
                                    description "Queue-group instance ID";
                                }

                            } // container port-redirect-group

                        } // container network

                    } // container qos

                    container mfib-allowed-mda-destinations {
                        description "Enter the mfib-allowed-mda-destinations context";

                        list mda {
                            key "mda-id";
                            description "Add a list entry for mda";

                            leaf mda-id {
                                type types-isa:slot-mda;
                                description "MFIB allowed MDA destination";
                            }

                        } // list mda

                    } // container mfib-allowed-mda-destinations

                } // container egress

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                        case cfm {

                            container eth-cfm-monitoring {
                                presence "Enable the eth-cfm-monitoring context";
                                description "Enable the eth-cfm-monitoring context";

                                leaf aggregate {
                                    type empty;
                                    description "Apply rate limit to the sum of the per peer packet rates";
                                }

                                leaf car {
                                    type empty;
                                    description "Ignore Ethernet CFM packets when enforcing overall rate";
                                }

                            } // container eth-cfm-monitoring

                        }
                    }
                } // container cpu-protection

                container bfd-liveness {
                    status obsolete;
                    presence "Enable the bfd-liveness context";
                    description "Enable the bfd-liveness context";

                    leaf encap {
                        status obsolete;
                        type types-services:bfd-encap;
                        default "ipv4";
                        description "BFD encapsulation used on the SDP binding";
                    }

                } // container bfd-liveness

                container bfd {
                    description "Enter the bfd context";

                    leaf bfd-template {
                        type leafref {
                            path "../../../../../bfd/bfd-template/name";
                        }
                        description "BFD template associated with the SDP binding";
                    }

                    container bfd-liveness {
                        presence "Enable the bfd-liveness context";
                        description "Enable the bfd-liveness context";

                        leaf encap {
                            type types-services:bfd-encap;
                            default "ipv4";
                            description "BFD encapsulation used on the SDP binding";
                        }

                    } // container bfd-liveness

                } // container bfd

                container pbb {
                    when "../../pbb-type = 'b-vpls'" {
                        description "supported on b-vpls service";
                    }
                    description "Enter the pbb context";

                    container fault-propagation {
                        description "Enter the fault-propagation context";

                        list backbone-mac-name {
                            key "name";
                            description "Add a list entry for backbone-mac-name";

                            leaf name {
                                type leafref {
                                    path "../../../../../../pbb/mac/name";
                                }
                                description "Backbone MAC address name";
                            }

                        } // list backbone-mac-name

                        list backbone-mac-address {
                            key "address";
                            description "Add a list entry for backbone-mac-address";

                            leaf address {
                                type types-sros:mac-unicast-address-no-zero;
                                description "Backbone MAC address";
                            }

                        } // list backbone-mac-address

                    } // container fault-propagation

                } // container pbb

                container fdb {
                    description "Enter the fdb context";

                    leaf mac-pinning {
                        type boolean;
                        default "false";
                        description "MAC address pinning in active status";
                    }

                    leaf auto-learn-mac-protect {
                        type boolean;
                        default "false";
                        description "Enable automatic population of the MAC protect list";
                    }

                    leaf auto-learn-mac-protect-exclude-list {
                        type leafref {
                            path "../../../../mac-list/name";
                        }
                        description "Referenced MAC protect exclusion list name";
                    }

                    leaf protected-src-mac-violation-action {
                        type types-services:sdp-protected-src-mac-violation-action;
                        description "Action to take whenever a relearn request for a protected MAC is received";
                    }

                } // container fdb

                container dhcp {
                    when "not(../../pbb-type)" {
                        description "VPLS PBB type must be 'none'";
                    }
                    description "Enter the dhcp context";

                    leaf description {
                        type types-sros:description;
                        description "Text description";
                    }

                    leaf snoop {
                        type boolean;
                        default "false";
                        description "Allow DHCP snooping of DHCP messages on the SAP or SDP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container dhcp

                container igmp-snooping {
                    when "not(../../pbb-type = 'b-vpls') and not(../../m-vpls = 'true')" {
                        description "not supported on b-vpls or m-vpls";
                    }
                    description "Enter the igmp-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf maximum-number-sources {
                        type uint32 {
                            range "1..1000";
                        }
                        description "Maximum sources that are allowed per group";
                    }

                    leaf maximum-number-group-sources {
                        type uint32 {
                            range "1..32000";
                        }
                        description "Maximum group source combinations";
                    }

                    leaf version {
                        type types-igmp:igmp-version;
                        default "3";
                        description "IGMP protocol version";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group

                    } // container static

                } // container igmp-snooping

                container mld-snooping {
                    when "not(../../pbb-type = 'b-vpls') and not(../../m-vpls = 'true')" {
                        description "not supported on b-vpls or m-vpls";
                    }
                    description "Enter the mld-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf version {
                        type types-igmp:mld-version;
                        default "2";
                        description "Version of MLD running on the SAP or SDP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container static {
                        description "Enter the static context";

                        list group {
                            key "group-address";
                            description "Enter the group list instance";

                            leaf group-address {
                                type types-sros:ipv6-multicast-address;
                                description "Group address of multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv6-unicast-address;
                                            description "Source IP address";
                                        }

                                    } // list source

                                }
                                case starg {

                                    leaf starg {
                                        type empty;
                                        description "any source address (*,G)";
                                    }

                                }
                            }
                        } // list group

                    } // container static

                } // container mld-snooping

                container eth-cfm {
                    description "Enter the eth-cfm context";

                    leaf collect-lmm-stats {
                        type boolean;
                        default "false";
                        description "Collect statistics for loss measurement message tests";
                    }

                    leaf-list squelch-ingress-levels {
                        type uint32 {
                            range "0..7";
                        }
                        max-elements 8;
                        description "Levels for which ETH-CFM packets are silently discarded";
                    }

                    leaf-list squelch-ingress-ctag-levels {
                        type uint32 {
                            range "0..7";
                        }
                        max-elements 8;
                        description "Squelch levels using additional VLAN C-Tag space";
                    }

                    leaf vmep-filter {
                        type boolean;
                        default "false";
                        description "Suppress eth-cfm PDUs based on level lower than or equal to configured Virtual MEP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container collect-lmm-fc-stats {
                        description "Enter the collect-lmm-fc-stats context";

                        leaf-list fc {
                            type types-eth-cfm:fc-type;
                            max-elements 8;
                            description "Forwarding class name for profile-unaware counter";
                        }

                        leaf-list fc-in-profile {
                            type types-eth-cfm:fc-type;
                            max-elements 8;
                            description "Forwarding class name for profile-aware counter";
                        }

                    } // container collect-lmm-fc-stats

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf primary-vlan {
                            type boolean;
                            sros-ext:immutable;
                            default "false";
                            description "MEP provisioned using MA primary VLAN ID";
                        }

                        leaf direction {
                            type types-eth-cfm:mp-direction;
                            sros-ext:immutable;
                            description "Direction the MEP faces";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf cfm-vlan-tag {
                            type types-sros:one-or-two-vlan-tags;
                            description "VLAN tags to apply to CFM PDUs for egress processing";
                        }

                        leaf low-priority-defect {
                            type types-eth-cfm:lowest-alarm-priority;
                            default "mac-rem-err-xcon";
                            description "Lowest priority defect allowed to generate fault alarm";
                        }

                        leaf fault-propagation {
                            type types-eth-cfm:fault-propagation-type;
                            description "Fault propagation for the MEP";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container ais {
                            presence "Enable the ais context";
                            description "Enable the ais context";

                            leaf-list client-meg-level {
                                type uint32 {
                                    range "1..7";
                                }
                                max-elements 7;
                                description "Client MEG level for AIS message generation";
                            }

                            leaf interface-support {
                                type boolean;
                                default "false";
                                description "Enable generation of AIS PDUs based on endpoint state";
                            }

                            leaf interval {
                                type uint32 {
                                    range "1|60";
                                }
                                units "seconds";
                                default "1";
                                description "Transmission interval for AIS messages";
                            }

                            leaf low-priority-defect {
                                type enumeration {
                                    enum all-def                        { value 1; }
                                    enum mac-rem-err-xcon               { value 2; }
                                }
                                default "all-def";
                                description "Lowest priority defect allowed to generate fault alarm";
                            }

                            leaf priority {
                                type types-eth-cfm:frame-priority;
                                default "7";
                                description "Priority of the AIS messages generated by the node";
                            }

                        } // container ais

                        container csf {
                            presence "Enable the csf context";
                            description "Enable the csf context";

                            leaf multiplier {
                                type decimal64 {
                                    range "0.0|2.0..30.0";
                                    fraction-digits 1;
                                }
                                default "3.5";
                                description "Multiplication factor used to clear the CSF condition";
                            }

                        } // container csf

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                    list mip {
                        key "primary-vlan";
                        description "Enter the mip list instance";

                        leaf primary-vlan {
                            type types-eth-cfm:vlan-id-or-none;
                            description "VLAN ID to which the MIP is attached";
                        }

                        leaf mac-address {
                            type types-sros:mac-unicast-address-no-zero;
                            description "MAC address of the MIP";
                        }

                        leaf cfm-vlan-tag {
                            type types-sros:one-or-two-vlan-tags;
                            description "VLAN tags to apply to CFM PDUs for egress processing";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mip

                } // container eth-cfm

                container mrp {
                    when "../../pbb-type = 'b-vpls' and not(../../m-vpls = 'true')" {
                        description "supported on non managed b-vpls service";
                    }
                    description "Enter the mrp context";

                    leaf join-time {
                        type uint32 {
                            range "1..10";
                        }
                        units "deciseconds";
                        default "2";
                        description "Maximum rate for attribute join messages sent on SDP";
                    }

                    leaf leave-time {
                        type uint32 {
                            range "30..60";
                        }
                        units "deciseconds";
                        default "30";
                        description "Time in LV state before transition to MT state";
                    }

                    leaf leave-all-time {
                        type uint32 {
                            range "60..300";
                        }
                        units "deciseconds";
                        default "100";
                        description "Frequency of LeaveAll PDUs by LeaveAll state machine";
                    }

                    leaf periodic-time {
                        type uint32 {
                            range "10..100";
                        }
                        units "deciseconds";
                        default "10";
                        description "Frequency of periodic events generated by state machine";
                    }

                    leaf periodic-timer {
                        type boolean;
                        default "false";
                        description "Enable the Periodic Transmission Timer";
                    }

                    leaf policy {
                        type leafref {
                            path "../../../../mrp/policy/policy-name";
                        }
                        description "MRP policy to control Group B-MAC attributes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container mrp

            } // list mesh-sdp

            list bgp-mh-site {
                key "site-name";
                description "Enter the bgp-mh-site list instance";

                leaf site-name {
                    type types-sros:named-item;
                    description "Name for the specific site";
                }

                leaf admin-state {
                    type types-sros:admin-state;
                    default "disable";
                    description "Administrative state of the VPLS BGP multi-homing site";
                }

                leaf id {
                    type types-services:site-id;
                    sros-ext:auto-restart-to-modify;
                    description "Site ID";
                }

                leaf boot-timer {
                    type types-services:site-boot-timer;
                    units "seconds";
                    description "Wait time after reboot to run the DF election algorithm";
                }

                leaf activation-timer {
                    type types-services:site-activation-timer;
                    units "seconds";
                    description "Time that the local sites are in standby status, waiting for BGP updates";
                }

                leaf monitor-oper-group {
                    type leafref {
                        path "../../../oper-group/name";
                    }
                    description "Operational group to monitor";
                }

                leaf failed-threshold {
                    type types-services:failed-threshold;
                    default "all";
                    description "Threshold for the site to be declared down";
                }

                leaf min-down-timer {
                    type types-services:site-min-down-timer;
                    units "seconds";
                    description "Minimum downtime for BGP multi-homing site after transition from up to down";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice site-object {
                    case spoke-sdp {

                        leaf spoke-sdp {
                            type types-services:sdp-bind-id;
                            sros-ext:auto-restart-to-modify;
                            description "SDP associated with the site";
                        }

                    }
                    case sap {

                        leaf sap {
                            type types-sros:sap;
                            sros-ext:auto-restart-to-modify;
                            description "SAP to be associated with this site";
                        }

                    }
                    case mesh-sdp {

                        leaf mesh-sdp-binds {
                            type empty;
                            description "Specify if a mesh-sdp-binding is associated with this site";
                        }

                    }
                    case shg {

                        leaf shg-name {
                            type types-sros:named-item;
                            sros-ext:auto-restart-to-modify;
                            description "SHG name to be associated with the site";
                        }

                    }
                }
            } // list bgp-mh-site

            list sap {
                key "sap-id";
                description "Enter the sap list instance";

                leaf sap-id {
                    type types-sros:sap;
                    description "SAP identifier";
                }

                leaf description {
                    type types-sros:long-description;
                    description "Text description";
                }

                leaf admin-state {
                    type types-sros:admin-state;
                    default "enable";
                    description "Administrative state of the SAP";
                }

                leaf accounting-policy {
                    type leafref {
                        path "../../../../log/accounting-policy/policy-id";
                    }
                    description "Accounting policy";
                }

                leaf anti-spoof {
                    type types-services:anti-spoof-option;
                    description "Type of anti-spoof filtering";
                }

                leaf app-profile {
                    type leafref {
                        path "../../../../application-assurance/group/partition/policy/app-profile/app-profile-name";
                    }
                    description "Application profile name";
                }

                leaf bandwidth {
                    type types-services:sap-bandwidth;
                    units "kilobps";
                    description "SAP bandwidth";
                }

                leaf calling-station-id {
                    type types-sros:string-not-all-spaces {
                        length "1..64";
                    }
                    description "Calling station ID";
                }

                leaf cflowd {
                    when "not(../../pbb-type = 'b-vpls')" {
                        description "VPLS PBB type must not be 'b-vpls'";
                    }
                    type boolean;
                    default "false";
                    description "Enable Cflowd collection and analysis on this SAP";
                }

                leaf collect-stats {
                    type boolean;
                    default "false";
                    description "Collect accounting statistics";
                }

                leaf dist-cpu-protection {
                    type leafref {
                        path "../../../../system/security/dist-cpu-protection/policy/policy-name";
                    }
                    description "Distributed CPU protection policy for SAP";
                }

                leaf host-admin-state {
                    type types-sros:admin-state;
                    default "enable";
                    description "Administrative state of the hosts";
                }

                leaf host-lockout-policy {
                    type leafref {
                        path "../../../../subscriber-mgmt/host-lockout-policy/name";
                    }
                    description "Host lockout policy";
                }

                leaf multi-service-site {
                    type leafref {
                        path "../../../customer/multi-service-site/multi-service-site-name";
                    }
                    description "Multi service site name";
                }

                leaf split-horizon-group {
                    type leafref {
                        path "../../split-horizon-group/shg-name";
                    }
                    sros-ext:immutable;
                    description "Split horizon group";
                }

                leaf multicast-source {
                    type boolean;
                    sros-ext:immutable;
                    default "false";
                    description "Enable multicast-source on the SAP";
                }

                leaf eth-ring {
                    type uint32 {
                        range "1..128";
                    }
                    sros-ext:immutable;
                    description "Ethernet ring operation";
                }

                leaf etree-leaf {
                    when "../../etree = 'true'" {
                        description "etree must be set";
                    }
                    type boolean;
                    sros-ext:immutable;
                    default "false";
                    description "Enable etree leaf access-circuit status";
                }

                leaf arp-reply-agent {
                    when "not(../../pbb-type)" {
                        description "VPLS PBB type must be 'none'";
                    }
                    type types-services:arp-reply-agent;
                    description "Enable arp-reply-agent function";
                }

                leaf bpdu-translation {
                    type types-services:bpdu-translation;
                    description "Bpdu translation on this SAP";
                }

                leaf process-cpm-traffic-on-sap-down {
                    type boolean;
                    default "false";
                    description "Process CPM traffic on SAP down event";
                }

                leaf bgp-vpls-mh-veid {
                    type int32 {
                        range "1..65535";
                    }
                    description "BGP-VPLS multi-homing VE-ID";
                }

                leaf radius-auth-policy {
                    type leafref {
                        path "../../../../subscriber-mgmt/radius-authentication-policy/name";
                    }
                    description "RADIUS authentication policy";
                }

                leaf shcv-policy-ipv4 {
                    type leafref {
                        path "../../../../subscriber-mgmt/shcv-policy/name";
                    }
                    description "Subscriber host connectivity verification policy for IPv4";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice oper-group-association {
                    case oper-group {

                        leaf oper-group {
                            type leafref {
                                path "../../../oper-group/name";
                            }
                            description "Operational group";
                        }

                    }
                    case monitor-oper-group {

                        leaf monitor-oper-group {
                            type leafref {
                                path "../../../oper-group/name";
                            }
                            description "Monitor operational group";
                        }

                    }
                }
                container ingress {
                    description "Enter the ingress context";

                    leaf shared-policer {
                        type leafref {
                            path "../../../../../qos/shared-policers/policer/shared-policer-name";
                        }
                        description "Ingress shared policer";
                    }

                    container qos {
                        description "Enter the qos context";

                        leaf match-qinq-dot1p {
                            type enumeration {
                                enum top                            { value 2; }
                                enum bottom                         { value 3; }
                            }
                            description "Ingress match QinQ Dot1p";
                        }

                        container sap-ingress {
                            description "Enter the sap-ingress context";

                            leaf policy-name {
                                type leafref {
                                    path "../../../../../../../qos/sap-ingress/sap-ingress-policy-name";
                                }
                                description "Policy ID";
                            }

                            leaf queuing-type {
                                type types-services:services-sap-queuing-type;
                                description "Queuing type";
                            }

                            container fp-redirect-group {
                                description "Enter the fp-redirect-group context";

                                leaf group-name {
                                    type leafref {
                                        path "../../../../../../../../qos/queue-group-templates/ingress/queue-group/ingress-queue-group-name";
                                    }
                                    description "Queue group template name created on forwarding plane";
                                }

                                leaf instance {
                                    type types-services:qos-qgrp-instance-id;
                                    description "Queue group instance";
                                }

                            } // container fp-redirect-group

                            container overrides {
                                description "Enter the overrides context";

                                container ip-criteria {
                                    description "Enter the ip-criteria context";

                                    leaf activate-entry-tag {
                                        type int32 {
                                            range "1..255";
                                        }
                                        description "Tag ID activated for IPv4 criteria";
                                    }

                                } // container ip-criteria

                                container ipv6-criteria {
                                    description "Enter the ipv6-criteria context";

                                    leaf activate-entry-tag {
                                        type int32 {
                                            range "1..255";
                                        }
                                        description "Tag ID activated for IPv6 criteria";
                                    }

                                } // container ipv6-criteria

                                list queue {
                                    key "queue-id";
                                    description "Enter the queue list instance";

                                    leaf queue-id {
                                        type leafref {
                                            path "../../../../../../../../../qos/sap-ingress[sap-ingress-policy-name=current()/../../../policy-name]/queue/queue-id";
                                        }
                                        description "Policer unique ID";
                                    }

                                    leaf cbs {
                                        type union {
                                            type uint32 {
                                                range "0..1048576";
                                            }
                                            type enumeration {
                                                enum auto                           { value -1; }
                                            }
                                        }
                                        units "kilobytes";
                                        description "CBS";
                                    }

                                    leaf mbs {
                                        type union {
                                            type types-qos:bytes {
                                                range "0..1073741824";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                    } // container monitor-queue-depth

                                } // list queue

                                list policer {
                                    key "policer-id";
                                    description "Enter the policer list instance";

                                    leaf policer-id {
                                        type leafref {
                                            path "../../../../../../../../../qos/sap-ingress[sap-ingress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:ingress-per-packet-offset-override;
                                        description "Packet size modification for policing information";
                                    }

                                    leaf stat-mode {
                                        type types-qos:ingress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                            } // container overrides

                        } // container sap-ingress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qtag-manipulation {
                        when "not(../../../pbb-type = 'b-vpls') and not(../../../pbb-type = 'i-vpls') and not(../../../m-vpls = 'true')" {
                            description "invalid VPLS PBB type or m-vpls set";
                        }
                        description "Enter the qtag-manipulation context";

                        choice tags {
                            case push-dot1q-vlan {

                                leaf push-dot1q-vlan {
                                    type types-services:qtag-manipulation-info;
                                    description "VLAN translation information";
                                }

                            }
                            case push-qinq-vlan {

                                leaf s-tag {
                                    type int32 {
                                        range "0..4094";
                                    }
                                    description "Outer ingress VLAN translation for two service delimiting VLAN values";
                                }

                                leaf c-tag {
                                    type types-services:qinq-vlan-translation-ctag;
                                    description "Inner ingress vlan translation for two service delimiting vlan values";
                                }

                            }
                        }
                    } // container qtag-manipulation

                    container vlan-manipulation {
                        description "Enter the vlan-manipulation context";

                        leaf action {
                            type types-services:vlan-manipulation-ingress-action-type;
                            description "Action to manipulate the VLAN tags of the packets";
                        }

                        leaf outer-tag {
                            type types-services:vlan-manipulate-ingress-vlan-type;
                            default "null";
                            description "Outer VLAN tag to apply";
                        }

                        leaf inner-tag {
                            type types-services:vlan-manipulate-ingress-vlan-type;
                            default "null";
                            description "Inner VLAN tag to apply in case of QinQ encapsulation";
                        }

                    } // container vlan-manipulation

                    container aggregate-policer {
                        description "Enter the aggregate-policer context";

                        leaf rate {
                            type types-qos:aggr-policer-rate;
                            units "kilobps";
                            default "max";
                            description "Aggregate policer rate";
                        }

                        leaf burst {
                            type types-qos:aggr-policer-burst;
                            default "default";
                            description "Aggregate policer burst";
                        }

                        leaf cir {
                            type types-qos:aggr-policer-cir;
                            units "kilobps";
                            description "Aggregate policer CIR";
                        }

                        leaf cbs {
                            type types-qos:aggr-policer-cbs;
                            units "kilobytes";
                            description "Aggregate policer CBS";
                        }

                    } // container aggregate-policer

                } // container ingress

                container egress {
                    description "Enter the egress context";

                    leaf dest-mac-rewrite {
                        type types-sros:mac-unicast-address-no-zero;
                        description "Destination MAC overwrite for unicast";
                    }

                    choice agg-rate-or-percent-agg-rate {
                        default "agg-rate";
                        case agg-rate {

                            container agg-rate {
                                description "Enter the agg-rate context";

                                leaf limit-unused-bandwidth {
                                    type boolean;
                                    default "false";
                                    description "Enable aggregate rate overrun protection";
                                }

                                leaf rate {
                                    type types-services:agg-rate-rate;
                                    units "kilobps";
                                    description "Enforced aggregate rate for all queues";
                                }

                                leaf queue-frame-based-accounting {
                                    type boolean;
                                    default "false";
                                    description "Enable frame based accounting on policers and queues";
                                }

                                leaf cir {
                                    type union {
                                        type int32 {
                                            range "0..400000000";
                                        }
                                        type enumeration {
                                            enum max                            { value -1; }
                                        }
                                    }
                                    units "kilobps";
                                    default "0";
                                    description "Administrative CIR";
                                }

                                leaf burst-limit {
                                    type union {
                                        type types-qos:bytes {
                                            range "1..14000000";
                                        }
                                        type enumeration {
                                            enum auto                           { value -1; }
                                        }
                                    }
                                    default "auto";
                                    description "Shaping burst size when an aggregate shaper is used";
                                }

                                leaf adaptation-rule {
                                    type types-qos:adaptation-rule;
                                    default "closest";
                                    description "Adaptation rule to compute the operational PIR value when an aggregate shaper is used";
                                }

                            } // container agg-rate

                        }
                        case percent-agg-rate {

                            container percent-agg-rate {
                                description "Enter the percent-agg-rate context";

                                leaf pir {
                                    type decimal64 {
                                        range "0.01..100.00";
                                        fraction-digits 2;
                                    }
                                    description "PIR percent rate";
                                }

                                leaf cir {
                                    type decimal64 {
                                        range "0.00..100.00";
                                        fraction-digits 2;
                                    }
                                    description "CIR percent rate";
                                }

                            } // container percent-agg-rate

                        }
                    }
                    container qos {
                        description "Enter the qos context";

                        leaf qinq-mark-top-only {
                            type boolean;
                            default "false";
                            description "Mark top Q-tags";
                        }

                        container sap-egress {
                            description "Enter the sap-egress context";

                            leaf policy-name {
                                type leafref {
                                    path "../../../../../../../qos/sap-egress/sap-egress-policy-name";
                                }
                                description "Policy ID to associate with SAP for mirrored service";
                            }

                            container port-redirect-group {
                                description "Enter the port-redirect-group context";

                                leaf group-name {
                                    type leafref {
                                        path "../../../../../../../../qos/queue-group-templates/egress/queue-group/egress-queue-group-name";
                                    }
                                    description "Name of the queue group redirect list policy";
                                }

                                leaf instance {
                                    type types-services:qos-qgrp-instance-id;
                                    description "Instance of port queue group";
                                }

                            } // container port-redirect-group

                            container overrides {
                                description "Enter the overrides context";

                                leaf hs-secondary-shaper {
                                    type types-sros:named-item;
                                    description "HS Secondary Shaper";
                                }

                                list queue {
                                    key "queue-id";
                                    description "Enter the queue list instance";

                                    leaf queue-id {
                                        type leafref {
                                            path "../../../../../../../../../qos/sap-egress[sap-egress-policy-name=current()/../../../policy-name]/queue/queue-id";
                                        }
                                        description "Policer unique ID";
                                    }

                                    leaf avg-frame-overhead {
                                        type decimal64 {
                                            range "0.00..100.00";
                                            fraction-digits 2;
                                        }
                                        description "Average packet-to-frame encapsulation overhead";
                                    }

                                    leaf burst-limit {
                                        type union {
                                            type types-qos:bytes {
                                                range "1..14000000";
                                            }
                                            type enumeration {
                                                enum auto                           { value -1; }
                                            }
                                        }
                                        description "Explicit shaping burst size for the queue";
                                    }

                                    leaf cbs {
                                        type union {
                                            type uint32 {
                                                range "0..1048576";
                                            }
                                            type enumeration {
                                                enum auto                           { value -1; }
                                            }
                                        }
                                        units "kilobytes";
                                        description "CBS";
                                    }

                                    leaf mbs {
                                        type union {
                                            type types-qos:bytes {
                                                range "0..1073741824";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf hs-wrr-weight {
                                        type types-qos:hs-wrr-weight-override;
                                        default "1";
                                        description "WRR weight to parent with the queue into the scheduler";
                                    }

                                    leaf hs-class-weight {
                                        type types-qos:hs-class-weight-override;
                                        description "Class weight override for the queue";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                        leaf violation-threshold {
                                            type decimal64 {
                                                range "0.01..99.99";
                                                fraction-digits 2;
                                            }
                                            description "Threshold for queue depth before violation is raised";
                                        }

                                    } // container monitor-queue-depth

                                    container hs-wred-queue {
                                        description "Enter the hs-wred-queue context";

                                        leaf policy {
                                            type leafref {
                                                path "../../../../../../../../../../qos/slope-policy/slope-policy-name";
                                            }
                                            description "Slope policy applied to the HSQ queue group queue";
                                        }

                                    } // container hs-wred-queue

                                } // list queue

                                list policer {
                                    key "policer-id";
                                    description "Enter the policer list instance";

                                    leaf policer-id {
                                        type leafref {
                                            path "../../../../../../../../../qos/sap-egress[sap-egress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:egress-per-packet-offset-override;
                                        description "Packet size modification for policing information";
                                    }

                                    leaf stat-mode {
                                        type types-qos:egress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                                list hs-wrr-group {
                                    key "group-id";
                                    description "Enter the hs-wrr-group list instance";

                                    leaf group-id {
                                        type leafref {
                                            path "../../../../../../../../../qos/sap-egress[sap-egress-policy-name=current()/../../../policy-name]/hs-wrr-group/group-id";
                                        }
                                        description "HS WRR group identifier";
                                    }

                                    leaf hs-class-weight {
                                        type types-qos:hs-class-weight-override;
                                        description "Class weight override of the WRR group";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice rate-or-percent-rate {
                                        case rate {

                                            leaf rate {
                                                type union {
                                                    type uint32 {
                                                        range "1..2000000000";
                                                    }
                                                    type enumeration {
                                                        enum max                            { value -1; }
                                                    }
                                                }
                                                units "kilobps";
                                                description "Scheduling rate override applied to the HS WRR group";
                                            }

                                        }
                                        case percent-rate {

                                            leaf percent-rate {
                                                type decimal64 {
                                                    range "0.01..100.00";
                                                    fraction-digits 2;
                                                }
                                                description "Percent rate override applied to the HS WRR group";
                                            }

                                        }
                                    }
                                } // list hs-wrr-group

                            } // container overrides

                        } // container sap-egress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                        container vlan-qos-policy {
                            description "Enter the vlan-qos-policy context";

                            leaf policy-name {
                                type leafref {
                                    path "../../../../../../../qos/vlan-qos-policy/vlan-qos-policy-name";
                                }
                                description "Egress vlan-qos-policy name";
                            }

                            leaf port-redirect {
                                type boolean;
                                default "false";
                                description "Enable egress vlan-qos-policy port-redirect";
                            }

                        } // container vlan-qos-policy

                        container egress-remark-policy {
                            description "Enter the egress-remark-policy context";

                            leaf policy-name {
                                type leafref {
                                    path "../../../../../../../qos/egress-remark-policy/egress-remark-policy-name";
                                }
                                description "Egress-remark-policy name";
                            }

                        } // container egress-remark-policy

                    } // container qos

                    container filter {
                        description "Enter the filter context";

                        leaf mac {
                            type leafref {
                                path "../../../../../../filter/mac-filter/filter-name";
                            }
                            description "MAC filter policy name";
                        }

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container vlan-manipulation {
                        description "Enter the vlan-manipulation context";

                        leaf action {
                            type types-services:vlan-manipulation-egress-action-type;
                            description "Action to manipulate the VLAN tags of the packets";
                        }

                        leaf tag {
                            type types-services:vlan-manipulation-egress-vlan-type;
                            default "null";
                            description "VLAN tag to be applied by action";
                        }

                    } // container vlan-manipulation

                    container virtual-port {
                        description "Enter the virtual-port context";

                        leaf vport-name {
                            type leafref {
                                path "../../../../../../port/ethernet/access/egress/virtual-port/vport-name";
                            }
                            description "Virtual port assigned to the SAP";
                        }

                    } // container virtual-port

                } // container egress

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                        case cfm {

                            container eth-cfm-monitoring {
                                presence "Enable the eth-cfm-monitoring context";
                                description "Enable the eth-cfm-monitoring context";

                                leaf aggregate {
                                    type empty;
                                    description "Apply rate limit to the sum of the per peer packet rates";
                                }

                                leaf car {
                                    type empty;
                                    description "Ignore Ethernet CFM packets when enforcing overall rate";
                                }

                            } // container eth-cfm-monitoring

                        }
                    }
                } // container cpu-protection

                container lag {
                    description "Enter the lag context";

                    leaf link-map-profile {
                        type types-services:link-map-profile-id;
                        description "LAG link map profile for a SAP or network interface";
                    }

                    container per-link-hash {
                        description "Enter the per-link-hash context";

                        leaf class {
                            type types-services:sap-lag-per-link-hash-class;
                            default "1";
                            description "Class used on LAG egress using weighted per-link-hash";
                        }

                        leaf weight {
                            type types-services:sap-lag-per-link-hash-weight;
                            default "1";
                            description "Weight used on LAG egress using weighted per-link-hash";
                        }

                    } // container per-link-hash

                } // container lag

                container transit-policy {
                    presence "Enable the transit-policy context";
                    description "Enable the transit-policy context";

                    choice transit-policy {
                        mandatory true;
                        case prefix {

                            leaf prefix {
                                type leafref {
                                    path "../../../../../application-assurance/group/partition/transit-prefix-policy/prefix-policy-id";
                                }
                                sros-ext:immutable;
                                description "IP prefix policy ID";
                            }

                        }
                        case ip {

                            leaf ip {
                                type leafref {
                                    path "../../../../../application-assurance/group/partition/transit-ip-policy/ip-policy-id";
                                }
                                sros-ext:immutable;
                                description "IP transit policy ID";
                            }

                        }
                    }
                } // container transit-policy


                container etree-root-leaf-tag {
                    when "../../etree = 'true'" {
                        description "etree must be set";
                    }
                    presence "Enable the etree-root-leaf-tag context";
                    description "Enable the etree-root-leaf-tag context";

                    leaf leaf {
                        type int32 {
                            range "1..4094";
                        }
                        sros-ext:immutable;
                        mandatory true;
                        description "Leaf tag value";
                    }

                } // container etree-root-leaf-tag

                container igmp-host-tracking {
                    description "Enter the igmp-host-tracking context";

                    leaf expiry-time {
                        type types-sros:time-duration {
                            range "1..65535";
                        }
                        units "seconds";
                        description "Time that the system continues to track inactive hosts";
                    }

                    leaf import-policy {
                        type leafref {
                            path "../../../../../policy-options/policy-statement/name";
                        }
                        description "Import policy that filters IGMP packets";
                    }

                    leaf maximum-number-groups {
                        type uint32 {
                            range "1..16000";
                        }
                        description "Maximum number of multicast groups to be tracked";
                    }

                    leaf maximum-number-group-sources {
                        type uint32 {
                            range "1..32000";
                        }
                        description "Maximum number of multicast groups to track per group";
                    }

                    leaf maximum-number-sources {
                        type uint32 {
                            range "1..1000";
                        }
                        description "Maximum number of multicast sources to be tracked";
                    }

                    leaf router-alert-check {
                        type boolean;
                        default "true";
                        description "Enable IGMP router alert check option";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container igmp-host-tracking

                container igmp-snooping {
                    when "not(../../pbb-type = 'b-vpls') and not(../../m-vpls = 'true')" {
                        description "not supported on b-vpls or m-vpls";
                    }
                    description "Enter the igmp-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf maximum-number-sources {
                        type uint32 {
                            range "1..1000";
                        }
                        description "Maximum sources that are allowed per group";
                    }

                    leaf maximum-number-group-sources {
                        type uint32 {
                            range "1..32000";
                        }
                        description "Maximum group source combinations";
                    }

                    leaf version {
                        type types-igmp:igmp-version;
                        default "3";
                        description "IGMP protocol version";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container mc-constraints {
                            description "Enter the mc-constraints context";

                            leaf use-lag-port-weight {
                                type boolean;
                                default "false";
                                description "Use LAG port weight in calculating MCAC constraints";
                            }

                            list level {
                                key "level-id";
                                description "Enter the level list instance";

                                leaf level-id {
                                    type types-mcast-cac:constraints-level;
                                    description "Bandwidth level ID for an MCAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list number-down

                        } // container mc-constraints

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container mvr {
                        when "not(../../../pbb-type = 'i-vpls')" {
                            description "not supported on i-vpls";
                        }
                        description "Enter the mvr context";

                        leaf from-vpls {
                            type leafref {
                                path "../../../../../vpls/service-name";
                            }
                            description "MVR VPLS from which the multicast channels are taken";
                        }

                        leaf to-sap {
                            type types-sros:sap;
                            description "Multicast channels copied to SAP";
                        }

                    } // container mvr

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group

                    } // container static

                } // container igmp-snooping

                container mld-snooping {
                    when "not(../../pbb-type = 'b-vpls') and not(../../m-vpls = 'true')" {
                        description "not supported on b-vpls or m-vpls";
                    }
                    description "Enter the mld-snooping context";

                    leaf router-alert-check {
                        type boolean;
                        default "true";
                        description "Enable IP router alert check option";
                    }

                    leaf import-policy {
                        type leafref {
                            path "../../../../../policy-options/policy-statement/name";
                        }
                        description "Import policy that filters IGMP packets";
                    }

                    leaf maximum-number-groups {
                        type uint32 {
                            range "1..16000";
                        }
                        description "Maximum groups allowed";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf query-last-member-interval {
                        type uint32 {
                            range "1..50";
                        }
                        units "deciseconds";
                        default "10";
                        description "Time between group-specific query messages";
                    }

                    leaf fast-leave {
                        type boolean;
                        default "false";
                        description "Allow IGMP fast leave processing";
                    }

                    leaf mrouter-port {
                        type boolean;
                        default "false";
                        description "Operate port as a multicast router port";
                    }

                    leaf robust-count {
                        type uint32 {
                            range "2..7";
                        }
                        default "2";
                        description "Number of retries after expected message loss";
                    }

                    leaf send-queries {
                        type boolean;
                        default "false";
                        description "Generate IGMP general queries";
                    }

                    leaf version {
                        type types-igmp:mld-version;
                        default "2";
                        description "Version of MLD running on the SAP or SDP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mvr {
                        when "not(../../../pbb-type = 'i-vpls')" {
                            description "not supported on i-vpls";
                        }
                        description "Enter the mvr context";

                        leaf from-vpls {
                            type leafref {
                                path "../../../../../vpls/service-name";
                            }
                            description "MVR VPLS from which the multicast channels are taken";
                        }

                        leaf to-sap {
                            type types-sros:sap;
                            description "SAP to which the multicast channels are copied";
                        }

                    } // container mvr

                    container static {
                        description "Enter the static context";

                        list group {
                            key "group-address";
                            description "Enter the group list instance";

                            leaf group-address {
                                type types-sros:ipv6-multicast-address;
                                description "Group address of multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv6-unicast-address;
                                            description "Source IP address";
                                        }

                                    } // list source

                                }
                                case starg {

                                    leaf starg {
                                        type empty;
                                        description "any source address (*,G)";
                                    }

                                }
                            }
                        } // list group

                    } // container static

                } // container mld-snooping

                container pim-snooping {
                    when "not(../../pbb-type = 'b-vpls') and not(../../m-vpls = 'true')" {
                        description "not supported on b-vpls or m-vpls";
                    }
                    description "Enter the pim-snooping context";

                    leaf maximum-number-groups {
                        type uint32 {
                            range "1..16000";
                        }
                        description "Maximum groups for this interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container pim-snooping

                container stp {
                    description "Enter the stp context";

                    leaf admin-state {
                        type types-sros:admin-state;
                        description "Administrative state of STP";
                    }

                    leaf auto-edge {
                        type boolean;
                        default "true";
                        description "Enable automatic detection of edge port characteristics";
                    }

                    leaf edge-port {
                        type boolean;
                        default "false";
                        description "Designate SAP or SDP as an edge port";
                    }

                    leaf link-type {
                        type types-services:stp-link-type;
                        default "pt-pt";
                        description "Configure STP link-type";
                    }

                    leaf path-cost {
                        type types-services:stp-path-cost;
                        default "10";
                        description "Configure path-cost";
                    }

                    leaf priority {
                        type int32 {
                            range "0..255";
                        }
                        default "128";
                        description "Configure STP priority";
                    }

                    leaf root-guard {
                        type boolean;
                        default "false";
                        description "Enable/disable STP root-guard";
                    }

                    leaf port-num {
                        type types-services:stp-port-num;
                        description "Configure virtual port number";
                    }

                    list mst-instance {
                        when "../../../m-vpls = 'true'" {
                            description "supported on managed vpls service";
                        }
                        key "mst-inst-number";
                        description "Enter the mst-instance list instance";

                        leaf mst-inst-number {
                            type uint32 {
                                range "1..4094";
                            }
                            description "Multiple Spanning Tree Instance number";
                        }

                        leaf mst-path-cost {
                            type types-services:stp-path-cost;
                            default "10";
                            description "MSTI path cost";
                        }

                        leaf mst-port-priority {
                            type int32 {
                                range "0|16|32|48|64|80|96|112|128|144|160|176|192|208|224|240";
                            }
                            default "128";
                            description "MSTI port priority";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mst-instance

                } // container stp

                container l2pt {
                    description "Enter the l2pt context";

                    container termination {
                        presence "Enable the termination context";
                        description "Enable the termination context";

                        container protocols {
                            description "Enter the protocols context";

                            leaf stp {
                                type boolean;
                                default "true";
                                description "Enable all spanning tree protocols";
                            }

                            leaf cdp {
                                type boolean;
                                default "false";
                                description "Enable Cisco discovery protocol";
                            }

                            leaf vtp {
                                type boolean;
                                default "false";
                                description "Enable virtual trunk protocol";
                            }

                            leaf dtp {
                                type boolean;
                                default "false";
                                description "Enable dynamic trunking protocol";
                            }

                            leaf pagp {
                                type boolean;
                                default "false";
                                description "Enable port aggregation protocol";
                            }

                            leaf udld {
                                type boolean;
                                default "false";
                                description "Enable unidirectional link detection";
                            }

                        } // container protocols

                    } // container termination

                    container force-boundary {
                        when "../../../m-vpls = 'true'" {
                            description "only supported on m-vpls";
                        }
                        presence "Enable the force-boundary context";
                        description "Enable the force-boundary context";

                        container protocols {
                            description "Enter the protocols context";

                            leaf stp {
                                type boolean;
                                default "true";
                                description "Enable all spanning tree protocols";
                            }

                            leaf cdp {
                                type boolean;
                                default "false";
                                description "Enable Cisco discovery protocol";
                            }

                            leaf vtp {
                                type boolean;
                                default "false";
                                description "Enable virtual trunk protocol";
                            }

                            leaf dtp {
                                type boolean;
                                default "false";
                                description "Enable dynamic trunking protocol";
                            }

                            leaf pagp {
                                type boolean;
                                default "false";
                                description "Enable port aggregation protocol";
                            }

                            leaf udld {
                                type boolean;
                                default "false";
                                description "Enable unidirectional link detection";
                            }

                        } // container protocols

                    } // container force-boundary

                } // container l2pt

                container fdb {
                    description "Enter the fdb context";

                    leaf discard-unknown-source {
                        type boolean;
                        default "false";
                        description "Discard packets with unknown destination MAC addresses";
                    }

                    leaf limit-mac-move {
                        type types-services:limit-mac-move;
                        default "blockable";
                        description "MAC move";
                    }

                    leaf mac-pinning {
                        type boolean;
                        default "false";
                        description "Enable MAC address pinning on this SAP";
                    }

                    leaf maximum-mac-addresses {
                        type types-services:max-mac-addr;
                        description "Maximum number of MAC address entries in the FDB";
                    }

                    leaf auto-learn-mac-protect {
                        type boolean;
                        default "false";
                        description "Enable automatic update of MAC protect list";
                    }

                    leaf auto-learn-mac-protect-exclude-list {
                        type leafref {
                            path "../../../../mac-list/name";
                        }
                        description "Referenced MAC protect exclusion list";
                    }

                    leaf protected-src-mac-violation-action {
                        type types-services:sap-protected-src-mac-violation-action;
                        description "Action to take whenever a relearn request for a protected MAC is received";
                    }

                    leaf discard-unprotected-dest-mac {
                        type boolean;
                        default "false";
                        description "Discard packet with unprotected destination MAC address";
                    }

                    container mac-learning {
                        description "Enter the mac-learning context";

                        leaf learning {
                            type boolean;
                            default "true";
                            description "Enable learning of new MAC addresses";
                        }

                        leaf aging {
                            type boolean;
                            default "true";
                            description "Enable aging of MAC addresses";
                        }

                    } // container mac-learning

                } // container fdb

                container mrp {
                    when "../../pbb-type = 'b-vpls' or ../../m-vpls = 'true'" {
                        description "supported on b-vpls service or m-vpls service only";
                    }
                    description "Enter the mrp context";

                    leaf join-time {
                        type uint32 {
                            range "1..10";
                        }
                        default "2";
                        description "Interval between transmit opportunities";
                    }

                    leaf leave-time {
                        type uint32 {
                            range "30..60";
                        }
                        default "30";
                        description "Time in leave state before transitioning to MT state";
                    }

                    leaf leave-all-time {
                        type uint32 {
                            range "60..300";
                        }
                        default "100";
                        description "Frequency that LeaveAll PDUs are generated";
                    }

                    leaf periodic-time {
                        type uint32 {
                            range "10..100";
                        }
                        default "10";
                        description "Frequency of periodic events generation";
                    }

                    leaf periodic-timer {
                        type boolean;
                        default "false";
                        description "Enable the periodic transmission timer";
                    }

                    leaf policy {
                        type leafref {
                            path "../../../../mrp/policy/policy-name";
                        }
                        description "MMRP policy name";
                    }


                } // container mrp

                container l2tpv3-session {
                    presence "Enable the l2tpv3-session context";
                    description "Enable the l2tpv3-session context";

                    leaf admin-state {
                        type types-sros:admin-state;
                        default "disable";
                        description "Administrative state of the session for the service";
                    }

                    leaf vc-id {
                        type types-services:vc-id;
                        sros-ext:auto-restart-to-modify;
                        description "VC ID for the L2TPv3 session";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                    container pseudo-wire {
                        sros-ext:auto-restart-to-modify;
                        description "Enter the pseudo-wire context";

                        choice type {
                            case ethernet {

                                leaf ethernet {
                                    type empty;
                                    sros-ext:auto-restart-to-modify;
                                    description "Enable the Ethernet PW-type for the L2TPv3 session";
                                }

                            }
                            case ethernet-vlan-id {

                                leaf ethernet-vlan-id {
                                    type int32 {
                                        range "0..4095";
                                    }
                                    sros-ext:auto-restart-to-modify;
                                    description "Ethernet-VLAN PW-type ID for the L2TPv3 session";
                                }

                            }
                        }
                    } // container pseudo-wire

                    container router {
                        sros-ext:auto-restart-to-modify;
                        description "Enter the router context";

                        leaf group {
                            type types-sros:named-item;
                            sros-ext:auto-restart-to-modify;
                            description "Tunnel group name";
                        }

                        leaf router-instance {
                            type types-sros:router-instance-base-vprn-loose;
                            sros-ext:auto-restart-to-modify;
                            description "Router name used to identify the router instance";
                        }

                    } // container router

                } // container l2tpv3-session

                container spb {
                    presence "Enable the spb context";
                    description "Enable the spb context";

                    leaf admin-state {
                        type types-sros:admin-state;
                        default "disable";
                        description "Admin state";
                    }

                    leaf lsp-pacing-interval {
                        type uint32 {
                            range "0..65535";
                        }
                        units "milliseconds";
                        default "100";
                        description "Lsp pacing interval";
                    }

                    leaf retransmit-interval {
                        type uint32 {
                            range "1..65535";
                        }
                        units "seconds";
                        default "5";
                        description "Retransmit interval";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list level {
                        key "id";
                        description "Enter the level list instance";

                        leaf id {
                            type int32 {
                                range "1";
                            }
                            description "Level identifier";
                        }

                        leaf hello-interval {
                            type uint32 {
                                range "1..20000";
                            }
                            units "seconds";
                            default "9";
                            description "Hello interval";
                        }

                        leaf hello-multiplier {
                            type int32 {
                                range "2..100";
                            }
                            default "3";
                            description "Hello multiplier";
                        }

                        leaf metric {
                            type uint32 {
                                range "0..16777215";
                            }
                            default "0";
                            description "Metric";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list level

                } // container spb

                container i-vpls-mac-flush {
                    when "../../pbb-type = 'i-vpls'" {
                        description "VPLS PBB type must be 'i-vpls'";
                    }
                    description "Enter the i-vpls-mac-flush context";

                    container bgp-evpn {
                        description "Enter the bgp-evpn context";

                        leaf send-to-bvpls {
                            type boolean;
                            default "true";
                            description "Send B-VPLS EVPN flush";
                        }

                    } // container bgp-evpn

                } // container i-vpls-mac-flush

                container arp-host {
                    description "Enter the arp-host context";

                    leaf admin-state {
                        type types-sros:admin-state;
                        description "Administrative state of ARP hosts";
                    }

                    leaf host-limit {
                        type uint32 {
                            range "1..131071";
                        }
                        description "Maximum number of ARP triggered hosts";
                    }

                    leaf min-auth-interval {
                        type types-sros:time-duration {
                            range "1..6000";
                        }
                        units "minutes";
                        default "15";
                        description "Minimum authentication interval";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container arp-host

                container dhcp {
                    when "not(../../pbb-type)" {
                        description "VPLS PBB type must be 'none'";
                    }
                    description "Enter the dhcp context";

                    leaf admin-state {
                        type types-sros:admin-state;
                        description "Administrative state of DHCP";
                    }

                    leaf description {
                        type types-sros:description;
                        description "Text description";
                    }

                    leaf snoop {
                        type boolean;
                        default "false";
                        description "Enable DHCP snooping on the SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container proxy-server {
                        description "Enter the proxy-server context";

                        leaf admin-state {
                            type types-sros:admin-state;
                            default "disable";
                            description "Administrative state of the DHCP proxy server";
                        }

                        leaf emulated-server {
                            type types-sros:ipv4-unicast-address;
                            description "IP address used as DHCP server address in SAP context";
                        }

                        container lease-time {
                            description "Enter the lease-time context";

                            leaf value {
                                type types-sros:time-duration {
                                    range "300..315446399";
                                }
                                units "seconds";
                                description "DHCP lease time";
                            }

                            leaf radius-override {
                                type boolean;
                                default "false";
                                description "Use lease time information provided by RADIUS server";
                            }

                        } // container lease-time

                    } // container proxy-server

                    container option-82 {
                        description "Enter the option-82 context";

                        leaf action {
                            type enumeration {
                                enum replace                        { value 1; }
                                enum drop                           { value 2; }
                                enum keep                           { value 3; }
                            }
                            default "keep";
                            description "Action to take with received DHCP Option 82";
                        }

                        container circuit-id {
                            description "Enter the circuit-id context";

                            choice circuit-id {
                                default "ascii-tuple";
                                case none {

                                    leaf none {
                                        type empty;
                                        description "Do not include the circuit ID";
                                    }

                                }
                                case ascii-tuple {

                                    leaf ascii-tuple {
                                        type empty;
                                        description "Use the ASCII-encoded tuple for the circuit ID";
                                    }

                                }
                                case vlan-ascii-tuple {

                                    leaf vlan-ascii-tuple {
                                        type empty;
                                        description "Include the VLAN ID and dot1p bits in the ASCII tuple";
                                    }

                                }
                                case hex-string {

                                    leaf hex-string {
                                        type types-sros:hex-string {
                                            length "1..66";
                                        }
                                        description "User-defined hexadeciaml value of the option";
                                    }

                                }
                            }
                        } // container circuit-id

                        container remote-id {
                            description "Enter the remote-id context";

                            choice remote-id {
                                default "none";
                                case none {

                                    leaf none {
                                        type empty;
                                        description "Do not include the remote ID";
                                    }

                                }
                                case mac {

                                    leaf mac {
                                        type empty;
                                        description "Use the MAC address for the remote ID";
                                    }

                                }
                                case ascii-string {

                                    leaf ascii-string {
                                        type types-sros:string-not-all-spaces {
                                            length "1..32";
                                        }
                                        description "User-defined ASCII string for the remote ID";
                                    }

                                }
                                case hex-string {

                                    leaf hex-string {
                                        type types-sros:hex-string {
                                            length "1..66";
                                        }
                                        description "Option as a hexadecimal string";
                                    }

                                }
                            }
                        } // container remote-id

                        container vendor-specific-option {
                            description "Enter the vendor-specific-option context";

                            leaf system-id {
                                type boolean;
                                default "false";
                                description "Send the system ID in the VSO";
                            }

                            leaf client-mac-address {
                                type boolean;
                                default "false";
                                description "Send the MAC address in the VSO";
                            }

                            leaf service-id {
                                type boolean;
                                default "false";
                                description "Send the service ID in the Vendor Specific Option";
                            }

                            leaf sap-id {
                                type boolean;
                                default "false";
                                description "Send SAP ID in the sub-option of the DHCP relay packet";
                            }

                            leaf string {
                                type types-sros:string-not-all-spaces {
                                    length "1..32";
                                }
                                description "User-defined ASCII string for the VSO";
                            }

                        } // container vendor-specific-option

                    } // container option-82

                    container lease-populate {
                        description "Enter the lease-populate context";

                        leaf max-leases {
                            type uint32 {
                                range "0..131071";
                            }
                            description "Maximum number of DHCPv4 leases";
                        }

                    } // container lease-populate

                } // container dhcp

                container dhcp6 {
                    when "not(../../pbb-type)" {
                        description "VPLS PBB type must be 'none'";
                    }
                    description "Enter the dhcp6 context";

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ldra {
                        presence "Enable the ldra context";
                        description "Enable the ldra context";

                        leaf interface-type {
                            type enumeration {
                                enum client-facing                  { value 1; }
                                enum network-facing                 { value 2; }
                            }
                            mandatory true;
                            description "LDRA interface type";
                        }

                        container options {
                            when "../interface-type = 'client-facing'" {
                                description "Interface-type must be 'client-facing'";
                            }
                            description "Enter the options context";

                            container interface-id {
                                presence "Enable the interface-id context";
                                description "Enable the interface-id context";

                                choice interface-id-format {
                                    mandatory true;
                                    case ascii-tuple {

                                        leaf ascii-tuple {
                                            type empty;
                                            description "Use an ASCII-encoded concatenated tuple";
                                        }

                                    }
                                    case vlan-ascii-tuple {

                                        leaf vlan-ascii-tuple {
                                            type empty;
                                            description "Use an enhanced ASCII-encoded concatenated tuple";
                                        }

                                    }
                                }
                            } // container interface-id

                            container remote-id {
                                description "Enter the remote-id context";

                                choice remote-id-format {
                                    case mac {

                                        leaf mac {
                                            type empty;
                                            description "Use the DHCPv6 client source MAC address";
                                        }

                                    }
                                    case string {

                                        leaf string {
                                            type string {
                                                length "1..32";
                                            }
                                            description "User-defined ASCII string";
                                        }

                                    }
                                }
                            } // container remote-id

                        } // container options

                    } // container ldra

                } // container dhcp6

                container static-host {
                    description "Enter the static-host context";

                    list ipv4 {
                        key "ip mac";
                        description "Enter the ipv4 list instance";

                        leaf ip {
                            type types-sros:ipv4-address;
                            description "IP address";
                        }

                        leaf mac {
                            type types-sros:mac-unicast-address;
                            description "MAC address";
                        }

                        leaf admin-state {
                            type types-sros:admin-state;
                            default "disable";
                            description "Administrative state of the static host";
                        }

                        leaf sub-profile {
                            type leafref {
                                path "../../../../../../subscriber-mgmt/sub-profile/name";
                            }
                            description "Sub-profile name";
                        }

                        leaf sla-profile {
                            type leafref {
                                path "../../../../../../subscriber-mgmt/sla-profile/name";
                            }
                            description "SLA profile name";
                        }

                        leaf ancp-string {
                            type types-submgt:ancp-string;
                            description "ANCP string";
                        }

                        leaf int-dest-id {
                            type types-submgt:int-dest-id;
                            description "Intermediate destination ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container app-profile {
                            description "Enter the app-profile context";

                            leaf profile {
                                type leafref {
                                    path "../../../../../../../application-assurance/group/partition/policy/app-profile/app-profile-name";
                                }
                                description "Application profile used by the static host";
                            }

                        } // container app-profile

                        container subscriber-id {
                            description "Enter the subscriber-id context";

                            choice subscriber-id {
                                case string {

                                    leaf string {
                                        type types-submgt:subscriber-id;
                                        description "Subscriber identification";
                                    }

                                }
                                case use-sap-id {

                                    leaf use-sap-id {
                                        type empty;
                                        description "Use the SAP id as subscriber ID";
                                    }

                                }
                            }
                        } // container subscriber-id

                        container shcv {
                            description "Enter the shcv context";

                        } // container shcv

                    } // list ipv4

                } // container static-host

                container sub-sla-mgmt {
                    when "not(../../pbb-type = 'b-vpls') and not(../../pbb-type = 'i-vpls')" {
                        description "invalid VPLS PBB type";
                    }
                    description "Enter the sub-sla-mgmt context";

                    leaf admin-state {
                        type types-sros:admin-state;
                        default "disable";
                        description "Administrative state of SAP subscriber management";
                    }

                    leaf sub-ident-policy {
                        type leafref {
                            path "../../../../../subscriber-mgmt/sub-ident-policy/name";
                        }
                        description "Subscriber identification policy used on this SAP";
                    }

                    leaf subscriber-limit {
                        type types-submgt:sap-subscriber-limit;
                        default "1";
                        description "Maximum number of subscribers on this SAP";
                    }

                    leaf mac-da-hashing {
                        type boolean;
                        default "false";
                        description "Use destination MAC address instead of subscriber ID to select egress LAG link";
                    }

                    container defaults {
                        description "Enter the defaults context";

                        leaf sub-profile {
                            type leafref {
                                path "../../../../../../subscriber-mgmt/sub-profile/name";
                            }
                            description "Default subscriber profile for the SAP";
                        }

                        leaf sla-profile {
                            type leafref {
                                path "../../../../../../subscriber-mgmt/sla-profile/name";
                            }
                            description "Default SLA profile for hosts on this SAP";
                        }

                        leaf app-profile {
                            type leafref {
                                path "../../../../../../application-assurance/group/partition/policy/app-profile/app-profile-name";
                            }
                            description "Default application profile name for this SAP";
                        }

                        container subscriber-id {
                            description "Enter the subscriber-id context";

                            choice subscriber-id {
                                case auto-id {

                                    leaf auto-id {
                                        type empty;
                                        description "Use auto-generated subscriber identification string";
                                    }

                                }
                                case sap-id {

                                    leaf sap-id {
                                        type empty;
                                        description "Use SAP ID as default subscriber identification string";
                                    }

                                }
                                case string {

                                    leaf string {
                                        type types-submgt:subscriber-id;
                                        description "Default subscriber identification string for the SAP";
                                    }

                                }
                            }
                        } // container subscriber-id

                        container int-dest-id {
                            description "Enter the int-dest-id context";

                            choice int-dest-id {
                                case top-q-tag {

                                    leaf top-q-tag {
                                        type empty;
                                        description "Use the top Q-tag of this SAP";
                                    }

                                }
                                case string {

                                    leaf string {
                                        type types-submgt:int-dest-id;
                                        description "Use the configured string";
                                    }

                                }
                            }
                        } // container int-dest-id

                    } // container defaults

                    container single-sub-parameters {
                        description "Enter the single-sub-parameters context";

                        leaf profiled-traffic-only {
                            type boolean;
                            default "false";
                            description "Include all traffic in subscriber profile";
                        }

                        container non-sub-traffic {
                            presence "Enable the non-sub-traffic context";
                            description "Enable the non-sub-traffic context";

                            leaf sub-profile {
                                type leafref {
                                    path "../../../../../../../subscriber-mgmt/sub-profile/name";
                                }
                                mandatory true;
                                description "Subscriber profile all non-subscriber traffic";
                            }

                            leaf sla-profile {
                                type leafref {
                                    path "../../../../../../../subscriber-mgmt/sla-profile/name";
                                }
                                mandatory true;
                                description "SLA profile applicable for all non-subscriber traffic";
                            }

                            leaf subscriber-id {
                                type types-submgt:subscriber-id;
                                sros-ext:immutable;
                                description "Subscriber ID applied for all non-subscriber traffic";
                            }

                            leaf app-profile {
                                type leafref {
                                    path "../../../../../../../application-assurance/group/partition/policy/app-profile/app-profile-name";
                                }
                                description "Application profile name for all non-subscriber traffic";
                            }

                        } // container non-sub-traffic

                    } // container single-sub-parameters

                } // container sub-sla-mgmt

                container eth-cfm {
                    description "Enter the eth-cfm context";

                    leaf collect-lmm-stats {
                        type boolean;
                        default "false";
                        description "Collect statistics for loss measurement message tests";
                    }

                    leaf-list squelch-ingress-levels {
                        type uint32 {
                            range "0..7";
                        }
                        max-elements 8;
                        description "Levels for which ETH-CFM packets are silently discarded";
                    }

                    leaf-list squelch-ingress-ctag-levels {
                        type uint32 {
                            range "0..7";
                        }
                        max-elements 8;
                        description "Squelch levels using additional VLAN C-Tag space";
                    }

                    leaf vmep-filter {
                        type boolean;
                        default "false";
                        description "Suppress eth-cfm PDUs based on level lower than or equal to configured Virtual MEP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container collect-lmm-fc-stats {
                        description "Enter the collect-lmm-fc-stats context";

                        leaf-list fc {
                            type types-eth-cfm:fc-type;
                            max-elements 8;
                            description "Forwarding class name for profile-unaware counter";
                        }

                        leaf-list fc-in-profile {
                            type types-eth-cfm:fc-type;
                            max-elements 8;
                            description "Forwarding class name for profile-aware counter";
                        }

                    } // container collect-lmm-fc-stats

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf primary-vlan {
                            type boolean;
                            sros-ext:immutable;
                            default "false";
                            description "MEP provisioned using MA primary VLAN ID";
                        }

                        leaf cp-vlan-tag {
                            type types-sros:vlan-id;
                            description "ETH-CFM VLAN tag for egress processing on a CP SAP";
                        }

                        leaf direction {
                            type types-eth-cfm:mp-direction;
                            sros-ext:immutable;
                            description "Direction the MEP faces";
                        }

                        leaf admin-state {
                            type types-sros:admin-state;
                            default "disable";
                            description "Administrative state of the MEP";
                        }

                        leaf description {
                            type types-sros:description;
                            description "Text description";
                        }

                        leaf mac-address {
                            type types-sros:mac-unicast-address-no-zero;
                            description "MAC address of the MEP";
                        }

                        leaf install-mep {
                            type boolean;
                            default "false";
                            description "Install MEP in the forwarding plane";
                        }

                        leaf cfm-vlan-tag {
                            type types-sros:one-or-two-vlan-tags;
                            description "VLAN tags to apply to CFM PDUs for egress processing";
                        }

                        leaf low-priority-defect {
                            type types-eth-cfm:lowest-alarm-priority;
                            default "mac-rem-err-xcon";
                            description "Lowest priority defect allowed to generate fault alarm";
                        }

                        leaf fault-propagation {
                            type types-eth-cfm:fault-propagation-type;
                            description "Fault propagation for the MEP";
                        }

                        leaf ccm {
                            type boolean;
                            default "false";
                            description "Generate CCM messages";
                        }

                        leaf ccm-ltm-priority {
                            type types-eth-cfm:frame-priority;
                            default "7";
                            description "Priority of CCM and LTM messages transmitted by the MEP";
                        }

                        leaf ccm-padding-size {
                            type uint32 {
                                range "3..1500";
                            }
                            description "Number of octets of padding to insert in CCM packets";
                        }

                        leaf lbm-svc-act-responder {
                            type boolean;
                            description "Process service activation streams in ETH-CFM LBM";
                        }

                        leaf one-way-delay-threshold {
                            type uint32 {
                                range "0..600";
                            }
                            units "seconds";
                            default "3";
                            description "Threshold time limit for the one-way delay test";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container alarm-notification {
                            description "Enter the alarm-notification context";

                            leaf fng-alarm-time {
                                type int32 {
                                    range "250|500|1000";
                                }
                                units "centiseconds";
                                description "Time that must expire before an FNG alarm is raised";
                            }

                            leaf fng-reset-time {
                                type int32 {
                                    range "250|500|1000";
                                }
                                units "centiseconds";
                                description "Time that must expire before an FNG alarm is reset";
                            }

                        } // container alarm-notification

                        container ais {
                            presence "Enable the ais context";
                            description "Enable the ais context";

                            leaf-list client-meg-level {
                                type uint32 {
                                    range "1..7";
                                }
                                max-elements 7;
                                description "Client MEG level for AIS message generation";
                            }

                            leaf interface-support {
                                type boolean;
                                default "false";
                                description "Enable generation of AIS PDUs based on endpoint state";
                            }

                            leaf interval {
                                type uint32 {
                                    range "1|60";
                                }
                                units "seconds";
                                default "1";
                                description "Transmission interval for AIS messages";
                            }

                            leaf low-priority-defect {
                                type enumeration {
                                    enum all-def                        { value 1; }
                                    enum mac-rem-err-xcon               { value 2; }
                                }
                                default "all-def";
                                description "Lowest priority defect allowed to generate fault alarm";
                            }

                            leaf priority {
                                type types-eth-cfm:frame-priority;
                                default "7";
                                description "Priority of the AIS messages generated by the node";
                            }

                        } // container ais

                        container csf {
                            presence "Enable the csf context";
                            description "Enable the csf context";

                            leaf multiplier {
                                type decimal64 {
                                    range "0.0|2.0..30.0";
                                    fraction-digits 1;
                                }
                                default "3.5";
                                description "Multiplication factor used to clear the CSF condition";
                            }

                        } // container csf

                        container eth-test {
                            presence "Enable the eth-test context";
                            description "Enable the eth-test context";

                            leaf bit-error-threshold {
                                type uint32 {
                                    range "0..11840";
                                }
                                units "bit errors";
                                default "1";
                                description "Lowest priority defect allowed to generate fault alarm";
                            }

                            container test-pattern {
                                description "Enter the test-pattern context";

                                leaf pattern {
                                    type enumeration {
                                        enum all-zeros                      { value 0; }
                                        enum all-ones                       { value 1; }
                                    }
                                    default "all-zeros";
                                    description "Test pattern for Ethernet Test frames";
                                }

                                leaf crc-tlv {
                                    type boolean;
                                    default "false";
                                    description "Generate a CRC checksum";
                                }

                            } // container test-pattern

                        } // container eth-test

                        container grace {
                            description "Enter the grace context";

                            container eth-ed {
                                description "Enter the eth-ed context";

                                leaf max-rx-defect-window {
                                    type uint32 {
                                        range "1..86400";
                                    }
                                    units "seconds";
                                    description "Maximum received ETH-ED expected defect window duration";
                                }

                                leaf priority {
                                    type int32 {
                                        range "0..7";
                                    }
                                    description "Transmission priority for ETH-ED PDUs";
                                }

                                leaf rx-eth-ed {
                                    type boolean;
                                    default "true";
                                    description "Receive and process ETH-ED ITU-T Y.1731 PDUs on the MEP";
                                }

                                leaf tx-eth-ed {
                                    type boolean;
                                    default "false";
                                    description "Transmit ETH-ED PDUs from the MEP";
                                }

                            } // container eth-ed

                            container eth-vsm-grace {
                                description "Enter the eth-vsm-grace context";

                                leaf rx-eth-vsm-grace {
                                    type boolean;
                                    default "true";
                                    description "Receive and process Nokia ETH-CFM Grace PDU on the MEP";
                                }

                                leaf tx-eth-vsm-grace {
                                    type boolean;
                                    default "true";
                                    description "Transmit ETH-ED PDUs from the MEP";
                                }

                            } // container eth-vsm-grace

                        } // container grace

                    } // list mep

                    list mip {
                        key "primary-vlan";
                        description "Enter the mip list instance";

                        leaf primary-vlan {
                            type types-eth-cfm:vlan-id-or-none;
                            description "VLAN ID to which the MIP is attached";
                        }

                        leaf mac-address {
                            type types-sros:mac-unicast-address-no-zero;
                            description "MAC address of the MIP";
                        }

                        leaf cfm-vlan-tag {
                            type types-sros:one-or-two-vlan-tags;
                            description "VLAN tags to apply to CFM PDUs for egress processing";
                        }

                        leaf cp-vlan-tag {
                            type types-sros:vlan-id;
                            description "ETH-CFM VLAN tag for egress processing on a CP SAP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list mip

                } // container eth-cfm

                container mc-ring {
                    presence "Enable the mc-ring context";
                    description "Enable the mc-ring context";

                    leaf ring-node {
                        type types-sros:named-item;
                        mandatory true;
                        description "Name for the ring node associated with this SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container mc-ring

                container static-isid {
                    description "Enter the static-isid context";

                    list range {
                        when "../../../pbb-type = 'b-vpls'" {
                            description "supported on b-vpls service";
                        }
                        key "range-id";
                        description "Enter the range list instance";

                        leaf range-id {
                            type uint32 {
                                range "1..8191";
                            }
                            description "Range ID for static ISID";
                        }

                        leaf start {
                            type types-services:isid-no-zero;
                            description "Lower bound of the ISID range";
                        }

                        leaf end {
                            type types-services:isid-no-zero;
                            description "Upper bound of the ISID range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list range

                } // container static-isid

                container managed-vlan-list {
                    when "../../m-vpls = 'true'" {
                        description "supported on managed vpls service";
                    }
                    description "Enter the managed-vlan-list context";

                    list range {
                        key "vlan-range";
                        description "Add a list entry for range";

                        leaf vlan-range {
                            type string {
                                pattern "((([0-9]|[1-9][0-9]{1,2}|[1-3][0-9]{3}|40[0-8][0-9]|409[0-4]))(\\.\\.(([0-9]|[1-9][0-9]{1,2}|[1-3][0-9]{3}|40[0-8][0-9]|409[0-4])))?)|(default-sap)";
                            }
                            description "Range of VLANs associated with the M-VPLS SAP";
                        }

                    } // list range

                } // container managed-vlan-list

                container pbb {
                    when "../../pbb-type = 'b-vpls'" {
                        description "supported on b-vpls service";
                    }
                    description "Enter the pbb context";

                    container fault-propagation {
                        description "Enter the fault-propagation context";

                        list backbone-mac-name {
                            key "name";
                            description "Add a list entry for backbone-mac-name";

                            leaf name {
                                type leafref {
                                    path "../../../../../../pbb/mac/name";
                                }
                                description "Backbone MAC address name";
                            }

                        } // list backbone-mac-name

                        list backbone-mac-address {
                            key "address";
                            description "Add a list entry for backbone-mac-address";

                            leaf address {
                                type types-sros:mac-unicast-address-no-zero;
                                description "Backbone MAC address";
                            }

                        } // list backbone-mac-address

                    } // container fault-propagation

                } // container pbb

            } // list sap

            list capture-sap {
                when "not(../pbb-type) and ../etree = 'false' and not(../m-vpls = 'true')" {
                    description "not supported with etree, on m-vpls and when pbb-type is not 'none'";
                }
                key "sap-id";
                description "Enter the capture-sap list instance";

                leaf sap-id {
                    type types-sros:sap;
                    description "SAP identifier";
                }

                leaf description {
                    type types-sros:long-description;
                    description "Text description";
                }

                leaf admin-state {
                    type types-sros:admin-state;
                    default "enable";
                    description "Administrative state of the SAP";
                }

                leaf bandwidth {
                    type types-services:sap-bandwidth;
                    units "kilobps";
                    description "SAP bandwidth";
                }

                leaf dist-cpu-protection {
                    type leafref {
                        path "../../../../system/security/dist-cpu-protection/policy/policy-name";
                    }
                    description "Distributed CPU protection policy for SAP";
                }

                leaf host-lockout-policy {
                    type leafref {
                        path "../../../../subscriber-mgmt/host-lockout-policy/name";
                    }
                    description "Host lockout policy";
                }

                leaf radius-auth-policy {
                    type leafref {
                        path "../../../../subscriber-mgmt/radius-authentication-policy/name";
                    }
                    description "RADIUS authentication policy";
                }

                leaf nasreq-auth-policy {
                    type leafref {
                        path "../../../../subscriber-mgmt/diameter-nasreq-policy/name";
                    }
                    description "Diameter NASREQ application policy to use for authentication";
                }

                leaf allow-dot1q-msaps {
                    type boolean;
                    default "false";
                    description "Enable support for triggering managed SAP creation";
                }

                leaf track-srrp {
                    type uint32 {
                        range "1..4294967295";
                    }
                    description "SRRP instance that this capture SAP tracks";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ingress {
                    description "Enter the ingress context";

                    container filter {
                        description "Enter the filter context";

                        leaf mac {
                            type leafref {
                                path "../../../../../../filter/mac-filter/filter-name";
                            }
                            description "MAC filter policy name";
                        }

                    } // container filter

                } // container ingress

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                    }
                } // container cpu-protection

                container pfcp {
                    description "Enter the pfcp context";

                    leaf association {
                        type leafref {
                            path "../../../../../subscriber-mgmt/pfcp/association/name";
                        }
                        description "Association used for PFCP messages on the capture SAP";
                    }

                    leaf l2-access-id-alias {
                        type string {
                            length "1..32";
                        }
                        description "String used as Layer 2 access ID for the capture SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container up-resiliency {
                        description "Enter the up-resiliency context";

                        list monitor-oper-group {
                            key "oper-group";
                            max-elements 2;
                            description "Enter the monitor-oper-group list instance";

                            leaf oper-group {
                                type leafref {
                                    path "../../../../../../oper-group/name";
                                }
                                description "Operational group name";
                            }

                            leaf health-drop {
                                type uint32 {
                                    range "1..100";
                                }
                                default "1";
                                description "Number subtracted from the health value per failure";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list monitor-oper-group

                    } // container up-resiliency

                } // container pfcp

                container trigger-packet {
                    description "Enter the trigger-packet context";

                    leaf arp {
                        type boolean;
                        default "false";
                        description "ARP packet";
                    }

                    leaf data {
                        type boolean;
                        default "false";
                        description "Data packet";
                    }

                    leaf dhcp {
                        type boolean;
                        default "false";
                        description "DHCP packet";
                    }

                    leaf dhcp6 {
                        type boolean;
                        default "false";
                        description "DHCP6 packet";
                    }

                    leaf pppoe {
                        type boolean;
                        default "false";
                        description "PPPoE packet";
                    }

                    leaf rtr-solicit {
                        type boolean;
                        default "false";
                        description "Router-solicit packet";
                    }

                } // container trigger-packet

                container msap-defaults {
                    description "Enter the msap-defaults context";

                    leaf policy {
                        type leafref {
                            path "../../../../../subscriber-mgmt/msap-policy/name";
                        }
                        description "MSAP policy";
                    }

                    leaf service-name {
                        type types-services:service-name;
                        description "Administrative service name";
                    }

                    leaf group-interface {
                        type types-sros:interface-name;
                        description "Group interface";
                    }

                } // container msap-defaults

                container ipoe-session {
                    description "Enter the ipoe-session context";

                    leaf admin-state {
                        type types-sros:admin-state;
                        description "Administrative state of IPoE session management";
                    }

                    leaf description {
                        type types-sros:description;
                        description "Text description";
                    }

                    leaf ipoe-session-policy {
                        type leafref {
                            path "../../../../../subscriber-mgmt/ipoe-session-policy/name";
                        }
                        sros-ext:auto-restart-to-modify;
                        description "IPoE Session policy to be used for new sessions";
                    }

                    leaf user-db {
                        type leafref {
                            path "../../../../../subscriber-mgmt/local-user-db/name";
                        }
                        sros-ext:auto-restart-to-modify;
                        description "Local user database for IPoE session authentication";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ipoe-session

                container dhcp {
                    description "Enter the dhcp context";

                    leaf python-policy {
                        type leafref {
                            path "../../../../../python/python-policy/name";
                        }
                        description "Python policy";
                    }

                    leaf user-db {
                        type leafref {
                            path "../../../../../subscriber-mgmt/local-user-db/name";
                        }
                        description "Local user database";
                    }

                } // container dhcp

                container dhcp6 {
                    description "Enter the dhcp6 context";

                    leaf python-policy {
                        type leafref {
                            path "../../../../../python/python-policy/name";
                        }
                        description "Python policy";
                    }

                    leaf user-db {
                        type leafref {
                            path "../../../../../subscriber-mgmt/local-user-db/name";
                        }
                        description "Local user database";
                    }

                } // container dhcp6

                container pppoe {
                    description "Enter the pppoe context";

                    leaf policy {
                        type leafref {
                            path "../../../../../subscriber-mgmt/ppp-policy/name";
                        }
                        description "PPP policy";
                    }

                    leaf python-policy {
                        type leafref {
                            path "../../../../../python/python-policy/name";
                        }
                        description "Python policy";
                    }

                    leaf user-db {
                        type leafref {
                            path "../../../../../subscriber-mgmt/local-user-db/name";
                        }
                        description "Local user database";
                    }

                } // container pppoe

                container router-solicit {
                    description "Enter the router-solicit context";

                    leaf user-db {
                        type leafref {
                            path "../../../../../subscriber-mgmt/local-user-db/name";
                        }
                        description "Local user database";
                    }

                } // container router-solicit

            } // list capture-sap

            list interface {
                when "not(../pbb-type = 'b-vpls') and not(../pbb-type = 'i-vpls') and not(../routed-vpls)" {
                    description "invalid VPLS PBB type or routed VPLS";
                }
                key "interface-name";
                description "Enter the interface list instance";

                leaf interface-name {
                    type types-sros:interface-name;
                    description "IP interface name";
                }

                leaf description {
                    type types-sros:very-long-description;
                    description "Text description";
                }

                leaf admin-state {
                    type types-sros:admin-state;
                    default "enable";
                    description "Administrative state of the interface";
                }

                leaf mac {
                    type types-sros:mac-unicast-address;
                    description "MAC address for the interface";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                container ipv4 {
                    description "Enter the ipv4 context";

                    container primary {
                        presence "Enable the primary context";
                        description "Enable the primary context";

                        leaf address {
                            type types-sros:ipv4-address;
                            mandatory true;
                            description "IP address of the interface";
                        }

                        leaf prefix-length {
                            type uint32 {
                                range "0..31";
                            }
                            mandatory true;
                            description "IPv4 address prefix length";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                    container neighbor-discovery {
                        description "Enter the neighbor-discovery context";

                        leaf timeout {
                            type uint32 {
                                range "0..65535";
                            }
                            units "seconds";
                            default "14400";
                            description "ARP timeout value to determine how long an ARP entry remains in the ARP cache";
                        }

                        list static-neighbor {
                            key "ipv4-address";
                            description "Enter the static-neighbor list instance";

                            leaf ipv4-address {
                                type types-sros:ipv4-address;
                                description "IPv4 address that corresponds to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                } // container ipv4

            } // list interface

            container igmp-host-tracking {
                when "not(../pbb-type) and not(../routed-vpls) and not(../m-vpls = 'true')" {
                    description "not supported on m-vpls, when pbb-type is not 'none' and when routed-vpls";
                }
                description "Enter the igmp-host-tracking context";

                leaf admin-state {
                    type types-sros:admin-state;
                    default "disable";
                    description "Administrative state of IGMP host tracking";
                }

                leaf expiry-time {
                    type types-sros:time-duration {
                        range "1..65535";
                    }
                    units "seconds";
                    default "260";
                    description "Time that the system continues to track inactive hosts";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container igmp-host-tracking

            container wlan-gw {
                description "Enter the wlan-gw context";

                leaf admin-state {
                    type types-sros:admin-state;
                    default "disable";
                    description "Administrative state of WLAN-GW";
                }

                leaf description {
                    type types-sros:description;
                    description "Text description";
                }

                leaf wlan-gw-group {
                    type leafref {
                        path "../../../../isa/wlan-gw-group/id";
                    }
                    sros-ext:auto-restart-to-modify;
                    description "WLAN-GW endpoint within the VPLS service";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container wlan-gw

            container gsmp {
                when "not(../pbb-type) and ../etree = 'false'" {
                    description "VPLS PBB type must be 'none' and etree mode must be 'false'";
                }
                description "Enter the gsmp context";

                leaf admin-state {
                    type types-sros:admin-state;
                    default "disable";
                    description "Administrative state of GSMP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list group {
                    key "name";
                    max-elements 1024;
                    description "Enter the group list instance";

                    leaf name {
                        type types-sros:named-item;
                        description "GSMP group name";
                    }

                    leaf admin-state {
                        type types-sros:admin-state;
                        default "disable";
                        description "Administrative state of the GSMP group";
                    }

                    leaf description {
                        type types-sros:description;
                        description "Text description";
                    }

                    leaf keepalive {
                        type types-sros:time-duration {
                            range "1..25";
                        }
                        units "seconds";
                        default "10";
                        description "Keepalive value for the GSMP connections in this group";
                    }

                    leaf hold-multiplier {
                        type uint32 {
                            range "1..100";
                        }
                        default "3";
                        description "Hold-multiplier for the GSMP connections in this group";
                    }

                    leaf persistency {
                        type boolean;
                        default "false";
                        description "Store DSL line information when the GSMP connection terminates";
                    }

                    leaf idle-filter {
                        type boolean;
                        default "false";
                        description "Filter ANCP messages from IDLE DSL lines";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ancp {
                        description "Enter the ancp context";

                        leaf dynamic-topology-discovery {
                            type boolean;
                            default "true";
                            description "Enable the ANCP dynamic topology discovery capability";
                        }

                        leaf oam {
                            type boolean;
                            default "false";
                            description "Enable GSMP ANCP OAM capability at startup of GSMP connection";
                        }

                    } // container ancp

                    list neighbor {
                        key "remote-address";
                        description "Enter the neighbor list instance";

                        leaf remote-address {
                            type types-sros:ipv4-unicast-address;
                            description "GSMP neighbor remote IP address";
                        }

                        leaf admin-state {
                            type types-sros:admin-state;
                            default "disable";
                            description "Administrative state of the GSMP neighbor";
                        }

                        leaf description {
                            type types-sros:description;
                            description "Text description";
                        }

                        leaf local-address {
                            type types-sros:ipv4-unicast-address;
                            sros-ext:auto-restart-to-modify;
                            description "Restrict connections to this local address only within the service running ANCP";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container priority-marking {
                            sros-ext:auto-restart-to-modify;
                            description "Enter the priority-marking context";

                            choice priority-marking {
                                case dscp {

                                    leaf dscp {
                                        type types-qos:dscp-name;
                                        sros-ext:auto-restart-to-modify;
                                        description "DSCP that is used while remarking the in profile packets";
                                    }

                                }
                                case prec {

                                    leaf prec {
                                        type types-qos:precedence-value;
                                        sros-ext:auto-restart-to-modify;
                                        description "Precedence priority marking";
                                    }

                                }
                            }
                        } // container priority-marking

                    } // list neighbor

                } // list group

            } // container gsmp

            container provider-tunnel {
                presence "Enable the provider-tunnel context";
                description "Enable the provider-tunnel context";

                leaf-list apply-groups {
                    type leafref {
                        path "../../../../groups/group/name";
                    }
                    max-elements 8;
                    ordered-by user;
                    sros-ext:auto-restart-to-modify;
                    description "Apply a configuration group at this level";
                }

                leaf-list apply-groups-exclude {
                    type leafref {
                        path "../../../../groups/group/name";
                    }
                    max-elements 8;
                    ordered-by user;
                    sros-ext:auto-restart-to-modify;
                    description "Exclude a configuration group at this level";
                }

                container inclusive {
                    sros-ext:auto-restart-to-modify;
                    description "Enter the inclusive context";

                    leaf data-delay-interval {
                        type int32 {
                            range "3..180";
                        }
                        units "seconds";
                        sros-ext:auto-restart-to-modify;
                        default "15";
                        description "I-PMSI data delay timer";
                    }

                    leaf owner {
                        type enumeration {
                            enum bgp-ad                         { value 1; }
                            enum bgp-vpls                       { value 2; }
                            enum bgp-evpn-mpls                  { value 3; }
                        }
                        sros-ext:auto-restart-to-modify;
                        description "Configure provider-tunnel owner";
                    }

                    leaf root-and-leaf {
                        type boolean;
                        sros-ext:auto-restart-to-modify;
                        default "false";
                        description "Configure whether the provider tunnel acts as a leaf or both a root and leaf";
                    }

                    leaf admin-state {
                        type types-sros:admin-state;
                        sros-ext:auto-restart-to-modify;
                        default "disable";
                        description "Administrative state of P2MP LSP as the I-PMSI";
                    }

                    choice ipmsi {
                        case mldp {

                            leaf mldp {
                                type empty;
                                sros-ext:auto-restart-to-modify;
                                description "Enable/Disable MLDP";
                            }

                        }
                        case rsvp {

                            container rsvp {
                                presence "Enable the rsvp context";
                                sros-ext:auto-restart-to-modify;
                                description "Enable the rsvp context";

                                leaf lsp-template {
                                    type leafref {
                                        path "../../../../../../router/mpls/lsp-template/template-name";
                                    }
                                    sros-ext:auto-restart-to-modify;
                                    description "Configure LSP template name";
                                }

                            } // container rsvp

                        }
                    }
                } // container inclusive

                container selective {
                    sros-ext:auto-restart-to-modify;
                    description "Enter the selective context";

                    leaf data-delay-interval {
                        type int32 {
                            range "3..180";
                        }
                        units "seconds";
                        sros-ext:auto-restart-to-modify;
                        default "3";
                        description "S-PMSI data delay timer";
                    }

                    leaf owner {
                        type enumeration {
                            enum bgp-evpn-mpls                  { value 1; }
                        }
                        sros-ext:auto-restart-to-modify;
                        description "Provider-tunnel selective owner";
                    }

                    leaf admin-state {
                        type types-sros:admin-state;
                        sros-ext:auto-restart-to-modify;
                        default "disable";
                        description "Administrative state of the selective provider tunnel";
                    }

                    leaf wildcard-spmsi {
                        type boolean;
                        sros-ext:auto-restart-to-modify;
                        default "false";
                        description "Enable wildcard S-PMSI support";
                    }

                    leaf mldp {
                        type boolean;
                        sros-ext:auto-restart-to-modify;
                        default "false";
                        description "Enable MLDP";
                    }

                    leaf maximum-p2mp-spmsi {
                        type uint32 {
                            range "1..4000";
                        }
                        sros-ext:auto-restart-to-modify;
                        default "10";
                        description "Maximum number of P2MP S-PMSIi tunnels";
                    }

                    container data-threshold {
                        sros-ext:auto-restart-to-modify;
                        description "Enter the data-threshold context";

                        list group-prefix {
                            key "ip-group-prefix";
                            description "Enter the group-prefix list instance";

                            leaf ip-group-prefix {
                                type types-sros:ip-multicast-prefix;
                                description "Multicast group prefix";
                            }

                            leaf threshold {
                                type int64 {
                                    range "0..4294967294";
                                }
                                units "kilobps";
                                mandatory true;
                                description "Threshold rate for a group prefix";
                            }

                            leaf pe-threshold-add {
                                type uint32 {
                                    range "1..65535";
                                }
                                default "65535";
                                description "Number of receiver PEs for S-PMSI tunnel creation";
                            }

                            leaf pe-threshold-delete {
                                type uint32 {
                                    range "2..65535";
                                }
                                default "65535";
                                description "Number of receiver PEs for S-PMSI tunnel deletion";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list group-prefix

                    } // container data-threshold

                } // container selective

            } // container provider-tunnel

            container isid-policy {
                description "Enter the isid-policy context";

                list entry {
                    when "../../pbb-type = 'b-vpls'" {
                        description "supported on b-vpls service";
                    }
                    key "range-entry-id";
                    description "Enter the entry list instance";

                    leaf range-entry-id {
                        type uint32 {
                            range "1..8191";
                        }
                        description "ISID policy entry ID";
                    }

                    leaf advertise-local {
                        type boolean;
                        default "true";
                        description "Advertise locally-defined I-VPLS ISIDs or static ISIDs";
                    }

                    leaf use-def-mcast {
                        type boolean;
                        default "false";
                        description "Use default multicast tree to propagate ISIS range";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container range {
                        description "Enter the range context";

                        leaf start {
                            type types-services:isid-no-zero;
                            description "Lower bound of the ISID range";
                        }

                        leaf end {
                            type types-services:isid-no-zero;
                            description "Upper bound of the ISID range";
                        }

                    } // container range

                } // list entry

            } // container isid-policy

            container network {
                description "Enter the network context";

                container ingress {
                    description "Enter the ingress context";

                    leaf classification-override {
                        type leafref {
                            path "../../../../../qos/ingress-classification-policy/ingress-classification-policy-name";
                        }
                        description "Short-pipe mode for CoS propagation";
                    }

                } // container ingress

            } // container network

        } // list vpls

    } // grouping conf-svc-vpls

}
