submodule nokia-state-router-l2tp {

    yang-version "1.1";

    belongs-to nokia-state { prefix "state"; }

    import ietf-inet-types                { prefix "inet"; }
    import ietf-yang-types                { prefix "yang"; }
    import nokia-sros-yang-extensions     { prefix "sros-ext"; }
    import nokia-types-l2tp               { prefix "types-l2tp"; }
    import nokia-types-ppp                { prefix "types-ppp"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for l2tp on SR OS based routers.

         Copyright 2016 Nokia. All rights reserved. Reproduction of this document
         is authorized on the condition that the foregoing copyright notice is included.

         This nokia-state-router-l2tp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-11-18";

    grouping state-router-l2tp {
        container l2tp {
            description "Enter the l2tp context";

            container statistics {
                description "Enter the statistics context";

                leaf last-cleared {
                    type yang:date-and-time;
                    description "Indicates when the statistics were cleared.";
                }

                leaf total-tunnels {
                    type yang:counter32;
                    description
                        "The total number of tunnels set up attempts since the last
                         re-initialization of the local network management subsystem,
                         or the last time the system statistics were cleared.";
                }

                leaf failed-tunnels {
                    type yang:counter32;
                    description
                        "The total number of tunnels that failed to reach the established
                         state since the last re-initialization of the local network
                         management subsystem, or the last time the system statistics were
                         cleared.";
                }

                leaf failed-authentication {
                    type yang:counter32;
                    description
                        "The total number of tunnels that failed authentication
                         since the last re-initialization of the local network
                         management subsystem, or the last time the system statistics were
                         cleared.";
                }

                leaf actual-tunnels {
                    type yang:counter32;
                    description "The actual number of tunnels.";
                }

                leaf active-tunnels {
                    type yang:counter32;
                    description "The number of tunnels currently established.";
                }

                leaf total-sessions {
                    type yang:counter32;
                    description
                        "The total number of session set up attempts since the last
                         re-initialization of the local network management subsystem,
                         or the last time the system statistics were cleared.";
                }

                leaf failed-sessions {
                    type yang:counter32;
                    description
                        "The total number of sessions that failed to reach the established
                         state since the last re-initialization of the local network
                         management subsystem, or the last time the system statistics were
                         cleared.";
                }

                leaf actual-sessions {
                    type yang:counter32;
                    description "The actual number of sessions.";
                }

                leaf active-sessions {
                    type yang:counter32;
                    description "The number of sessions currently established.";
                }

                leaf blacklist-len {
                    type yang:gauge32;
                    description
                        "The actual number of tunnels and peers in the tunnel
                         selection blacklist.";
                }

                leaf unavailable-tunnel-ids {
                    type yang:gauge32;
                    description
                        "The number of tunnel identifiers that is unavailable for the
                         L2TP protocol because they are used by some other application.";
                }

            } // container statistics

            list oper-group {
                key "tunnel-group-name";
                description "Enter the oper-group list instance";

                leaf tunnel-group-name {
                    type types-sros:named-item-64 {
                        length "1..63";
                    }
                    description "Tunnel group name";
                }

                leaf oper-state {
                    type types-l2tp:group-oper-state;
                    description "The operational state of the tunnel group.";
                }

                leaf session-limit {
                    type types-l2tp:base-session-limit;
                    description "The administrative session limit of this tunnel group.";
                }

                leaf oper-session-limit {
                    type uint32;
                    description "The operational session limit of this tunnel group.";
                }

                leaf session-assign-method {
                    type types-l2tp:base-session-assign-method;
                    description
                        "The latest actual method use for the authentication
                         of the tunnels in this tunnel group.";
                }

                container statistics {
                    description "Enter the statistics context";

                    leaf last-cleared {
                        type yang:date-and-time;
                        description "Indicates when the statistics were cleared.";
                    }

                    leaf total-tunnels {
                        type yang:counter32;
                        description
                            "The total number of tunnel set up attempts
                             in this tunnel group since the last re-initialization
                             of the local network management subsystem, or the last
                             time the system statistics were cleared.";
                    }

                    leaf failed-tunnels {
                        type yang:counter32;
                        description
                            "The total number of tunnels in this tunnel group
                             that failed to reach the established state since the last
                             re-initialization of the local network management subsystem,
                             or the last time the system statistics were cleared.";
                    }

                    leaf auth-failed-tunnels {
                        type yang:counter32;
                        description
                            "The total number of tunnels in this tunnel group
                             that failed authentication since the last re-initialization
                             of the local network management subsystem, or the last time
                             the system statistics were cleared.";
                    }

                    leaf active-tunnels {
                        type yang:gauge32;
                        description
                            "The total number of tunnels currently established
                             in this tunnel group.";
                    }

                    leaf tunnels {
                        type yang:gauge32;
                        description "The actual number of tunnels in this tunnel group.";
                    }

                    leaf total-sessions {
                        type yang:counter32;
                        description
                            "The total number of session creation attempts
                             in this tunnel group since the last re-initialization
                             of the local network management subsystem, or the last
                             time the system statistics were cleared.";
                    }

                    leaf failed-sessions {
                        type yang:counter32;
                        description
                            "The total number of sessions in this tunnel group
                             that failed to reach the established state since the last
                             re-initialization of the local network management subsystem,
                             or the last time the system statistics were cleared.";
                    }

                    leaf active-sessions {
                        type yang:gauge32;
                        description
                            "The total number of sessions currently established
                             in this tunnel group.";
                    }

                    leaf sessions {
                        type yang:gauge32;
                        description "The actual number of sessions in this tunnel group.";
                    }

                    leaf rx-control-octets {
                        type yang:counter64;
                        units "octets";
                        description
                            "The number of control-channel octets received by the
                             current tunnels in this tunnel group.";
                    }

                    leaf rx-control-packets {
                        type yang:counter32;
                        units "packets";
                        description
                            "The number of control-channel packets received by the
                             current tunnels in this tunnel group.";
                    }

                    leaf errored-packets {
                        type yang:gauge32;
                        units "packets";
                        description
                            "The accumulated number of control packets that were
                             received by the current tunnel endpoints in this tunnel group.";
                    }

                    leaf tx-control-octets {
                        type yang:counter64;
                        units "octets";
                        description
                            "The number of control-channel octets transmitted by the
                             current tunnels in this tunnel group.";
                    }

                    leaf tx-control-packets {
                        type yang:counter32;
                        units "packets";
                        description
                            "The number of control-channel packets transmitted by the
                             current tunnels in this tunnel group.";
                    }

                    leaf transmission-errors {
                        type yang:gauge32;
                        units "packets";
                        description
                            "The accumulated number of control packet transmission errors
                             on the current tunnels in this tunnel group.";
                    }

                } // container statistics

            } // list oper-group

            list tunnel {
                key "tunnel-conn-id";
                description "Enter the tunnel list instance";

                leaf tunnel-conn-id {
                    type types-l2tp:connection-id;
                    description "The local connection-id of the control channel of the tunnel.";
                }

                leaf oper-state {
                    type types-l2tp:tunnel-oper-state;
                    description "The operational state of the tunnel.";
                }

                leaf start-time {
                    type yang:date-and-time;
                    description "The time when this tunnel reached the state wait-reply or wait-connected.";
                }

                leaf established-time {
                    type yang:date-and-time;
                    description "The time when this tunnel reached an active state.";
                }

                leaf idle-time {
                    type yang:date-and-time;
                    description "The time when this tunnel entered the state idle.";
                }

                leaf closed-time {
                    type yang:date-and-time;
                    description "The time when this tunnel entered the state closed or closed-by-peer.";
                }

                leaf stop-ccn-result {
                    type types-l2tp:stop-ccn-result;
                    description "The result of a transmitted or received StopCCN message.";
                }

                leaf general-error {
                    type types-l2tp:general-error;
                    description "The general error of a transmitted or received StopCCN message.";
                }

                leaf error-message {
                    type string {
                        length "1..255";
                    }
                    description "Describes the L2TP error condition in human readable form.";
                }

                leaf act-receive-window-size {
                    type uint32;
                    description "The actual receive window size.";
                }

                leaf blacklist-state {
                    type types-l2tp:blacklist-state;
                    description "Indicates if this tunnel is deemed reachable or not.";
                }

                leaf blacklist-time {
                    type yang:date-and-time;
                    description "The time when this tunnel was placed in the tunnel-selection-blacklist.";
                }

                leaf blacklist-remain-time {
                    type uint32;
                    units "seconds";
                    description "Indicates how long the tunnel must still remain in the tunnel-selection-blacklist.";
                }

                leaf oper-session-limit {
                    type uint32;
                    description "The operational session limit of this tunnel.";
                }

                container connection {
                    description "Enter the connection context";

                    leaf rem-conn-id {
                        type types-l2tp:connection-id;
                        description "The remote connection-id of control channel.";
                    }

                    leaf loc-tunnel-id {
                        type types-l2tp:tunnel-id;
                        description "The local tunnel-id.";
                    }

                    leaf rem-tunnel-id {
                        type types-l2tp:tunnel-id;
                        description "The remote tunnel-id.";
                    }

                    leaf transport-type {
                        type types-l2tp:transport-type;
                        description "The transport type used to carry L2TP messages.";
                    }

                    leaf peer {
                        type types-sros:ip-address;
                        description "The peer address";
                    }

                    leaf rem-udp-port {
                        type inet:port-number;
                        description "The remote UDP port of this L2TP tunnel.";
                    }

                    leaf tx-dst-address {
                        type types-sros:ip-address;
                        description
                            "The address used as destination IP address for transmitting
                             L2TP control messages";
                    }

                    leaf tx-dst-udp-port {
                        type inet:port-number;
                        description "The destination UDP port used while transmitting L2TP control messages.";
                    }

                    leaf rx-src-address {
                        type types-sros:ip-address;
                        description
                            "The address found as source IP address in received L2TP control
                             messages";
                    }

                    leaf rx-src-udp-port {
                        type inet:port-number;
                        description "The source UDP port found in received L2TP control messages.";
                    }

                    leaf local-address {
                        type types-sros:ip-address;
                        description "The local address";
                    }

                    leaf loc-udp-port {
                        type inet:port-number;
                        description "The local UDP port of this L2TP tunnel.";
                    }

                    leaf local-name {
                        type types-sros:named-item-64;
                        description "The local host name.";
                    }

                    leaf remote-name {
                        type types-sros:named-item-64;
                        description "The remote host name.";
                    }

                } // container connection

                container parameters {
                    description "Enter the parameters context";

                    leaf protocol {
                        type types-l2tp:protocol-version;
                        description "The protocol version being used";
                    }

                    leaf tunnel-group-name {
                        type types-sros:named-item-64;
                        description "The name of the tunnel group to which this tunnel belongs";
                    }

                    leaf assignment-id {
                        type types-sros:named-item {
                            length "1..32";
                        }
                        description "The identifier assigned to this tunnel.";
                    }

                    leaf preference {
                        type uint32;
                        description "The preference of the tunnel.";
                    }

                    leaf hello-interval {
                        type types-l2tp:base-hello-interval;
                        description "The hello interval.";
                    }

                    leaf idle-timeout {
                        type types-l2tp:base-idle-timeout;
                        description "The idle timeout.";
                    }

                    leaf destruct-timeout {
                        type types-l2tp:base-destruct-timeout;
                        description "The destruction timeout.";
                    }

                    leaf max-retries-estab {
                        type types-l2tp:base-max-retries;
                        description "The maximum number of retries when the tunnel is established.";
                    }

                    leaf max-retries-not-estab {
                        type types-l2tp:base-max-retries;
                        description "The maximum number of retries when the tunnel is not established.";
                    }

                    leaf radius-accounting-policy {
                        type types-sros:named-item;
                        description "The RADIUS accounting policy.";
                    }

                    leaf challenge {
                        type boolean;
                        description "Indicates if challenge-response authentication is used or not.";
                    }

                    leaf avp-hiding {
                        type types-l2tp:base-avp-hiding;
                        description "The AVP hiding.";
                    }

                    leaf session-limit {
                        type types-l2tp:base-session-limit;
                        description "The administrative session limit of this L2TP tunnel";
                    }

                    leaf df-bit-lac {
                        type boolean;
                        description "Indicates if the DF (don't fragment) bit is set in data traffic transmitted as LAC.";
                    }

                } // container parameters

                container failover {
                    description "Enter the failover context";

                    leaf failover-state {
                        type types-l2tp:failover-state;
                        description "The failover state of this tunnel.";
                    }

                    leaf recovery-conn-id {
                        type types-l2tp:connection-id;
                        description "The connection-id of the recovery tunnel.";
                    }

                    leaf recovery-state {
                        type types-l2tp:recovery-state;
                        description "The failover state of a recovery tunnel.";
                    }

                    leaf recovered-conn-id {
                        type types-l2tp:connection-id;
                        description "The connection-id of the recovered tunnel.";
                    }

                    leaf recovery-method {
                        type types-l2tp:base-failover-recovery-method;
                        description "The recovery method.";
                    }

                    leaf track-srrp {
                        type uint32;
                        description "The SRRP instance used for recovery.";
                    }

                    leaf ctrl-msg-behavior {
                        type types-l2tp:control-msg-behavior;
                        description "The behavior of the system with respect to L2TP control traffic.";
                    }

                    leaf requested-recovery-time {
                        type types-l2tp:recovery-time;
                        description "The recovery time requested to the peer system.";
                    }

                    leaf peer-recovery-time {
                        type types-l2tp:recovery-time;
                        description "The recovery time requested by the peer system.";
                    }

                } // container failover

                container l2tpv3 {
                    description "Enter the l2tpv3 context";

                    leaf cookie-length {
                        type types-l2tp:base-v3-cookie-length;
                        description "The cookie length.";
                    }

                    leaf digest-type {
                        type types-l2tp:base-v3-digest-type;
                        description "The digest type";
                    }

                    leaf local-nonce {
                        type types-l2tp:nonce;
                        description "The nonce AVP added to the outgoing control messages.";
                    }

                    leaf remote-nonce {
                        type types-l2tp:nonce;
                        description "The nonce AVP found in incoming control messages.";
                    }

                    leaf rem-router-id {
                        type types-sros:ipv4-address;
                        description "The filter used on remote router ID.";
                    }

                    leaf public-tcp-mss-adjust {
                        type types-l2tp:base-v3-tcp-mss-adjust;
                        description "The TCP maximum segment size (MSS) on public network.";
                    }

                    leaf private-tcp-mss-adjust {
                        type types-l2tp:base-v3-tcp-mss-adjust;
                        description "The TCP maximum segment size (MSS) on private network.";
                    }

                    container pw-cap-list {
                        description "Enter the pw-cap-list context";

                        leaf ethernet {
                            type boolean;
                            description "Ethernet pseudo-wire encapsulation is accepted";
                        }

                        leaf ethernet-vlan {
                            type boolean;
                            description "Ethernet VLAN pseudo-wire encapsulation is accepted";
                        }

                    } // container pw-cap-list

                } // container l2tpv3

                container statistics {
                    description "Enter the statistics context";

                    leaf last-cleared {
                        type yang:date-and-time;
                        description "The time when the statistics were cleared.";
                    }

                    leaf total-sessions {
                        type yang:counter32;
                        description
                            "The total number of session creation attempts
                             in this tunnel since the last re-initialization
                             of the local network management subsystem, or the last
                             time the system statistics were cleared.";
                    }

                    leaf failed-sessions {
                        type yang:counter32;
                        description
                            "The total number of sessions in this tunnel
                             that failed to reach the established state since the last
                             re-initialization of the local network management subsystem,
                             or the last time the system statistics were cleared.";
                    }

                    leaf active-sessions {
                        type yang:gauge32;
                        description
                            "The total number of sessions currently established
                             in this tunnel.";
                    }

                    leaf sessions {
                        type yang:gauge32;
                        description "The actual number of sessions in this tunnel.";
                    }

                    leaf rx-control-octets {
                        type yang:counter64;
                        units "octets";
                        description
                            "The number of control-channel octets received by the
                             tunnel.";
                    }

                    leaf rx-control-packets {
                        type yang:counter32;
                        units "packets";
                        description
                            "The number of control-channel packets received by the
                             tunnel.";
                    }

                    leaf errored-packets {
                        type yang:gauge32;
                        units "packets";
                        description
                            "The accumulated number of control packets that were
                             received by the current tunnel endpoints in this tunnel group.";
                    }

                    leaf tx-control-octets {
                        type yang:counter64;
                        units "octets";
                        description
                            "The number of control-channel octets transmitted by the
                             tunnel.";
                    }

                    leaf tx-control-packets {
                        type yang:counter32;
                        units "packets";
                        description
                            "The number of control-channel packets transmitted by the
                             tunnel.";
                    }

                    leaf transmission-errors {
                        type yang:gauge32;
                        units "packets";
                        description
                            "The accumulated number of control packet transmission errors
                             for the tunnel.";
                    }

                    leaf fsm-msg-accepted {
                        type yang:counter32;
                        units "packets";
                        description
                            "The number of Finite State Machine (FSM) messages that were
                             accepted on this tunnel since the last re-initialization of the local
                             network management subsystem, or the last time the tunnel statistics were
                             cleared.";
                    }

                    leaf fsm-msg-duplicates {
                        type yang:counter32;
                        units "packets";
                        description
                            "The number of duplicate Finite State Machine (FSM) messages that
                             were received on this tunnel since the last re-initialization of the local
                             network management subsystem, or the last time the tunnel statistics were
                             cleared.";
                    }

                    leaf fsm-msg-out-of-rx-window {
                        type yang:counter32;
                        units "packets";
                        description
                            "The number of Finite State Machine (FSM) messages that were received
                             out of the receive window on this tunnel since the last re-initialization of
                             the local network management subsystem, or the last time the tunnel statistics
                             were cleared.";
                    }

                    leaf max-unsent-queue-length {
                        type yang:gauge32;
                        units "packets";
                        description
                            "The maximum length of the unsent message queue on this tunnel since the last
                             re-initialization of the local network management subsystem, or the last time
                             the tunnel statistics were cleared.";
                    }

                    leaf cur-unsent-queue-length {
                        type yang:gauge32;
                        units "packets";
                        description "The current length of the unsent message queue on this tunnel.";
                    }

                    leaf max-ack-queue-length {
                        type yang:gauge32;
                        units "packets";
                        description
                            "The maximum length of the to-be-acknowledged message queue on this tunnel since
                             the last re-initialization of the local network management subsystem, or the
                             last time the tunnel statistics were cleared.";
                    }

                    leaf cur-ack-queue-length {
                        type yang:gauge32;
                        units "packets";
                        description "The current length of the to-be-acknowledged  message queue on this tunnel.";
                    }

                    leaf cur-window-size {
                        type yang:gauge32;
                        description "The current size of the receive window on this tunnel.";
                    }

                    list protocol {
                        key "type id";
                        description "Enter the protocol list instance";

                        leaf type {
                            type types-l2tp:proto-stats-type;
                            description "The statistics type.";
                        }

                        leaf id {
                            type uint32 {
                                range "0..69|4294967294|4294967295";
                            }
                            description "The counter id.";
                        }

                        leaf name {
                            type types-sros:display-string;
                            description "The human-readable identifier of the statistic.";
                        }

                        leaf value {
                            type yang:counter32;
                            description "The counter value";
                        }

                    } // list protocol

                } // container statistics

            } // list tunnel

            list session {
                key "session-conn-id";
                description "Enter the session list instance";

                leaf session-conn-id {
                    type types-l2tp:connection-id;
                    description "The local connection-id of the session.";
                }

                leaf oper-state {
                    type types-l2tp:session-oper-state;
                    description "The operational state of the session.";
                }

                leaf start-time {
                    type yang:date-and-time;
                    description "The time when this session reached the state idle, wait-tunnel, wait-reply or wait-acceptance.";
                }

                leaf established-time {
                    type yang:date-and-time;
                    description "The time when this session entered the state established.";
                }

                leaf closed-time {
                    type yang:date-and-time;
                    description "The time when this session entered the state closed or closed-by-peer.";
                }

                leaf cdn-result {
                    type types-l2tp:cdn-result;
                    description "The result of a transmitted or received CDN message.";
                }

                leaf general-error {
                    type types-l2tp:general-error;
                    description "The general error of a transmitted or received CDN message.";
                }

                leaf error-message {
                    type string {
                        length "0..255";
                    }
                    description "Describes an L2TP error condition in human readable form.";
                }

                leaf mlppp-bundle {
                    type types-l2tp:mlppp-bundle-index;
                    description "The index of the MLPPP bundle to which this session belongs.";
                }

                leaf pw-type {
                    type types-l2tp:pseudo-wire-type;
                    description "The pseudo-wire type of the session.";
                }

                container connection {
                    description "Enter the connection context";

                    leaf loc-tunnel-id {
                        type types-l2tp:tunnel-id;
                        description "The local tunnel-id.";
                    }

                    leaf rem-tunnel-id {
                        type types-l2tp:tunnel-id;
                        description "The remote tunnel-id.";
                    }

                    leaf loc-session-id {
                        type types-l2tp:session-id;
                        description "The local session-id.";
                    }

                    leaf rem-session-id {
                        type types-l2tp:session-id;
                        description "The remote session-id.";
                    }

                    leaf rem-connection-id {
                        type types-l2tp:connection-id;
                        description "The remote connection-id of the session.";
                    }

                    leaf control-connection-id {
                        type types-l2tp:connection-id;
                        description "The local connection-id of the control connection of the tunnel.";
                    }

                } // container connection

                container l2tpv3 {
                    description "Enter the l2tpv3 context";

                    leaf rx-cookie {
                        type binary {
                            length "1..8";
                        }
                        description "The cookie found in received data packets.";
                    }

                    leaf tx-cookie {
                        type binary {
                            length "1..8";
                        }
                        description "The cookie used in transmitted data packets.";
                    }

                    leaf endpoint-id {
                        type binary {
                            length "1..250";
                        }
                        description "The endpoint identification of the session.";
                    }

                    leaf endpoint-description {
                        type types-sros:display-string-or-empty {
                            length "0..80";
                        }
                        description "The endpoint description of the session.";
                    }

                    leaf seq-num-in-rx {
                        type types-l2tp:seq-num-present-in-packet-type;
                        description "Indicates in which received packets sequence numbers are present.";
                    }

                    leaf seq-num-in-tx {
                        type types-l2tp:seq-num-present-in-packet-type;
                        description "Indicates in which received packets sequence numbers are present.";
                    }

                    leaf l2-sub-layer-in-rx {
                        type boolean;
                        description "Indicates if the l2 sub-layer is present in received packets.";
                    }

                    leaf l2-sub-layer-in-tx {
                        type boolean;
                        description "Indicates if the l2 sub-layer is present in transmitted packets.";
                    }

                } // container l2tpv3

                container statistics {
                    description "Enter the statistics context";

                    container ethernet-tunnel {
                        description "Enter the ethernet-tunnel context";

                        leaf rx-packets {
                            type yang:counter64;
                            units "packets";
                            description "The the number of packets received.";
                        }

                        leaf rx-octets {
                            type yang:counter64;
                            units "octets";
                            description "The number of octets received.";
                        }

                        leaf rx-errors {
                            type yang:counter64;
                            units "packets";
                            description "The number of packets dropped while receiving.";
                        }

                        leaf rx-cookie-mismatch {
                            type yang:counter64;
                            units "packets";
                            description
                                "The number of packets dropped because the received cookie value
                                 did not match the cookie value negotiated during session establishment.";
                        }

                        leaf rx-session-id-mismatch {
                            type yang:counter64;
                            units "packets";
                            description
                                "The number of packets dropped because the received session-id
                                 did not match the session-id negotiated during session establishment.";
                        }

                        leaf tx-packets {
                            type yang:counter64;
                            units "packets";
                            description "The number of packets transmitted.";
                        }

                        leaf tx-octets {
                            type yang:counter64;
                            units "octets";
                            description "The number of octets transmitted.";
                        }

                        leaf tx-errors {
                            type yang:counter64;
                            units "packets";
                            description "The number of packets dropped while transmitting.";
                        }

                    } // container ethernet-tunnel

                } // container statistics

            } // list session

            list oper-ethernet-tunnel {
                key "tunnel-group-name vc-id";
                description "Enter the oper-ethernet-tunnel list instance";

                leaf tunnel-group-name {
                    type types-sros:named-item-64 {
                        length "1..63";
                    }
                    description "The name of the tunnel group to which this ethernet tunnel belongs";
                }

                leaf vc-id {
                    type types-services:vc-id;
                    description "The virtual circuit identifier of the ethernet tunnel";
                }

                leaf loc-conn-id {
                    type types-l2tp:connection-id;
                    description "The local connection-id of the ethernet tunnel.";
                }

                leaf down-reason {
                    type string {
                        length "0..80";
                    }
                    description "The reason for the ethernet tunnel not being established.";
                }

                leaf reconnect-timeout {
                    type types-l2tp:base-v3-reconnect-timeout;
                    description "The reconnect timeout for an ethernet tunnel.";
                }

                leaf remaining-time {
                    type uint32;
                    units "seconds";
                    description "The remaining time before a reconnection attempt is made.";
                }

                leaf sap-id {
                    type types-sros:sap;
                    description "The SAP-id.";
                }

                leaf sap-service-name {
                    type types-sros:named-item-64;
                    description "The service of the SAP.";
                }

                leaf control-conn-id {
                    type types-l2tp:connection-id;
                    description "The control connection-id of the L2TP tunnel controling the ethernet tunnel.";
                }

                leaf matches-config {
                    type boolean;
                    description
                        "Indicates if the operational settings of the ethernet tunnel match the tunnel
                         group configuration.";
                }

            } // list oper-ethernet-tunnel

            list udp-peer {
                key "ip-address udp-port";
                description "Enter the udp-peer list instance";

                leaf ip-address {
                    type types-sros:ip-address;
                    description "The peer address";
                }

                leaf udp-port {
                    type inet:port-number;
                    description "The UDP port.";
                }

                leaf draining {
                    type boolean;
                    description "Indicates if this peer is being drained.";
                }

                leaf reachability {
                    type types-l2tp:peer-reachability;
                    description "Indicates if this peer is deemed reachable or not.";
                }

                leaf unreachable-time {
                    type yang:date-and-time;
                    description "The time when this peer was deemed unreachable for the last time.";
                }

                leaf remaining-time {
                    type uint32;
                    units "seconds";
                    description "The remaining time that the peer will remain in the selection-blacklist.";
                }

                leaf roles-capability {
                    type types-l2tp:peer-roles;
                    description "The roles the peer can take.";
                }

                leaf actual-roles {
                    type types-l2tp:peer-roles;
                    description "The roles the peer currently has.";
                }

                container statistics {
                    description "Enter the statistics context";

                    leaf tunnels {
                        type yang:gauge32;
                        description "The actual number of tunnels associated with this peer.";
                    }

                    leaf active-tunnels {
                        type yang:gauge32;
                        description "The actual number of tunnels associated with this peer that are currently established.";
                    }

                    leaf sessions {
                        type yang:gauge32;
                        description "The actual number of sessions associated with this peer.";
                    }

                    leaf active-sessions {
                        type yang:gauge32;
                        description "The actual number of sessions associated with this peer that are currently established.";
                    }

                    leaf rx-control-octets {
                        type yang:counter64;
                        units "octets";
                        description
                            "The number of control channel octets received from this peer since the last re-initialization
                             of the local network management subsystem, or the last time the tunnel statistics were cleared.";
                    }

                    leaf rx-control-packets {
                        type yang:counter32;
                        units "packets";
                        description
                            "The number of control channel packets received from this peer since the last re-initialization
                             of the local network management subsystem, or the last time the tunnel statistics were cleared.";
                    }

                    leaf errored-packets {
                        type yang:counter32;
                        units "packets";
                        description
                            "The number of errored packets received from this peer since the last re-initialization
                             of the local network management subsystem, or the last time the tunnel statistics were cleared.";
                    }

                    leaf tx-control-octets {
                        type yang:counter64;
                        units "octets";
                        description
                            "The number of control channel octets transmitted to this peer since the last re-initialization
                             of the local network management subsystem, or the last time the tunnel statistics were cleared.";
                    }

                    leaf tx-control-packets {
                        type yang:counter32;
                        units "packets";
                        description
                            "The number of control channel packets transmitted to this peer since the last re-initialization
                             of the local network management subsystem, or the last time the tunnel statistics were cleared.";
                    }

                    leaf transmission-errors {
                        type yang:counter32;
                        units "packets";
                        description
                            "The number of packets transmission error for this peer since the last re-initialization
                             of the local network management subsystem, or the last time the tunnel statistics were cleared.";
                    }

                    leaf fsm-msg-accepted {
                        type yang:counter32;
                        units "packets";
                        description
                            "The number of Finite State Machine messages from this peer accepted since the last re-initialization
                             of the local network management subsystem, or the last time the tunnel statistics were cleared.";
                    }

                    leaf fsm-msg-duplicates {
                        type yang:counter32;
                        units "packets";
                        description
                            "The number of duplicate Finite State Machine messages from this peer received since the last re-initialization
                             of the local network management subsystem, or the last time the tunnel statistics were cleared.";
                    }

                    leaf fsm-msg-out-of-rx-window {
                        type yang:counter32;
                        units "packets";
                        description
                            "The number of Finite State Machine (FSM) messages that were received
                             out of the receive window from this peer since the last re-initialization of
                             the local network management subsystem, or the last time the tunnel statistics
                             were cleared.";
                    }

                    leaf last-cleared {
                        type yang:date-and-time;
                        description "The time when the statistics were cleared for the last time.";
                    }

                    list protocol {
                        key "type id";
                        description "Enter the protocol list instance";

                        leaf type {
                            type types-l2tp:proto-stats-type;
                            description "The statistics type.";
                        }

                        leaf id {
                            type uint32 {
                                range "0..69|4294967294|4294967295";
                            }
                            description "The counter id.";
                        }

                        leaf name {
                            type types-sros:display-string;
                            description "The human-readable identifier of the statistic.";
                        }

                        leaf value {
                            type yang:counter32;
                            description "The counter value";
                        }

                    } // list protocol

                } // container statistics

            } // list udp-peer

            list ip-peer {
                key "ip-address";
                description "Enter the ip-peer list instance";

                leaf ip-address {
                    type types-sros:ip-address;
                    description "The peer address";
                }

                leaf draining {
                    type boolean;
                    description "Indicates if this peer is being drained.";
                }

                leaf reachability {
                    type types-l2tp:peer-reachability;
                    description "Indicates if this peer is deemed reachable or not.";
                }

                leaf unreachable-time {
                    type yang:date-and-time;
                    description "The time when this peer was deemed unreachable for the last time.";
                }

                leaf remaining-time {
                    type uint32;
                    units "seconds";
                    description "The remaining time that the peer will remain in the selection-blacklist.";
                }

                leaf roles-capability {
                    type types-l2tp:peer-roles;
                    description "The roles the peer can take.";
                }

                leaf actual-roles {
                    type types-l2tp:peer-roles;
                    description "The roles the peer currently has.";
                }

                container statistics {
                    description "Enter the statistics context";

                    leaf tunnels {
                        type yang:gauge32;
                        description "The actual number of tunnels associated with this peer.";
                    }

                    leaf active-tunnels {
                        type yang:gauge32;
                        description "The actual number of tunnels associated with this peer that are currently established.";
                    }

                    leaf sessions {
                        type yang:gauge32;
                        description "The actual number of sessions associated with this peer.";
                    }

                    leaf active-sessions {
                        type yang:gauge32;
                        description "The actual number of sessions associated with this peer that are currently established.";
                    }

                    leaf rx-control-octets {
                        type yang:counter64;
                        units "octets";
                        description
                            "The number of control channel octets received from this peer since the last re-initialization
                             of the local network management subsystem, or the last time the tunnel statistics were cleared.";
                    }

                    leaf rx-control-packets {
                        type yang:counter32;
                        units "packets";
                        description
                            "The number of control channel packets received from this peer since the last re-initialization
                             of the local network management subsystem, or the last time the tunnel statistics were cleared.";
                    }

                    leaf errored-packets {
                        type yang:counter32;
                        units "packets";
                        description
                            "The number of errored packets received from this peer since the last re-initialization
                             of the local network management subsystem, or the last time the tunnel statistics were cleared.";
                    }

                    leaf tx-control-octets {
                        type yang:counter64;
                        units "octets";
                        description
                            "The number of control channel octets transmitted to this peer since the last re-initialization
                             of the local network management subsystem, or the last time the tunnel statistics were cleared.";
                    }

                    leaf tx-control-packets {
                        type yang:counter32;
                        units "packets";
                        description
                            "The number of control channel packets transmitted to this peer since the last re-initialization
                             of the local network management subsystem, or the last time the tunnel statistics were cleared.";
                    }

                    leaf transmission-errors {
                        type yang:counter32;
                        units "packets";
                        description
                            "The number of packets transmission error for this peer since the last re-initialization
                             of the local network management subsystem, or the last time the tunnel statistics were cleared.";
                    }

                    leaf fsm-msg-accepted {
                        type yang:counter32;
                        units "packets";
                        description
                            "The number of Finite State Machine messages from this peer accepted since the last re-initialization
                             of the local network management subsystem, or the last time the tunnel statistics were cleared.";
                    }

                    leaf fsm-msg-duplicates {
                        type yang:counter32;
                        units "packets";
                        description
                            "The number of duplicate Finite State Machine messages from this peer received since the last re-initialization
                             of the local network management subsystem, or the last time the tunnel statistics were cleared.";
                    }

                    leaf fsm-msg-out-of-rx-window {
                        type yang:counter32;
                        units "packets";
                        description
                            "The number of Finite State Machine (FSM) messages that were received
                             out of the receive window from this peer since the last re-initialization of
                             the local network management subsystem, or the last time the tunnel statistics
                             were cleared.";
                    }

                    leaf last-cleared {
                        type yang:date-and-time;
                        description "The time when the statistics were cleared for the last time.";
                    }

                    list protocol {
                        key "type id";
                        description "Enter the protocol list instance";

                        leaf type {
                            type types-l2tp:proto-stats-type;
                            description "The statistics type.";
                        }

                        leaf id {
                            type uint32 {
                                range "0..69|4294967294|4294967295";
                            }
                            description "The counter id.";
                        }

                        leaf name {
                            type types-sros:display-string;
                            description "The human-readable identifier of the statistic.";
                        }

                        leaf value {
                            type yang:counter32;
                            description "The counter value";
                        }

                    } // list protocol

                } // container statistics

            } // list ip-peer

            list vas-tunnel {
                key "tunnel-conn-id";
                description "Enter the vas-tunnel list instance";

                leaf tunnel-conn-id {
                    type types-l2tp:connection-id;
                    description "The connection-id of the VAS tunnel.";
                }

                leaf transport-type {
                    type types-l2tp:transport-type;
                    description "The transport type used to carry L2TP messages.";
                }

                leaf local-address {
                    type types-sros:ip-address;
                    description "The local address";
                }

                leaf loc-udp-port {
                    type inet:port-number;
                    description "The local UDP port of this VAS tunnel.";
                }

                leaf remote-address {
                    type types-sros:ip-address;
                    description "The remote address";
                }

                leaf rem-udp-port {
                    type inet:port-number;
                    description "The remote UDP port of this VAS tunnel.";
                }

                leaf base-router {
                    type types-sros:router-instance;
                    description "The virtual router instance used as the base of the VAS tunnel.";
                }

                leaf loc-tunnel-id {
                    type types-l2tp:tunnel-id;
                    description "The local tunnel-id.";
                }

                leaf rem-tunnel-id {
                    type types-l2tp:tunnel-id;
                    description "The remote tunnel-id.";
                }

                leaf rem-conn-id {
                    type types-l2tp:connection-id;
                    description "The remote connection-id of the VAS tunnel.";
                }

                list vas-session {
                    key "session-conn-id";
                    description "Enter the vas-session list instance";

                    leaf session-conn-id {
                        type types-l2tp:connection-id;
                        description "The connection-id of the VAS session.";
                    }

                    leaf loc-session-id {
                        type types-l2tp:session-id;
                        description "The local session-id.";
                    }

                    leaf rem-session-id {
                        type types-l2tp:session-id;
                        description "The remote session-id.";
                    }

                    leaf rem-conn-id {
                        type types-l2tp:connection-id;
                        description "The remote connection-id of the VAS session.";
                    }

                } // list vas-session

            } // list vas-tunnel

            list mlppp-bundle {
                key "bundle-index";
                description "Enter the mlppp-bundle list instance";

                leaf bundle-index {
                    type uint32;
                    description "The bundle index";
                }

                leaf service-name {
                    type types-sros:named-item-64;
                    description "The service to which this MLPPP bundle belongs.";
                }

                leaf forwarding-tunnel-id {
                    type types-l2tp:tunnel-id;
                    description
                        "The id of the LTS (L2TP Tunnel Stitching) tunnel if this bundle
                         is associated with PPP sessions that are stiched to another L2TP tunnel.";
                }

                leaf user-name {
                    type types-sros:named-item;
                    description
                        "The user name of the subscriber associated with this MLPPP bundle or another
                         string used to identify that subscriber.";
                }

                container local-endpoint {
                    description "Enter the local-endpoint context";

                    leaf endpoint-class {
                        type types-ppp:mlppp-endpoint-class;
                        description "Endpoint class";
                    }

                    leaf endpoint-id {
                        type binary {
                            length "1..20";
                        }
                        description "Endpoint identifier";
                    }

                    leaf description {
                        type types-sros:description;
                        description "The endpoint description.";
                    }

                } // container local-endpoint

                container remote-endpoint {
                    description "Enter the remote-endpoint context";

                    leaf endpoint-class {
                        type types-ppp:mlppp-endpoint-class;
                        description "Endpoint class";
                    }

                    leaf endpoint-id {
                        type binary {
                            length "1..20";
                        }
                        description "Endpoint identifier";
                    }

                    leaf description {
                        type types-sros:description;
                        description "The endpoint description.";
                    }

                } // container remote-endpoint

                list link {
                    key "session-conn-id";
                    description "Enter the link list instance";

                    leaf session-conn-id {
                        type types-l2tp:connection-id;
                        description "The local connection-id of the session.";
                    }

                    leaf oper-state {
                        type types-l2tp:session-oper-state;
                        description "The operational state of the session.";
                    }

                } // list link

            } // list mlppp-bundle

        } // container l2tp

    } // grouping state-router-l2tp

}
