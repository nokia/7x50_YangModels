submodule nokia-state-saa {

    yang-version "1.1";

    belongs-to nokia-state { prefix "state"; }

    import ietf-yang-types                { prefix "yang"; }
    import nokia-sros-yang-extensions     { prefix "sros-ext"; }
    import nokia-types-oam                { prefix "types-oam"; }
    import nokia-types-sros               { prefix "types-sros"; }

    sros-ext:sros-major-release "rel23";
    organization "Nokia";
    contact
        "Nokia SR OS Support
         Web: <http://www.nokia.com>";
    description
        "Nokia YANG Data model with operational state for Service Assurance Agent (SAA) on SR OS based routers.

         Copyright 2016 Nokia. All rights reserved. Reproduction of this document
         is authorized on the condition that the foregoing copyright notice is included.

         This nokia-state-saa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-09-08";

    grouping state-saa {
        container saa {
            description "Enter the saa context";

            list owner {
                key "owner-name test";
                description "Enter the owner list instance";

                leaf owner-name {
                    type types-sros:named-item;
                    description "Optional owner name of the SAA operation";
                }

                leaf test {
                    type types-sros:named-item;
                    description "SAA test name";
                }

                container statistics {
                    description "Enter the statistics context";

                    leaf runs-since-last-clear {
                        type yang:counter32;
                        description "Indicates the number of times this SAA test has started";
                    }

                    leaf number-of-failed-test-runs {
                        type yang:counter32;
                        description "Indicates the number of times this SAA test has failed";
                    }

                    leaf last-test-result {
                        type types-oam:test-result;
                        description
                            "Indicates the completion status the last time this test was executed. If this SAA
                             test is currently in progress, this object indicates the result of the previous
                             test run, if any";
                    }

                    leaf newest-test-run {
                        type uint32;
                        description "Indicates the most recently completed instance of this SAA test";
                    }

                    container thresholds {
                        description "Enter the thresholds context";

                        list jitter {
                            key "measurement-direction threshold-direction";
                            description "Enter the jitter list instance";

                            leaf measurement-direction {
                                type enumeration {
                                    enum inbound                        { value 1; }
                                    enum outbound                       { value 2; }
                                    enum round-trip                     { value 3; }
                                }
                                description "Indicates the direction of the measurement";
                            }

                            leaf threshold-direction {
                                type enumeration {
                                    enum rising                         { value 1; }
                                    enum falling                        { value 2; }
                                }
                                description "Indicates the direction of the threshold crossing";
                            }

                            leaf last-event {
                                type yang:date-and-time;
                                description
                                    "Indicates the last time a threshold notification was generated as a result of
                                     crossing the specified threshold";
                            }

                            leaf run-number {
                                type uint32;
                                description
                                    "Indicates the test run index of the SAA test for which the specified threshold
                                     notification was generated as a result of crossing the specified threshold";
                            }

                            leaf threshold-value {
                                type int32;
                                units "microseconds";
                                description
                                    "Indicates the value of the statistic that caused the specified threshold
                                     notification to be generated";
                            }

                        } // list jitter

                        list latency {
                            key "measurement-direction threshold-direction";
                            description "Enter the latency list instance";

                            leaf measurement-direction {
                                type enumeration {
                                    enum inbound                        { value 1; }
                                    enum outbound                       { value 2; }
                                    enum round-trip                     { value 3; }
                                }
                                description "Indicates the direction of the measurement";
                            }

                            leaf threshold-direction {
                                type enumeration {
                                    enum rising                         { value 1; }
                                    enum falling                        { value 2; }
                                }
                                description "Indicates the direction of the threshold crossing";
                            }

                            leaf last-event {
                                type yang:date-and-time;
                                description
                                    "Indicates the last time a threshold notification was generated as a result of
                                     crossing the specified threshold";
                            }

                            leaf run-number {
                                type uint32;
                                description
                                    "Indicates the test run index of the SAA test for which the specified threshold
                                     notification was generated as a result of crossing the specified threshold";
                            }

                            leaf threshold-value {
                                type int32;
                                units "microseconds";
                                description
                                    "Indicates the value of the statistic that caused the specified threshold
                                     notification to be generated";
                            }

                        } // list latency

                        list loss {
                            key "measurement-direction threshold-direction";
                            description "Enter the loss list instance";

                            leaf measurement-direction {
                                type enumeration {
                                    enum inbound                        { value 1; }
                                    enum outbound                       { value 2; }
                                    enum round-trip                     { value 3; }
                                }
                                description "Indicates the direction of the measurement";
                            }

                            leaf threshold-direction {
                                type enumeration {
                                    enum rising                         { value 1; }
                                    enum falling                        { value 2; }
                                }
                                description "Indicates the direction of the threshold crossing";
                            }

                            leaf last-event {
                                type yang:date-and-time;
                                description
                                    "Indicates the last time a threshold notification was generated as a result of
                                     crossing the specified threshold";
                            }

                            leaf run-number {
                                type uint32;
                                description
                                    "Indicates the test run index of the SAA test for which the specified threshold
                                     notification was generated as a result of crossing the specified threshold";
                            }

                            leaf threshold-value {
                                type int32;
                                units "packets";
                                description
                                    "Indicates the value of the statistic that caused the specified threshold
                                     notification to be generated";
                            }

                        } // list loss

                    } // container thresholds

                    container ping-common {
                        description "Enter the ping-common context";

                        list test-run {
                            key "run-number";
                            description "Enter the test-run list instance";

                            leaf run-number {
                                type uint32;
                                description "SAA test run number";
                            }

                            leaf execution-state {
                                type enumeration {
                                    enum running                        { value 1; }
                                    enum not-running                    { value 2; }
                                }
                                description "Indicates if the test run is running, or not (i.e. ran to completion, or was stopped by the user)";
                            }

                            leaf sent {
                                type uint32;
                                units "packets";
                                description "Indicates the number of probes sent for the specified test run";
                            }

                            leaf received {
                                type uint32;
                                units "packets";
                                description "Indicates the number of responses received for the specified test run";
                            }

                            leaf loss {
                                type decimal64 {
                                    range "0.000..100.000";
                                    fraction-digits 3;
                                }
                                units "percent";
                                description "Indicates the percentage of packets that failed to be transmitted or timed out";
                            }

                            leaf failed-transmissions {
                                type uint32;
                                units "packets";
                                description "Indicates the number of probes that failed to be sent for the specified test run";
                            }

                            leaf timeouts {
                                type uint32;
                                units "packets";
                                description "Indicates the number of probes that timed out for the specified test run";
                            }

                            leaf total-failures {
                                type uint32;
                                units "packets";
                                description
                                    "Indicates the total number of probes that failed to be transmitted plus the number
                                     of probes that timed out";
                            }

                            list summary {
                                key "summary-type";
                                description "Enter the summary list instance";

                                leaf summary-type {
                                    type enumeration {
                                        enum outbound                       { value 1; }
                                        enum inbound                        { value 2; }
                                        enum round-trip                     { value 3; }
                                    }
                                    description "Delay direction";
                                }

                                leaf delay-minimum {
                                    type int32;
                                    units "microseconds";
                                    description "Indicates the minimum time for the specified probe in the specified direction";
                                }

                                leaf delay-maximum {
                                    type int32;
                                    units "microseconds";
                                    description "Indicates the maximum time for the specified probe in the specified direction";
                                }

                                leaf delay-average {
                                    type int32;
                                    units "microseconds";
                                    description "Indicates the average time for the specified probe in the specified direction";
                                }

                                leaf jitter {
                                    type uint32;
                                    units "microseconds";
                                    description
                                        "Indicates the amount of jitter for the specified test run in the specified
                                         direction";
                                }

                            } // list summary

                            list probe {
                                key "probe-index";
                                description "Enter the probe list instance";

                                leaf probe-index {
                                    type uint32;
                                    description "Probe index number";
                                }

                                leaf outbound {
                                    type int32;
                                    units "microseconds";
                                    description "Indicates the outbound trip time for the specified probe";
                                }

                                leaf inbound {
                                    type int32;
                                    units "microseconds";
                                    description "Indicates the inbound trip time for the specified probe";
                                }

                                leaf round-trip {
                                    type uint32;
                                    units "microseconds";
                                    description "Indicates the round trip time for the specified probe";
                                }

                                leaf return-code {
                                    type types-oam:ping-return-code;
                                    description "Indicates the OAM return code received in the probe response";
                                }

                                leaf response-status {
                                    type types-oam:response-status;
                                    description "Indicates the OAM response status for the specified probe";
                                }

                                leaf responder-source-address {
                                    type types-sros:ip-address;
                                    description "Indicates the IP address of the sender";
                                }

                            } // list probe

                        } // list test-run

                    } // container ping-common

                } // container statistics

            } // list owner

        } // container saa

    } // grouping state-saa

}
