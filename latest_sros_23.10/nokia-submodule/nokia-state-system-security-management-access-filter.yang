submodule nokia-state-system-security-management-access-filter {

    yang-version "1.1";

    belongs-to nokia-state { prefix "state"; }

    import ietf-yang-types                { prefix "yang"; }
    import nokia-sros-yang-extensions     { prefix "sros-ext"; }

    sros-ext:sros-major-release "rel23";
    organization "Nokia";
    contact
        "Nokia SR OS Support
         Web: <http://www.nokia.com>";
    description
        "Nokia YANG Data model with operational state for System security management access filter configuration. on SR OS based routers.

         Copyright 2016 Nokia. All rights reserved. Reproduction of this document
         is authorized on the condition that the foregoing copyright notice is included.

         This nokia-state-system-security-management-access-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-11-14";

    grouping state-system-security-management-access-filter {
        container management-access-filter {
            description "Enter the management-access-filter context";

            container ip-filter {
                description "Enter the ip-filter context";

                list entry {
                    key "entry-id";
                    description "Enter the entry list instance";

                    leaf entry-id {
                        type uint32 {
                            range "1..9999";
                        }
                        description "Entry ID to identify the match criteria and the action";
                    }

                    container statistics {
                        description "Enter the statistics context";

                        leaf match-count {
                            type yang:counter64;
                            description
                                "Indicates the number of times a management packet has matched
                                 this filter entry.";
                        }

                    } // container statistics

                } // list entry

            } // container ip-filter

            container ipv6-filter {
                description "Enter the ipv6-filter context";

                list entry {
                    key "entry-id";
                    description "Enter the entry list instance";

                    leaf entry-id {
                        type uint32 {
                            range "1..9999";
                        }
                        description "Entry ID to identify the match criteria and the action";
                    }

                    container statistics {
                        description "Enter the statistics context";

                        leaf match-count {
                            type yang:counter64;
                            description
                                "Indicates the number of times a management packet has matched
                                 this filter entry.";
                        }

                    } // container statistics

                } // list entry

            } // container ipv6-filter

            container mac-filter {
                description "Enter the mac-filter context";

                list entry {
                    key "entry-id";
                    description "Enter the entry list instance";

                    leaf entry-id {
                        type uint32 {
                            range "1..9999";
                        }
                        description "Entry ID to identify the match criteria and the action";
                    }

                    container statistics {
                        description "Enter the statistics context";

                        leaf match-count {
                            type yang:counter64;
                            description
                                "Indicates the number of times a management packet has matched
                                 this filter entry.";
                        }

                    } // container statistics

                } // list entry

            } // container mac-filter

        } // container management-access-filter

    } // grouping state-system-security-management-access-filter

}
