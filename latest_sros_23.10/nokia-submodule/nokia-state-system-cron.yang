submodule nokia-state-system-cron {

    yang-version "1.1";

    belongs-to nokia-state { prefix "state"; }

    import ietf-yang-types                { prefix "yang"; }
    import nokia-sros-yang-extensions     { prefix "sros-ext"; }
    import nokia-types-sros               { prefix "types-sros"; }
    import nokia-types-system             { prefix "types-system"; }

    sros-ext:sros-major-release "rel23";
    organization "Nokia";
    contact
        "Nokia SR OS Support
         Web: <http://www.nokia.com>";
    description
        "Nokia YANG Data model with operational state for system cron on SR OS based routers.

         Copyright 2016 Nokia. All rights reserved. Reproduction of this document
         is authorized on the condition that the foregoing copyright notice is included.

         This nokia-state-system-cron YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping state-system-cron {
        container cron {
            description "Enter the cron context";

            list schedule {
                key "schedule-name owner";
                description "Enter the schedule list instance";

                leaf schedule-name {
                    type types-sros:named-item;
                    description "Schedule name";
                }

                leaf owner {
                    type types-sros:named-item;
                    description "Schedule owner";
                }

                leaf oper-state {
                    type types-system:cron-oper-state;
                    description
                        "The value of the this object indicates the operational
                         state of the cron.";
                }

                leaf next-scheduled-run {
                    type types-sros:time-interval;
                    units "seconds";
                    description
                        "The value of the this object indicates the inteval in sec for
                         next run.";
                }

                leaf number-of-schedule-runs {
                    type uint32;
                    description "The value of the this object indicates the number of schedule runs.";
                }

                leaf last-schedule-run {
                    type yang:date-and-time;
                    description "The value of the this object indicates the last schedule run.";
                }

                leaf number-of-schedule-failures {
                    type uint32;
                    description
                        "The value of the this object indicates the number of schedule
                         failures.";
                }

                leaf last-schedule-failure-cause {
                    type types-system:schedule-failure;
                    description "The value of the this object indicates the last schedule failure cause.";
                }

                leaf last-failure-time {
                    type yang:date-and-time;
                    description "The value of the this object indicates the last schedule failure time.";
                }

            } // list schedule

        } // container cron

    } // grouping state-system-cron

}
