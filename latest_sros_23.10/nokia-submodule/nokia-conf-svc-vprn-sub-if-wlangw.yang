submodule nokia-conf-svc-vprn-sub-if-wlangw {

    yang-version "1.1";

    belongs-to nokia-conf { prefix "conf"; }

    import nokia-sros-yang-extensions     { prefix "sros-ext"; }
    import nokia-types-sros               { prefix "types-sros"; }

    include nokia-conf-groups;
    include nokia-conf-isa;

    sros-ext:sros-major-release "rel23";
    organization "Nokia";
    contact
        "Nokia SR OS Support
         Web: <http://www.nokia.com>";
    description
        "Nokia YANG Data model to configure vprn service subscriber interface WLAN Gateway on SR OS based routers.

         Copyright 2016 Nokia. All rights reserved. Reproduction of this document
         is authorized on the condition that the foregoing copyright notice is included.

         This nokia-conf-svc-vprn-sub-if-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-11-05";

    grouping conf-svc-vprn-sub-if-wlangw-wlan-gw {
        container wlan-gw {
            presence "Enable the wlan-gw context";
            description "Enable the wlan-gw context";

            leaf-list apply-groups {
                type leafref {
                    path "../../../../../groups/group/name";
                }
                max-elements 8;
                ordered-by user;
                description "Apply a configuration group at this level";
            }

            leaf-list apply-groups-exclude {
                type leafref {
                    path "../../../../../groups/group/name";
                }
                max-elements 8;
                ordered-by user;
                description "Exclude a configuration group at this level";
            }

            container pool-manager {
                description "Enter the pool-manager context";

                leaf wlan-gw-group {
                    type leafref {
                        path "../../../../../../isa/wlan-gw-group/id";
                    }
                    description "ID of WLAN gateway group where prefixes are installed";
                }

                leaf-list apply-groups {
                    type leafref {
                        path "../../../../../../groups/group/name";
                    }
                    max-elements 8;
                    ordered-by user;
                    description "Apply a configuration group at this level";
                }

                leaf-list apply-groups-exclude {
                    type leafref {
                        path "../../../../../../groups/group/name";
                    }
                    max-elements 8;
                    ordered-by user;
                    description "Exclude a configuration group at this level";
                }

                container dhcp6-client {
                    description "Enter the dhcp6-client context";

                    leaf source-ip {
                        type union {
                            type enumeration {
                                enum use-interface-ip               { value 0; }
                            }
                            type types-sros:ipv6-address;
                        }
                        default "use-interface-ip";
                        description "Source IP address that is used by the DHCPv6 client";
                    }

                    leaf-list servers {
                        type types-sros:ipv6-unicast-address;
                        max-elements 8;
                        description "DHCPv6 servers that are used for requesting addresses";
                    }

                    container lease-query {
                        presence "Enable the lease-query context";
                        description "Enable the lease-query context";

                        leaf max-retries {
                            type uint32 {
                                range "0..10";
                            }
                            default "2";
                            description "Retries before lease query assumes no allocated subnets";
                        }

                    } // container lease-query

                    container dhcpv4-nat {
                        description "Enter the dhcpv4-nat context";

                        leaf admin-state {
                            type types-sros:admin-state;
                            default "disable";
                            description "Administrative state of the DHCPv6 client entity";
                        }

                        leaf link-address {
                            type types-sros:ipv6-address;
                            default "::";
                            description "IPv6 address in the link address field of relay header";
                        }

                        leaf pool-name {
                            type types-sros:named-item;
                            description "Pool name to be sent in the DHCPv6 messages";
                        }

                    } // container dhcpv4-nat

                    container ia-na {
                        description "Enter the ia-na context";

                        leaf admin-state {
                            type types-sros:admin-state;
                            default "disable";
                            description "Administrative state of the DHCPv6 client entity";
                        }

                        leaf link-address {
                            type types-sros:ipv6-address;
                            default "::";
                            description "IPv6 address in the link address field of relay header";
                        }

                        leaf pool-name {
                            type types-sros:named-item;
                            description "Pool name to be sent in the DHCPv6 messages";
                        }

                    } // container ia-na

                    container slaac {
                        description "Enter the slaac context";

                        leaf admin-state {
                            type types-sros:admin-state;
                            default "disable";
                            description "Administrative state of the DHCPv6 client entity";
                        }

                        leaf link-address {
                            type types-sros:ipv6-address;
                            default "::";
                            description "IPv6 address in the link address field of relay header";
                        }

                        leaf pool-name {
                            type types-sros:named-item;
                            description "Pool name to be sent in the DHCPv6 messages";
                        }

                    } // container slaac

                } // container dhcp6-client

                container watermarks {
                    description "Enter the watermarks context";

                    leaf high {
                        type uint32 {
                            range "51..99";
                        }
                        default "95";
                        description "High watermark when new prefix is allocated";
                    }

                    leaf low {
                        type uint32 {
                            range "50..98";
                        }
                        default "90";
                        description "Low watermark when unused prefix is released";
                    }

                } // container watermarks

            } // container pool-manager

            container redundancy {
                description "Enter the redundancy context";

                leaf admin-state {
                    type types-sros:admin-state;
                    default "disable";
                    description "Administrative state of WLAN-GW redundancy";
                }

                leaf export {
                    type types-sros:ipv4-unicast-prefix;
                    sros-ext:auto-restart-to-modify;
                    description "Route to export to peer";
                }

                leaf monitor {
                    type types-sros:ipv4-unicast-prefix;
                    sros-ext:auto-restart-to-modify;
                    description "Peer route to monitor";
                }

            } // container redundancy

        } // container wlan-gw

    } // grouping conf-svc-vprn-sub-if-wlangw-wlan-gw

}
