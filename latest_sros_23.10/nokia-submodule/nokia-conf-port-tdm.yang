submodule nokia-conf-port-tdm {

    yang-version "1.1";

    belongs-to nokia-conf { prefix "conf"; }

    import ietf-yang-types                { prefix "yang"; }
    import nokia-sros-yang-extensions     { prefix "sros-ext"; }
    import nokia-types-port               { prefix "types-port"; }
    import nokia-types-qos                { prefix "types-qos"; }
    import nokia-types-sros               { prefix "types-sros"; }

    include nokia-conf-groups;
    include nokia-conf-log;
    include nokia-conf-qos;

    sros-ext:sros-major-release "rel23";
    organization "Nokia";
    contact
        "Nokia SR OS Support
         Web: <http://www.nokia.com>";
    description
        "Nokia YANG Data model to configure TDM ports on SR OS based routers.

         Copyright 2016 Nokia. All rights reserved. Reproduction of this document
         is authorized on the condition that the foregoing copyright notice is included.

         This nokia-conf-port-tdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-04";

    grouping conf-port-tdm {
        container tdm {
            description "Enter the tdm context";

            leaf buildout {
                type enumeration {
                    enum short                          { value 1; }
                    enum long                           { value 2; }
                }
                default "short";
                description "Line buildout for physical DS1/DS3 ports";
            }

            leaf encoding {
                type enumeration {
                    enum b8zs                           { value 1; }
                    enum ami                            { value 2; }
                    enum hdb3                           { value 3; }
                }
                description "Encoding for the physical DS1/E1 port";
            }

            leaf line-impedance {
                type uint32 {
                    range "75 | 100 | 120";
                }
                units "ohms";
                description "Line impedance for the physical DS1/E1 port";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container hold-time {
                description "Enter the hold-time context";

                leaf up {
                    type uint32 {
                        range "1..100";
                    }
                    description "Hold timer for link up event dampening";
                }

                leaf down {
                    type uint32 {
                        range "0..100";
                    }
                    default "5";
                    description "Hold timer for link down event dampening";
                }

            } // container hold-time

            list ds1 {
                key "ds1-index";
                description "Enter the ds1 list instance";

                leaf ds1-index {
                    type types-port:tdm-ds1-index;
                    description "DS-1 channel ID";
                }

                leaf clock-source {
                    type enumeration {
                        enum loop-timed                     { value 1; }
                        enum node-timed                     { value 2; }
                        enum adaptive                       { value 3; }
                        enum differential                   { value 4; }
                    }
                    description "Clock source for data transmission";
                }

                leaf signal-mode {
                    type enumeration {
                        enum channel-associated-signaling   { value 2; }
                    }
                    sros-ext:auto-restart-to-modify;
                    description "Signal mode on the channel";
                }

                leaf admin-state {
                    type types-sros:admin-state;
                    default "disable";
                    description "Administrative state of the DS1 channel";
                }

                leaf framing {
                    type enumeration {
                        enum extended-super-frame           { value 1; }
                        enum super-frame                    { value 2; }
                        enum ds1-unframed                   { value 6; }
                    }
                    sros-ext:auto-restart-to-modify;
                    default "extended-super-frame";
                    description "Framing for the DS1 channel";
                }

                leaf loopback {
                    type enumeration {
                        enum line                           { value 1; }
                        enum internal                       { value 2; }
                        enum fdl-ansi                       { value 3; }
                        enum fdl-bellcore                   { value 4; }
                        enum payload-ansi                   { value 5; }
                        enum inband-ansi                    { value 6; }
                        enum inband-bellcore                { value 7; }
                    }
                    description "Loopback mode for the port";
                }

                leaf remote-loop-respond {
                    type boolean;
                    default "false";
                    description "Respond to requests for remote loopbacks";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    leaf up {
                        type uint32 {
                            range "0..100";
                        }
                        units "deciseconds";
                        default "0";
                        description "Hold timer for link up event dampening on channels";
                    }

                    leaf down {
                        type uint32 {
                            range "0..100";
                        }
                        units "deciseconds";
                        default "0";
                        description "Hold timer for link down event dampening on channels";
                    }

                } // container hold-time

                list channel-group {
                    key "ds0-index";
                    description "Enter the channel-group list instance";

                    leaf ds0-index {
                        type uint32 {
                            range "1..24";
                        }
                        description "Channel group ID";
                    }

                    leaf admin-state {
                        type types-sros:admin-state;
                        default "disable";
                        description "Administrative state of the DS1 channel group";
                    }

                    leaf description {
                        type types-sros:long-description;
                        default "DS0GRP";
                        description "Text description";
                    }

                    leaf load-balancing-algorithm {
                        type types-port:load-balancing-algorithm;
                        description "Load balancing algorithm to be used on the port";
                    }

                    leaf mac-address {
                        type yang:mac-address;
                        default "00:00:00:00:00:00";
                        description "MAC address for the port";
                    }

                    leaf mode {
                        type enumeration {
                            enum access                         { value 1; }
                            enum network                        { value 2; }
                        }
                        sros-ext:auto-restart-to-modify;
                        description "Operation mode for the TDM channel group";
                    }

                    leaf encap-type {
                        type types-port:tdm-encap-type;
                        sros-ext:auto-restart-to-modify;
                        description "Encapsulation method";
                    }

                    leaf mtu {
                        type uint32 {
                            range "512..9208";
                        }
                        units "bytes";
                        description "Maximum payload MTU size for the port";
                    }

                    leaf speed {
                        type uint32 {
                            range "56|64";
                        }
                        sros-ext:auto-restart-to-modify;
                        default "64";
                        description "Speed of the DS0 channels in the channel group";
                    }

                    leaf-list timeslot {
                        type uint32 {
                            range "1..24";
                        }
                        max-elements 24;
                        sros-ext:auto-restart-to-modify;
                        description "Timeslot for the channel group";
                    }

                    leaf loopback {
                        type enumeration {
                            enum line                           { value 1; }
                            enum internal                       { value 2; }
                        }
                        description "Activate a loopback on this channel group.";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container egress {
                        description "Enter the egress context";

                        container port-scheduler-policy {
                            description "Enter the port-scheduler-policy context";

                            leaf policy-name {
                                type leafref {
                                    path "../../../../../../../qos/port-scheduler-policy/name";
                                }
                                description "Port egress scheduler policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container max-rate {
                                    description "Enter the max-rate context";

                                    choice rate-or-percent-rate {
                                        case rate {

                                            leaf rate {
                                                type types-qos:scheduler-pir-rate;
                                                units "kilobps";
                                                default "max";
                                                description "PIR";
                                            }

                                        }
                                        case percent-rate {

                                            leaf percent-rate {
                                                type decimal64 {
                                                    range "0.01..100";
                                                    fraction-digits 2;
                                                }
                                                units "percent";
                                                default "100";
                                                description "PIR";
                                            }

                                        }
                                    }
                                } // container max-rate

                                list level {
                                    key "priority-level";
                                    description "Enter the level list instance";

                                    leaf priority-level {
                                        type uint32 {
                                            range "1..8";
                                        }
                                        description "Port priority levels override";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice rate-or-percent-rate {
                                        case rate {

                                            container rate {
                                                description "Enter the rate context";

                                                leaf pir {
                                                    type types-qos:scheduler-pir-rate;
                                                    units "kilobps";
                                                    default "max";
                                                    description "PIR for the priority level";
                                                }

                                                leaf cir {
                                                    type types-qos:scheduler-cir-rate;
                                                    units "kilobps";
                                                    default "max";
                                                    description "CIR for the priority level";
                                                }

                                            } // container rate

                                        }
                                        case percent-rate {

                                            container percent-rate {
                                                description "Enter the percent-rate context";

                                                leaf pir {
                                                    type decimal64 {
                                                        range "0.01..100";
                                                        fraction-digits 2;
                                                    }
                                                    units "percent";
                                                    default "100";
                                                    description "PIR for the priority level";
                                                }

                                                leaf cir {
                                                    type decimal64 {
                                                        range "0..100";
                                                        fraction-digits 2;
                                                    }
                                                    units "percent";
                                                    default "100";
                                                    description "CIR for the priority level";
                                                }

                                            } // container percent-rate

                                        }
                                    }
                                } // list level

                            } // container overrides

                        } // container port-scheduler-policy

                    } // container egress

                    container idle-payload-fill {
                        description "Enter the idle-payload-fill context";

                        choice idle-payload-fill-choice {
                            case all-ones {

                                leaf all-ones {
                                    type empty;
                                    description "Transmit 8-bit value to be 11111111";
                                }

                            }
                            case pattern {

                                leaf pattern {
                                    type uint32 {
                                        range "0..255";
                                    }
                                    description "User-defined pattern to be transmitted";
                                }

                            }
                        }
                    } // container idle-payload-fill

                    container idle-signal-fill {
                        when "../../signal-mode = 'channel-associated-signaling'" {
                            description "idle-signal-fill is only valid when signal-mode is CAS.";
                        }
                        description "Enter the idle-signal-fill context";

                        choice idle-signal-fill-choice {
                            case all-ones {

                                leaf all-ones {
                                    type empty;
                                    description "Transmit 8-bit value as 11111111";
                                }

                            }
                            case pattern {

                                leaf pattern {
                                    type uint32 {
                                        range "0..15";
                                    }
                                    description "User-defined pattern to be transmitted";
                                }

                            }
                        }
                    } // container idle-signal-fill

                    container network {
                        description "Enter the network context";

                        leaf accounting-policy {
                            type leafref {
                                path "../../../../../../log/accounting-policy/policy-id";
                            }
                            description "Accounting policy";
                        }

                        leaf collect-stats {
                            type boolean;
                            default "false";
                            description "Collect accounting and statistical data";
                        }

                        leaf queue-policy {
                            type leafref {
                                path "../../../../../../qos/network-queue/network-queue-policy";
                            }
                            description "Queue policy on the TDM DS0 network channel group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container network

                } // list channel-group

                container report-alarm {
                    description "Enter the report-alarm context";

                    leaf ais {
                        type boolean;
                        default "true";
                        description "Report alarm indication signal errors";
                    }

                    leaf los {
                        type boolean;
                        default "true";
                        description "Report loss of signal errors";
                    }

                    leaf looped {
                        type boolean;
                        default "false";
                        description "Report looped packet errors";
                    }

                    leaf oof {
                        type boolean;
                        default "false";
                        description "Report out-of-frame errors";
                    }

                    leaf rai {
                        type boolean;
                        default "false";
                        description "Report resource availability indicator events";
                    }

                    leaf ber-sd {
                        when "../../framing = 'extended-super-frame'" {
                            description "ber-sd is only valid when framing is extended-super-frame.";
                        }
                        type boolean;
                        default "false";
                        description "Report the BER that specifies signal degradation";
                    }

                    leaf ber-sf {
                        when "../../framing = 'extended-super-frame'" {
                            description "ber-sf is only valid when framing is extended-super-frame.";
                        }
                        type boolean;
                        default "false";
                        description "Report the BER that species signal failure";
                    }

                } // container report-alarm

                container ber-threshold {
                    when "../framing = 'extended-super-frame'" {
                        description "ber-threshold is only valid when framing is extended-super-frame.";
                    }
                    description "Enter the ber-threshold context";

                    leaf signal-degrade {
                        type uint32 {
                            range "1|5|10|50|100";
                        }
                        default "5";
                        description "BER signal degredation threshold";
                    }

                    leaf signal-failure {
                        type uint32 {
                            range "1|5|10|50|100";
                        }
                        default "50";
                        description "BER signal failure threshold";
                    }

                } // container ber-threshold

            } // list ds1

            list ds3 {
                key "ds3-index";
                description "Enter the ds3 list instance";

                leaf ds3-index {
                    type types-port:tdm-ds3-index;
                    description "TDM DS3 index";
                }

                leaf admin-state {
                    type types-sros:admin-state;
                    default "disable";
                    description "Administrative state of the DS3 port";
                }

                leaf channelized {
                    type enumeration {
                        enum ds1                            { value 2; }
                        enum e1                             { value 3; }
                    }
                    sros-ext:auto-restart-to-modify;
                    description "Channelization of the DS3";
                }

                leaf crc {
                    type uint32 {
                        range "16|32";
                    }
                    sros-ext:auto-restart-to-modify;
                    description "Precision of the cyclic redundancy check (CRC)";
                }

                leaf description {
                    type types-sros:long-description;
                    default "DS3";
                    description "Text description";
                }

                leaf feac-loop-respond {
                    type boolean;
                    default "false";
                    description "Enable DS-3 interface to respond to remote loop signals";
                }

                leaf framing {
                    type enumeration {
                        enum c-bit                          { value 1; }
                        enum m23                            { value 2; }
                        enum ds3-unframed                   { value 6; }
                    }
                    sros-ext:auto-restart-to-modify;
                    default "c-bit";
                    description "Framing for the DS3 channel";
                }

                leaf idle-cycle-flag {
                    type types-port:tdm-dsx-idle-cycle-flag;
                    description "Value transmitted during idle cycles";
                }

                leaf load-balancing-algorithm {
                    type types-port:load-balancing-algorithm;
                    description "Load balancing algorithm to be used on the port";
                }

                leaf loopback {
                    type enumeration {
                        enum line                           { value 1; }
                        enum internal                       { value 2; }
                        enum remote                         { value 3; }
                    }
                    description "Loopback mode on the channel";
                }

                leaf mode {
                    type enumeration {
                        enum access                         { value 1; }
                        enum network                        { value 2; }
                    }
                    sros-ext:auto-restart-to-modify;
                    description "Operation mode";
                }

                leaf encap-type {
                    type types-port:tdm-encap-type;
                    sros-ext:auto-restart-to-modify;
                    description "Encapsulation method";
                }

                leaf mtu {
                    type uint32 {
                        range "512..9208";
                    }
                    units "bytes";
                    description "Maximum payload MTU size for the port";
                }

                leaf scramble {
                    type boolean;
                    description "Enable TDM DS3 payload scrambling";
                }

                leaf clock-source {
                    type enumeration {
                        enum loop-timed                     { value 1; }
                        enum node-timed                     { value 2; }
                    }
                    default "node-timed";
                    description "Clock for data transmission";
                }

                leaf mac-address {
                    type yang:mac-address;
                    default "00:00:00:00:00:00";
                    description "MAC address for the port";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container egress {
                    description "Enter the egress context";

                    container port-scheduler-policy {
                        description "Enter the port-scheduler-policy context";

                        leaf policy-name {
                            type leafref {
                                path "../../../../../../qos/port-scheduler-policy/name";
                            }
                            description "Port egress scheduler policy name";
                        }

                        container overrides {
                            presence "Enable the overrides context";
                            description "Enable the overrides context";

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container max-rate {
                                description "Enter the max-rate context";

                                choice rate-or-percent-rate {
                                    case rate {

                                        leaf rate {
                                            type types-qos:scheduler-pir-rate;
                                            units "kilobps";
                                            default "max";
                                            description "PIR";
                                        }

                                    }
                                    case percent-rate {

                                        leaf percent-rate {
                                            type decimal64 {
                                                range "0.01..100";
                                                fraction-digits 2;
                                            }
                                            units "percent";
                                            default "100";
                                            description "PIR";
                                        }

                                    }
                                }
                            } // container max-rate

                            list level {
                                key "priority-level";
                                description "Enter the level list instance";

                                leaf priority-level {
                                    type uint32 {
                                        range "1..8";
                                    }
                                    description "Port priority levels override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                choice rate-or-percent-rate {
                                    case rate {

                                        container rate {
                                            description "Enter the rate context";

                                            leaf pir {
                                                type types-qos:scheduler-pir-rate;
                                                units "kilobps";
                                                default "max";
                                                description "PIR for the priority level";
                                            }

                                            leaf cir {
                                                type types-qos:scheduler-cir-rate;
                                                units "kilobps";
                                                default "max";
                                                description "CIR for the priority level";
                                            }

                                        } // container rate

                                    }
                                    case percent-rate {

                                        container percent-rate {
                                            description "Enter the percent-rate context";

                                            leaf pir {
                                                type decimal64 {
                                                    range "0.01..100";
                                                    fraction-digits 2;
                                                }
                                                units "percent";
                                                default "100";
                                                description "PIR for the priority level";
                                            }

                                            leaf cir {
                                                type decimal64 {
                                                    range "0..100";
                                                    fraction-digits 2;
                                                }
                                                units "percent";
                                                default "100";
                                                description "CIR for the priority level";
                                            }

                                        } // container percent-rate

                                    }
                                }
                            } // list level

                        } // container overrides

                    } // container port-scheduler-policy

                } // container egress

                container maintenance-data-link {
                    description "Enter the maintenance-data-link context";

                    leaf equipment-id-code {
                        type string {
                            length "0..10";
                        }
                        description "Equipment ID Code (EIC) of the MDL";
                    }

                    leaf facility-id-code {
                        type string {
                            length "0..38";
                        }
                        description "Facility ID Code sent in the MDL Path message";
                    }

                    leaf frame-id-code {
                        type string {
                            length "0..10";
                        }
                        description "Frame ID Code (FIC) of the MDL";
                    }

                    leaf generator-string {
                        type string {
                            length "0..38";
                        }
                        description "Generator number string sent in MDL test signal message";
                    }

                    leaf location-id-code {
                        type string {
                            length "0..11";
                        }
                        description "Location ID Code (LIC) of the MDL";
                    }

                    leaf port-string {
                        type string {
                            length "0..38";
                        }
                        description "Port number string sent in the MDL idle signal message";
                    }

                    leaf unit-id-code {
                        type string {
                            length "0..6";
                        }
                        description "Unit ID Code (UIC) of the MDL";
                    }

                    container transmit-message-type {
                        description "Enter the transmit-message-type context";

                        leaf path {
                            type boolean;
                            default "false";
                            description "Enabletransmission of MDL path messages";
                        }

                        leaf idle-signal {
                            type boolean;
                            default "false";
                            description "Enable transmission of MDL idle signal messages";
                        }

                        leaf test-signal {
                            type boolean;
                            default "false";
                            description "Enable transmission of MDL test signal messages";
                        }

                    } // container transmit-message-type

                } // container maintenance-data-link

                container network {
                    description "Enter the network context";

                    leaf accounting-policy {
                        type leafref {
                            path "../../../../../log/accounting-policy/policy-id";
                        }
                        description "Accounting policy";
                    }

                    leaf collect-stats {
                        type boolean;
                        default "false";
                        description "Collect accounting and statistical data";
                    }

                    leaf queue-policy {
                        type leafref {
                            path "../../../../../qos/network-queue/network-queue-policy";
                        }
                        description "Queue policy on the TDM DS3 network channel";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container network

                container report-alarm {
                    description "Enter the report-alarm context";

                    leaf ais {
                        type boolean;
                        default "true";
                        description "Report alarm indication signal errors";
                    }

                    leaf los {
                        type boolean;
                        default "true";
                        description "Report loss of signal errors";
                    }

                    leaf looped {
                        type boolean;
                        default "false";
                        description "Report looped packet errors";
                    }

                    leaf oof {
                        type boolean;
                        default "false";
                        description "Report out-of-frame errors";
                    }

                    leaf rai {
                        type boolean;
                        default "false";
                        description "Report resource availability indicator events";
                    }

                } // container report-alarm

                container subrate {
                    description "Enter the subrate context";

                    leaf csu-mode {
                        type enumeration {
                            enum digital-link                   { value 1; }
                            enum larscom                        { value 3; }
                        }
                        sros-ext:auto-restart-to-modify;
                        description "Channel Service Unit (CSU) compatibility mode";
                    }

                    leaf rate-step {
                        when "../csu-mode = 'digital-link' or ../csu-mode = 'larscom'" {
                            description "rate-step is only valid when csu-mode is 'digital-link' or 'larscom'.";
                        }
                        type uint32 {
                            range "0..147";
                        }
                        sros-ext:auto-restart-to-modify;
                        description "Subrate for the associated DS3";
                    }

                } // container subrate

            } // list ds3

            list e3 {
                key "e3-index";
                description "Enter the e3 list instance";

                leaf e3-index {
                    type types-port:tdm-e3-index;
                    description "Components making up the SONET/SDH Path";
                }

                leaf admin-state {
                    type types-sros:admin-state;
                    default "disable";
                    description "Administrative state of the E3 channel";
                }

                leaf crc {
                    type uint32 {
                        range "16|32";
                    }
                    sros-ext:auto-restart-to-modify;
                    description "Precision of the CRC";
                }

                leaf description {
                    type types-sros:long-description;
                    default "E3";
                    description "Text description";
                }

                leaf framing {
                    type enumeration {
                        enum g751                           { value 3; }
                        enum g832                           { value 4; }
                        enum e3-unframed                    { value 5; }
                    }
                    sros-ext:auto-restart-to-modify;
                    default "g751";
                    description "Framing for the E3 channel";
                }

                leaf idle-cycle-flag {
                    type types-port:tdm-dsx-idle-cycle-flag;
                    description "Value transmitted by channel group during idle cycle";
                }

                leaf load-balancing-algorithm {
                    type types-port:load-balancing-algorithm;
                    description "Load balancing algorithm to be used on this port";
                }

                leaf loopback {
                    type enumeration {
                        enum line                           { value 1; }
                        enum internal                       { value 2; }
                    }
                    description "Loopback mode";
                }

                leaf mode {
                    type enumeration {
                        enum access                         { value 1; }
                        enum network                        { value 2; }
                    }
                    sros-ext:auto-restart-to-modify;
                    description "Operation mode";
                }

                leaf encap-type {
                    type types-port:tdm-encap-type;
                    sros-ext:auto-restart-to-modify;
                    description "Encapsulation method used on a port, path, or channel";
                }

                leaf mtu {
                    type uint32 {
                        range "512..9208";
                    }
                    units "bytes";
                    description "Maximum payload MTU size";
                }

                leaf scramble {
                    type boolean;
                    description "Enable TDM E3 payload scrambling";
                }

                leaf clock-source {
                    type enumeration {
                        enum loop-timed                     { value 1; }
                        enum node-timed                     { value 2; }
                    }
                    default "node-timed";
                    description "Clock for data transmission";
                }

                leaf mac-address {
                    type yang:mac-address;
                    default "00:00:00:00:00:00";
                    description "MAC address for the port";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container egress {
                    description "Enter the egress context";

                    container port-scheduler-policy {
                        description "Enter the port-scheduler-policy context";

                        leaf policy-name {
                            type leafref {
                                path "../../../../../../qos/port-scheduler-policy/name";
                            }
                            description "Port egress scheduler policy name";
                        }

                        container overrides {
                            presence "Enable the overrides context";
                            description "Enable the overrides context";

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container max-rate {
                                description "Enter the max-rate context";

                                choice rate-or-percent-rate {
                                    case rate {

                                        leaf rate {
                                            type types-qos:scheduler-pir-rate;
                                            units "kilobps";
                                            default "max";
                                            description "PIR";
                                        }

                                    }
                                    case percent-rate {

                                        leaf percent-rate {
                                            type decimal64 {
                                                range "0.01..100";
                                                fraction-digits 2;
                                            }
                                            units "percent";
                                            default "100";
                                            description "PIR";
                                        }

                                    }
                                }
                            } // container max-rate

                            list level {
                                key "priority-level";
                                description "Enter the level list instance";

                                leaf priority-level {
                                    type uint32 {
                                        range "1..8";
                                    }
                                    description "Port priority levels override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                choice rate-or-percent-rate {
                                    case rate {

                                        container rate {
                                            description "Enter the rate context";

                                            leaf pir {
                                                type types-qos:scheduler-pir-rate;
                                                units "kilobps";
                                                default "max";
                                                description "PIR for the priority level";
                                            }

                                            leaf cir {
                                                type types-qos:scheduler-cir-rate;
                                                units "kilobps";
                                                default "max";
                                                description "CIR for the priority level";
                                            }

                                        } // container rate

                                    }
                                    case percent-rate {

                                        container percent-rate {
                                            description "Enter the percent-rate context";

                                            leaf pir {
                                                type decimal64 {
                                                    range "0.01..100";
                                                    fraction-digits 2;
                                                }
                                                units "percent";
                                                default "100";
                                                description "PIR for the priority level";
                                            }

                                            leaf cir {
                                                type decimal64 {
                                                    range "0..100";
                                                    fraction-digits 2;
                                                }
                                                units "percent";
                                                default "100";
                                                description "CIR for the priority level";
                                            }

                                        } // container percent-rate

                                    }
                                }
                            } // list level

                        } // container overrides

                    } // container port-scheduler-policy

                } // container egress

                container network {
                    description "Enter the network context";

                    leaf accounting-policy {
                        type leafref {
                            path "../../../../../log/accounting-policy/policy-id";
                        }
                        description "Accounting policy";
                    }

                    leaf collect-stats {
                        type boolean;
                        default "false";
                        description "Collect accounting and statistical data";
                    }

                    leaf queue-policy {
                        type leafref {
                            path "../../../../../qos/network-queue/network-queue-policy";
                        }
                        description "Queue policy on the TDM E3 network channel";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container network

                container report-alarm {
                    description "Enter the report-alarm context";

                    leaf ais {
                        type boolean;
                        default "true";
                        description "Report alarm indication signal errors";
                    }

                    leaf los {
                        type boolean;
                        default "true";
                        description "Report loss of signal errors";
                    }

                    leaf looped {
                        type boolean;
                        default "false";
                        description "Report looped packet errors";
                    }

                    leaf oof {
                        type boolean;
                        default "false";
                        description "Report out-of-frame errors";
                    }

                    leaf rai {
                        type boolean;
                        default "false";
                        description "Report resource availability indicator events";
                    }

                } // container report-alarm

            } // list e3

            list e1 {
                key "e1-index";
                description "Enter the e1 list instance";

                leaf e1-index {
                    type types-port:tdm-e1-index;
                    description "E-1 channel";
                }

                leaf clock-source {
                    type enumeration {
                        enum loop-timed                     { value 1; }
                        enum node-timed                     { value 2; }
                        enum adaptive                       { value 3; }
                        enum differential                   { value 4; }
                    }
                    sros-ext:auto-restart-to-modify;
                    description "Clock source for data transmission";
                }

                leaf signal-mode {
                    type enumeration {
                        enum channel-associated-signaling   { value 2; }
                    }
                    sros-ext:auto-restart-to-modify;
                    description "Signal mode on the channel";
                }

                leaf admin-state {
                    type types-sros:admin-state;
                    default "disable";
                    description "Administrative state of the E1 channel";
                }

                leaf framing {
                    type enumeration {
                        enum no-crc-g704                    { value 3; }
                        enum g704                           { value 4; }
                        enum e1-unframed                    { value 5; }
                    }
                    sros-ext:auto-restart-to-modify;
                    default "g704";
                    description "Framing on the E1 channel";
                }

                leaf loopback {
                    type enumeration {
                        enum line                           { value 1; }
                        enum internal                       { value 2; }
                    }
                    description "Loopback mode";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    leaf up {
                        type uint32 {
                            range "0..100";
                        }
                        units "deciseconds";
                        default "0";
                        description "Hold timer for link up event dampening on channels";
                    }

                    leaf down {
                        type uint32 {
                            range "0..100";
                        }
                        units "deciseconds";
                        default "0";
                        description "Hold timer for link down event dampening on channels";
                    }

                } // container hold-time

                list channel-group {
                    key "ds0-index";
                    description "Enter the channel-group list instance";

                    leaf ds0-index {
                        type uint32 {
                            range "1..32";
                        }
                        description "DS0 channel group in a channelized DS1 or E1 circuit";
                    }

                    leaf admin-state {
                        type types-sros:admin-state;
                        default "disable";
                        description "Administrative state of the E1 channel group";
                    }

                    leaf description {
                        type types-sros:long-description;
                        default "DS0GRP";
                        description "Text description";
                    }

                    leaf load-balancing-algorithm {
                        type types-port:load-balancing-algorithm;
                        description "Load balancing algorithm to be used on this port";
                    }

                    leaf mac-address {
                        type yang:mac-address;
                        default "00:00:00:00:00:00";
                        description "MAC address for the port";
                    }

                    leaf mode {
                        type enumeration {
                            enum access                         { value 1; }
                            enum network                        { value 2; }
                        }
                        sros-ext:auto-restart-to-modify;
                        description "Operation mode";
                    }

                    leaf encap-type {
                        type types-port:tdm-encap-type;
                        sros-ext:auto-restart-to-modify;
                        description "Encapsulation method used on a port, path, or channel";
                    }

                    leaf mtu {
                        type uint32 {
                            range "512..9208";
                        }
                        units "bytes";
                        description "Maximum payload MTU";
                    }

                    leaf speed {
                        type uint32 {
                            range "56|64";
                        }
                        sros-ext:auto-restart-to-modify;
                        default "64";
                        description "Speed of the E0 channels in this channel group";
                    }

                    leaf-list timeslot {
                        type uint32 {
                            range "1..32";
                        }
                        max-elements 32;
                        sros-ext:auto-restart-to-modify;
                        description "Timeslot list for the channel group";
                    }

                    leaf loopback {
                        type enumeration {
                            enum line                           { value 1; }
                            enum internal                       { value 2; }
                        }
                        description "Loopback mode on the channel group";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container egress {
                        description "Enter the egress context";

                        container port-scheduler-policy {
                            description "Enter the port-scheduler-policy context";

                            leaf policy-name {
                                type leafref {
                                    path "../../../../../../../qos/port-scheduler-policy/name";
                                }
                                description "Port egress scheduler policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container max-rate {
                                    description "Enter the max-rate context";

                                    choice rate-or-percent-rate {
                                        case rate {

                                            leaf rate {
                                                type types-qos:scheduler-pir-rate;
                                                units "kilobps";
                                                default "max";
                                                description "PIR";
                                            }

                                        }
                                        case percent-rate {

                                            leaf percent-rate {
                                                type decimal64 {
                                                    range "0.01..100";
                                                    fraction-digits 2;
                                                }
                                                units "percent";
                                                default "100";
                                                description "PIR";
                                            }

                                        }
                                    }
                                } // container max-rate

                                list level {
                                    key "priority-level";
                                    description "Enter the level list instance";

                                    leaf priority-level {
                                        type uint32 {
                                            range "1..8";
                                        }
                                        description "Port priority levels override";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice rate-or-percent-rate {
                                        case rate {

                                            container rate {
                                                description "Enter the rate context";

                                                leaf pir {
                                                    type types-qos:scheduler-pir-rate;
                                                    units "kilobps";
                                                    default "max";
                                                    description "PIR for the priority level";
                                                }

                                                leaf cir {
                                                    type types-qos:scheduler-cir-rate;
                                                    units "kilobps";
                                                    default "max";
                                                    description "CIR for the priority level";
                                                }

                                            } // container rate

                                        }
                                        case percent-rate {

                                            container percent-rate {
                                                description "Enter the percent-rate context";

                                                leaf pir {
                                                    type decimal64 {
                                                        range "0.01..100";
                                                        fraction-digits 2;
                                                    }
                                                    units "percent";
                                                    default "100";
                                                    description "PIR for the priority level";
                                                }

                                                leaf cir {
                                                    type decimal64 {
                                                        range "0..100";
                                                        fraction-digits 2;
                                                    }
                                                    units "percent";
                                                    default "100";
                                                    description "CIR for the priority level";
                                                }

                                            } // container percent-rate

                                        }
                                    }
                                } // list level

                            } // container overrides

                        } // container port-scheduler-policy

                    } // container egress

                    container idle-payload-fill {
                        description "Enter the idle-payload-fill context";

                        choice idle-payload-fill-choice {
                            case all-ones {

                                leaf all-ones {
                                    type empty;
                                    description "Transmit 8-bit value to be 11111111";
                                }

                            }
                            case pattern {

                                leaf pattern {
                                    type uint32 {
                                        range "0..255";
                                    }
                                    description "User-defined pattern to be transmitted";
                                }

                            }
                        }
                    } // container idle-payload-fill

                    container idle-signal-fill {
                        when "../../signal-mode = 'channel-associated-signaling'" {
                            description "idle-signal-fill is only valid when signal-mode is CAS.";
                        }
                        description "Enter the idle-signal-fill context";

                        choice idle-signal-fill-choice {
                            case all-ones {

                                leaf all-ones {
                                    type empty;
                                    description "Transmit 8-bit value as 11111111";
                                }

                            }
                            case pattern {

                                leaf pattern {
                                    type uint32 {
                                        range "0..15";
                                    }
                                    description "User-defined pattern to be transmitted";
                                }

                            }
                        }
                    } // container idle-signal-fill

                    container network {
                        description "Enter the network context";

                        leaf accounting-policy {
                            type leafref {
                                path "../../../../../../log/accounting-policy/policy-id";
                            }
                            description "Accounting policy";
                        }

                        leaf collect-stats {
                            type boolean;
                            default "false";
                            description "Collect accounting and statistical data";
                        }

                        leaf queue-policy {
                            type leafref {
                                path "../../../../../../qos/network-queue/network-queue-policy";
                            }
                            description "Network queue policy on TDM E0 network channel group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container network

                } // list channel-group

                container national-bits {
                    when "../framing = 'no-crc-g704' or ../framing = 'g704'" {
                        description "national-bits are only valid when framing is g704 or no-crc-g704.";
                    }
                    description "Enter the national-bits context";

                    leaf sa4 {
                        type boolean;
                        default "false";
                        description "Enable bit Sa4";
                    }

                    leaf sa5 {
                        type boolean;
                        default "false";
                        description "Enable bit Sa5";
                    }

                    leaf sa6 {
                        type boolean;
                        default "false";
                        description "Enable bit Sa6";
                    }

                    leaf sa7 {
                        type boolean;
                        default "false";
                        description "Enable bit Sa7";
                    }

                    leaf sa8 {
                        type boolean;
                        default "false";
                        description "Enable bit Sa8";
                    }

                } // container national-bits

                container report-alarm {
                    description "Enter the report-alarm context";

                    leaf ais {
                        type boolean;
                        default "true";
                        description "Report alarm indication signal errors";
                    }

                    leaf los {
                        type boolean;
                        default "true";
                        description "Report loss of signal errors";
                    }

                    leaf looped {
                        type boolean;
                        default "false";
                        description "Report looped packet errors";
                    }

                    leaf oof {
                        type boolean;
                        default "false";
                        description "Report out-of-frame errors";
                    }

                    leaf rai {
                        type boolean;
                        default "false";
                        description "Report resource availability indicator events";
                    }

                    leaf ber-sd {
                        when "../../framing = 'g704'" {
                            description "ber-sd is only valid when framing is g704.";
                        }
                        type boolean;
                        default "false";
                        description "Enable/disable ber-sd alarm.";
                    }

                    leaf ber-sf {
                        when "../../framing = 'g704'" {
                            description "ber-sf is only valid when framing is g704.";
                        }
                        type boolean;
                        default "false";
                        description "Enable/disable ber-sf alarm.";
                    }

                } // container report-alarm

                container ber-threshold {
                    when "../framing = 'g704'" {
                        description "ber-threshold is only valid when framing is g704.";
                    }
                    description "Enter the ber-threshold context";

                    leaf signal-degrade {
                        type uint32 {
                            range "1|5|10|50|100";
                        }
                        default "5";
                        description "BER signal degredation threshold";
                    }

                    leaf signal-failure {
                        type uint32 {
                            range "1|5|10|50|100";
                        }
                        default "50";
                        description "BER signal failure threshold";
                    }

                } // container ber-threshold

            } // list e1

        } // container tdm

    } // grouping conf-port-tdm

}
