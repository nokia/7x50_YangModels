module nokia-sr-ietf-netconf-monitoring-deviations {
    yang-version "1.1";

    namespace "urn:nokia.com:sros:ns:yang:sr:ietf-netconf-monitoring-deviations";
    prefix nokia-ncm-devs;

    import ietf-netconf-monitoring {
        prefix ncm;
        revision-date 2010-10-04;
    }

    import ietf-inet-types { prefix inet; }

    organization "Nokia";

    contact
        "Nokia SR OS Support
         Web: <http://www.nokia.com>";

    description
        "YANG Data model for Nokia NETCONF Monitoring deviations.

        Copyright 2021 Nokia. All rights reserved.
        Reproduction of this document is authorized on the condition
        that the foregoing copyright notice is included.

        This nokia-sr-ietf-netconf-monitoring-deviations YANG module
        embodies Nokia's proprietary intellectual property.  Nokia
        retains all title and ownership in the Specification, including
        any revisions.

        Nokia grants all interested parties a non-exclusive license
        to use and distribute an unmodified copy of this Specification
        in connection with management of Nokia products, and without
        fee, provided this copyright notice and license appear on all
        copies.

        This Specification is supplied `as is`, and Nokia makes no
        warranty, either express or implied, as to the use, operation,
        condition, or performance of the Specification.

        NOTE: This module is currently for prototype use and is not
        shipped as part of SR OS.  The purpose of this module is for
        pre-release and must be manually referenced/loaded from a YANG
        capable client/compiler.  Do not redistribute.
        ";

    revision 2021-02-23;

    typedef sr-netconf-datastore-type {
        type enumeration {
            enum running;
            enum candidate;
            enum startup;
            enum intended;
            enum operational;

            enum configure-running;
            enum configure-candidate;
            enum configure-startup;
            enum configure-intended;
            enum configure-operational;

            enum li-running;
            enum li-candidate;
            enum li-startup;
            enum li-intended;

            enum bof-running;
            enum bof-candidate;
            enum bof-startup;
            enum bof-intended;

            enum debug-running;
            enum debug-candidate;
        }
        description
            "Enumeration of possible NETCONF datastore types based on netconf-datastore-type
             extended with proprietary datastores.";
    }

    //Deviations

    deviation /ncm:netconf-state/ncm:capabilities/ncm:capability {
        description
            "Maximum number of capabilities is 256.";
        deviate add {
            max-elements 256;
        }
    }

    deviation /ncm:netconf-state/ncm:datastores/ncm:datastore/ncm:name {
        description
            "Type of name is sr-netconf-datastore-type.";
        deviate replace {
            type nokia-ncm-devs:sr-netconf-datastore-type;
        }
    }

    deviation /ncm:netconf-state/ncm:datastores/ncm:datastore/ncm:locks/ncm:lock-type/ncm:partial-lock {
        description
            "partial-lock subtree is not supported.";
        deviate not-supported;
    }

    deviation /ncm:netconf-state/ncm:schemas/ncm:schema/ncm:identifier {
        description
            "Maximum length of identifier is 64 characters.";
        deviate replace {
            type string {
                length 0..64;
            }
        }
    }

    deviation /ncm:netconf-state/ncm:schemas/ncm:schema/ncm:version {
        description
            "Maximum length of version is 16 characters.";
        deviate replace {
            type string {
                length 0..16;
            }
        }
    }

    deviation /ncm:netconf-state/ncm:schemas/ncm:schema/ncm:namespace {
        description
            "Maximum length of namespace is 96 characters.";
        deviate replace {
            type inet:uri {
                length 0..96;
            }
        }
    }

    deviation /ncm:netconf-state/ncm:sessions/ncm:session/ncm:username {
        description
            "Maximum length of username is 32 characters.";
        deviate replace {
            type string {
                length 0..32;
            }
        }
    }
}
