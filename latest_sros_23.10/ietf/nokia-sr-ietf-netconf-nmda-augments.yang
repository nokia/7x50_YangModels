module nokia-sr-ietf-netconf-nmda-augments {

  yang-version 1.1;

  namespace "urn:nokia.com:sros:ns:yang:sr:ietf-netconf-nmda-augments";

  prefix nokia-ncds-augs;

  import ietf-netconf-nmda { prefix ncds; }
  import nokia-sr-ietf-netconf-augments { prefix nokia-nc-augs; }

  description "This YANG module defines augmentations to the standard NETCONF nmda RPCs.";

  revision "2020-12-23" {
    description "Initial revision.";
  }


  augment /ncds:get-data/ncds:input {
    uses nokia-nc-augs:nokia-configuration-region;
    uses nokia-nc-augs:nokia-output-formats;
    uses nokia-nc-augs:nokia-managed;
  }


}
