module nokia-types-cflowd {

    yang-version "1.1";

    namespace "urn:nokia.com:sros:ns:yang:sr:types-cflowd";

    prefix "types-cflowd";

    import nokia-sros-yang-extensions     { prefix "sros-ext"; }

    sros-ext:sros-major-release "rel23";
    organization "Nokia";
    contact
        "Nokia SR OS Support
         Web: <http://www.nokia.com>";
    description
        "Common cflowd data types used in the SR OS management system.

         Copyright 2016 Nokia. All rights reserved. Reproduction of this document
         is authorized on the condition that the foregoing copyright notice is included.

         This nokia-types-cflowd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-05-12";

    typedef collector-version {
        type uint32 {
            range "5|8..10";
        }
        description "The version of a cflowd collector.";
    }

    typedef metering-process {
        type enumeration {
            enum standard                       { value 1; }
            enum fp-accelerated                 { value 2; }
        }
        description "The metering process for the sample-profile";
    }

    typedef slice-selection {
        type enumeration {
            enum standard                       { value 1; }
            enum full                           { value 2; }
        }
        description "The sample slice selection for the sample-profile";
    }

}
