module nokia-types-wlangw {

    yang-version "1.1";

    namespace "urn:nokia.com:sros:ns:yang:sr:types-wlangw";

    prefix "types-wlangw";

    import nokia-sros-yang-extensions     { prefix "sros-ext"; }
    import nokia-types-sros               { prefix "types-sros"; }

    sros-ext:sros-major-release "rel23";
    organization "Nokia";
    contact
        "Nokia SR OS Support
         Web: <http://www.nokia.com>";
    description
        "Common WLAN Gateway types data types used in the SR OS management system.

         Copyright 2016 Nokia. All rights reserved. Reproduction of this document
         is authorized on the condition that the foregoing copyright notice is included.

         This nokia-types-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2019-04-11";

    typedef idle-timeout-action {
        type enumeration {
            enum remove                         { value 0; }
            enum shcv                           { value 1; }
        }
        description
            "Indicates the action to be performed when the idle-timeout timer
             expires.";
    }

    typedef shaping-granularity {
        type enumeration {
            enum per-tunnel {
                value 1;
                description "Specifies that a separate shaper is applied to each tunnel.";
            }
            enum per-retailer {
                value 2;
                description "Specifies that a separate shaper is applied to each retailer Mobile Network Operator's fraction of the tunnel payload.";
            }
        }
        description
            "The granularity of the egress shaping for WLAN Gateway on a group
             interface.";
    }

    typedef one-time-http-redirect-url {
        type types-sros:string-not-all-spaces {
            length "1..255";
        }
        description
            "A string that represents an HTTP URL configured for one time HTTP
             redirection.

             This string may contain the following substitution macro's:
             - $URL: specifies that '$URL' must be substituted with the
                     content of the Request-URI in the HTTP GET Request
                     received.

             - $MAC: specifies that '$MAC' must be replaced with a
                     string that represents the MAC address of the
                     subscriber host; the MAC address is formatted in
                     Nokia SROS style, like 00:0c:f1:99:85:b8.

             - $IP:  specifies that '$IP' must be replaced with a string
                     that represents the IP address of the subscriber
                     host.";
    }

    typedef mobile-gateway-connection {
        type enumeration {
            enum gn                             { value 1; }
            enum s2a                            { value 2; }
            enum s2b                            { value 3; }
            enum s11                            { value 4; }
        }
        description "the interface type of the connection between WLAN Gateway and Mobile Gateway";
    }

    typedef mobile-gateway-state {
        type enumeration {
            enum disabled                       { value 0; }
            enum up                             { value 1; }
            enum request-timeout                { value 2; }
            enum fault                          { value 3; }
            enum idle                           { value 4; }
            enum restart                        { value 5; }
        }
        description "state of the connection with this Mobile Gateway";
    }

    typedef pool-address-family {
        type enumeration {
            enum dhcpv6                         { value 0; }
            enum slaac                          { value 1; }
            enum dhcpv4                         { value 2; }
        }
        description "the address family of the pool";
    }

    typedef ue-address-type {
        type enumeration {
            enum ipv4 {
                value 1;
                description "any IPv4 address";
            }
            enum ipv6 {
                value 2;
                description "any IPv6 address";
            }
            enum ipv4-only {
                value 3;
                description "only an IPv4 address";
            }
            enum ipv6-only {
                value 4;
                description "only an IPv6 address";
            }
            enum ipv4v6 {
                value 5;
                description "both an IPv4 and an IPv6 address";
            }
        }
        description "The UE address type";
    }

    typedef encapsulation {
        type enumeration {
            enum gre                            { value 1; }
            enum l2tp                           { value 2; }
            enum l2                             { value 3; }
            enum vxlan                          { value 4; }
        }
        description
            "Wireless LAN Gateway tunnel encapsulation type

             'gre' : Soft GRE
             'l2tp': Soft L2TPv3
             'vlan': IEEE 802.1Q or IEEE 802.1ad
             'vxlan': vxlan endpoint";
    }

    typedef qos-oper-state {
        type enumeration {
            enum admin-down                     { value 0; }
            enum active                         { value 1; }
            enum pending                        { value 2; }
            enum problem                        { value 3; }
        }
        description "Operational state of a WLAN Gateway User Equipment (UE)";
    }

}
