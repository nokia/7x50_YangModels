module nokia-oper-global {

    yang-version "1.1";

    namespace "urn:nokia.com:sros:ns:yang:sr:oper-global";

    prefix "oper-global";

    import nokia-conf                     { prefix "conf"; }
    import nokia-sros-yang-extensions     { prefix "sros-ext"; }
    import nokia-state                    { prefix "state"; }
    import nokia-types-eth-cfm            { prefix "types-eth-cfm"; }
    import nokia-types-oam                { prefix "types-oam"; }
    import nokia-types-operation          { prefix "types-operation"; }
    import nokia-types-qos                { prefix "types-qos"; }
    import nokia-types-sros               { prefix "types-sros"; }
    import nokia-types-subscriber-mgmt    { prefix "types-subscriber-mgmt"; }

    sros-ext:sros-major-release "rel23";
    organization "Nokia";
    contact
        "Nokia SR OS Support
         Web: <http://www.nokia.com>";
    description
        "Nokia YANG Data model for Nokia global operations on SR OS based routers.

         Copyright 2016 Nokia. All rights reserved. Reproduction of this document
         is authorized on the condition that the foregoing copyright notice is included.

         This nokia-oper-global YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-10-15";

    container global-operations {
        config false;
        description "Global operations";

        action md-cli-raw-command {
            description "Trigger MD-CLI command.";

            input {

                leaf md-cli-input-line {
                    type string;
                    mandatory true;
                    description "MD-CLI command to be executed..";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                container results {
                    description "Enter the results context";

                    leaf md-cli-output-block {
                        type string;
                        description "Output of executed MD-CLI command.";
                    }

                } // container results

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action md-cli-raw-command

        action md-compare {
            description "Trigger md-compare command.";

            input {

                container path {
                    description "This parameter contains the path to the target node to compare.";

                    choice path-type {
                        case subtree-path {

                            anyxml subtree-path {
                                description " The source datastore for the compare operation.";

                            } // anyxml subtree-path

                        }
                    }
                } // container path

                leaf configuration-region {
                    type types-sros:configuration-region;
                    description "This parameter contains the configuration region to operate on.";
                }

                container source {
                    description " The source datastore for the compare operation.";

                    choice destination-type {
                        case candidate {

                            leaf candidate {
                                type empty;
                            }

                        }
                        case baseline {

                            leaf baseline {
                                type empty;
                            }

                        }
                        case url {

                            leaf url {
                                type string;
                            }

                        }
                        case running {

                            leaf running {
                                type empty;
                            }

                        }
                        case startup {

                            leaf startup {
                                type empty;
                            }

                        }
                        case booted {

                            leaf booted {
                                type empty;
                            }

                        }
                        case rollback {
                            status obsolete;

                            container rollback {
                                status obsolete;
                                description "Enter the rollback context";

                                leaf checkpoint-id {
                                    status obsolete;
                                    type uint32;
                                }

                            } // container rollback

                        }
                        case rollback-id {

                            leaf rollback-id {
                                type uint32 {
                                    range "0..200";
                                }
                            }

                        }
                        case commit-id {

                            leaf commit-id {
                                type uint32 {
                                    range "1..max";
                                }
                            }

                        }
                    }
                } // container source

                container destination {
                    description "The destination datastore for the compare operation.";

                    choice destination-type {
                        case candidate {

                            leaf candidate {
                                type empty;
                            }

                        }
                        case baseline {

                            leaf baseline {
                                type empty;
                            }

                        }
                        case url {

                            leaf url {
                                type string;
                            }

                        }
                        case running {

                            leaf running {
                                type empty;
                            }

                        }
                        case startup {

                            leaf startup {
                                type empty;
                            }

                        }
                        case booted {

                            leaf booted {
                                type empty;
                            }

                        }
                        case rollback {
                            status obsolete;

                            container rollback {
                                status obsolete;
                                description "Enter the rollback context";

                                leaf checkpoint-id {
                                    status obsolete;
                                    type uint32;
                                }

                            } // container rollback

                        }
                        case rollback-id {

                            leaf rollback-id {
                                type uint32 {
                                    range "0..200";
                                }
                            }

                        }
                        case commit-id {

                            leaf commit-id {
                                type uint32 {
                                    range "1..max";
                                }
                            }

                        }
                    }
                } // container destination

                leaf format {
                    type enumeration {
                        enum xml                            { value 0; }
                        enum md-cli                         { value 1; }
                    }
                    default "xml";
                    description "RPC output format tag.";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                container results {
                    description "Enter the results context";

                    leaf md-compare-output {
                        type string;
                        description "Output of executed md-compare command.";
                    }

                } // container results

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action md-compare

        container oam {
            description "Enter the oam context for operations, administration and maintenance";

            container eth-cfm {
                description "Enter the Eth-CFM context";

                action linktrace {
                    description "Initiate a linktrace test";

                    input {

                        leaf asynchronous {
                            type types-operation:operation-asynchronous;
                            description "Controls execution type of the operation.";
                        }

                        leaf retention-timeout {
                            type types-operation:operation-timeout;
                            description "Timeout for operation data retention in global operation table.";
                        }

                        leaf destination {
                            type union {
                                type types-sros:mac-unicast-address-no-zero;
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf ttl {
                            type uint32 {
                                range "0..255";
                            }
                            default "64";
                            description "Time to live for a returned linktrace";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action linktrace

                action loopback {
                    description "Initiate a loopback test";

                    input {

                        leaf asynchronous {
                            type types-operation:operation-asynchronous;
                            description "Controls execution type of the operation.";
                        }

                        leaf execution-timeout {
                            type types-operation:operation-timeout;
                            description "Timeout for operation execution.";
                        }

                        leaf retention-timeout {
                            type types-operation:operation-timeout;
                            description "Timeout for operation data retention in global operation table.";
                        }

                        leaf destination {
                            type union {
                                type types-sros:mac-unicast-address-no-zero;
                                type enumeration {
                                    enum multicast {
                                        value 0;
                                        description "Class one destination multicast address based on the level of the local MEP";
                                    }
                                }
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf send-count {
                            type int32 {
                                range "1..1024";
                            }
                            default "1";
                            description "Number of loopback messages to send";
                        }

                        leaf size {
                            type uint32 {
                                range "0..1500";
                            }
                            units "bytes";
                            default "0";
                            description "Data portion size of the data TLV, octet string allowed";
                        }

                        leaf priority {
                            type int32 {
                                range "0..7";
                            }
                            description "Frame priority that can be manipulated by QoS policies";
                        }

                        leaf lbm-padding {
                            type uint32 {
                                range "0|3..9778";
                            }
                            default "0";
                            description "Data portion size of the data TLV, no octet string";
                        }

                        leaf timeout {
                            type uint32 {
                                range "1..10";
                            }
                            units "seconds";
                            default "5";
                            description "Wait time for a reply to a sent message request";
                        }

                        leaf interval {
                            type uint32 {
                                range "0..600";
                            }
                            units "deciseconds";
                            default "0";
                            description "Time between probes within the test run";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action loopback

            } // container eth-cfm

            container lsp-ping {
                description "Perform a Label Switched Path (LSP) ping test";

                action bgp-label {
                    description "Perform a BGP-label LSP trace test";

                    input {

                        leaf prefix {
                            type types-sros:ip-prefix;
                            mandatory true;
                            description "Destination IP prefix for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action bgp-label

                action ldp {
                    description "Perform Label Distribution Protocal (LDP) LSP ping test";

                    input {

                        leaf prefix {
                            type types-sros:ip-prefix;
                            mandatory true;
                            description "Destination IP prefix for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action ldp

                action rsvp-te {
                    description "Perform an RSVP-TE LSP ping test";

                    input {

                        leaf lsp-name {
                            type leafref {
                                path "/state:state/state:router/state:mpls/state:lsp/state:lsp-name";
                                require-instance "false";
                            }
                            mandatory true;
                            description "Name of the LSP to test";
                        }

                        leaf path {
                            type leafref {
                                path "/state:state/state:router/state:mpls/state:path/state:path-name";
                                require-instance "false";
                            }
                            description "Name of the MPLS path to test";
                        }

                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf lsp-name {
                                    type types-sros:named-item-64;
                                    description "The name of the LSP to be tested";
                                }

                                leaf path {
                                    type types-sros:named-item-64;
                                    description "The name of the MPLS path to be tested";
                                }

                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action rsvp-te

                action sr-isis {
                    description "Perform an SR-ISIS LSP ping test";

                    input {

                        leaf prefix {
                            type types-sros:ip-prefix;
                            mandatory true;
                            description "Destination IP prefix for the test";
                        }

                        leaf igp-instance {
                            type uint32 {
                                range "0..127";
                            }
                            default "0";
                            description "IGP instance for the SR-ISIS test";
                        }

                        leaf flex-algo {
                            type uint32 {
                                range "128..255";
                            }
                            description "Segment Routing Flexible Algorithm for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf flex-algo {
                                    type uint32 {
                                        range "128..255";
                                    }
                                    description "Segment Routing Flexible Algorithm for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-isis

                action sr-ospf {
                    description "Perform an SR-OSPF LSP ping test";

                    input {

                        leaf prefix {
                            type types-sros:ip-prefix;
                            mandatory true;
                            description "Destination IP prefix for the test";
                        }

                        leaf igp-instance {
                            type uint32 {
                                range "0..31";
                            }
                            default "0";
                            description "IGP instance for the SR-OSPF test";
                        }

                        leaf flex-algo {
                            type uint32 {
                                range "128..255";
                            }
                            description "Segment Routing Flexible Algorithm for the test";
                        }

                        leaf path-destination {
                            type types-sros:ipv4-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ipv4-address;
                                    description "Egress IP next hop address to use with path destination";
                                }

                            }
                        }
                        leaf source-ip-address {
                            type types-sros:ipv4-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf flex-algo {
                                    type uint32 {
                                        range "128..255";
                                    }
                                    description "Segment Routing Flexible Algorithm for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ipv4-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-ospf

                action sr-ospf3 {
                    description "Perform an SR-OSPFv3 LSP ping test";

                    input {

                        leaf prefix {
                            type types-sros:ip-prefix;
                            mandatory true;
                            description "Destination IP prefix for the test";
                        }

                        leaf igp-instance {
                            type uint32 {
                                range "0..31|64..95";
                            }
                            default "0";
                            description "IGP instance for the SR-OSPFv3 test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-ospf3

                action sr-policy {
                    description "Perform an SR policy LSP ping test";

                    input {

                        leaf color {
                            type uint32;
                            mandatory true;
                            description "Segment Routing color for the test";
                        }

                        leaf endpoint {
                            type types-sros:ip-address;
                            mandatory true;
                            description "Segment Routing endpoint for the test";
                        }

                        leaf segment-list {
                            type uint32 {
                                range "1..32";
                            }
                            description "Segment Routing segment list for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf color {
                                    type uint32;
                                    description "The Segment Routing color for the test";
                                }

                                leaf endpoint {
                                    type types-sros:ip-address;
                                    description "The Segment Routing endpoint for the test";
                                }

                                leaf segment-list {
                                    type uint32 {
                                        range "0..32";
                                    }
                                    description "The Segment Routing segment list for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-policy

                action sr-te {
                    description "Perform an SR-TE LSP ping test";

                    input {

                        leaf lsp-name {
                            type leafref {
                                path "/state:state/state:router/state:mpls/state:lsp/state:lsp-name";
                                require-instance "false";
                            }
                            mandatory true;
                            description "Name of the LSP to test";
                        }

                        leaf path {
                            type leafref {
                                path "/state:state/state:router/state:mpls/state:path/state:path-name";
                                require-instance "false";
                            }
                            description "Name of the MPLS path to test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf ttl {
                            type uint32 {
                                range "1..255";
                            }
                            default "255";
                            description "TTL value for the MPLS label of the echo request";
                        }

                        leaf send-count {
                            type uint32 {
                                range "1..100";
                            }
                            units "packets";
                            default "1";
                            description "Number of echo request packets to send";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf lsp-name {
                                    type types-sros:named-item-64;
                                    description "The name of the LSP to be tested";
                                }

                                leaf path {
                                    type types-sros:named-item-64;
                                    description "The name of the MPLS path to be tested";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf ttl {
                                    type uint32 {
                                        range "1..255";
                                    }
                                    description "TTL value for the request's MPLS label";
                                }

                                leaf send-count {
                                    type uint32 {
                                        range "1..100";
                                    }
                                    units "packets";
                                    description "Number of request packets to send";
                                }

                            } // container test-parameters

                            list probe {
                                key "probe-index";
                                description "Probe data for the specified test run";

                                leaf probe-index {
                                    type uint32 {
                                        range "1..max";
                                    }
                                    description "Probe index number";
                                }

                                leaf egress-interface {
                                    type types-sros:interface-name;
                                    description "Indicates the interface name this probe was transmitted from";
                                }

                                leaf round-trip-time {
                                    type uint32;
                                    units "microseconds";
                                    description "Indicates the round trip time for the probe";
                                }

                                leaf status {
                                    type types-oam:response-status;
                                    description "Indicates the OAM response status code for the probe";
                                }

                                container response-packet {
                                    description "Data from packet received as a response to the transmitted probe";

                                    leaf size {
                                        type uint32;
                                        units "bytes";
                                        description "Indicates the number of bytes in the response packet for the specified probe";
                                    }

                                    leaf source-address {
                                        type types-sros:ip-address;
                                        description "Indicates the source address in the response packet for the specified probe";
                                    }

                                    leaf sequence-number {
                                        type uint32;
                                        description
                                            "Indicates the sequence number in the response packet for the
                                             specified probe";
                                    }

                                    leaf return-code {
                                        type int32;
                                        description "Indicates the OAM return code received in the probe response";
                                    }

                                    leaf return-code-string {
                                        type types-oam:lsp-ping-trace-return-code;
                                        description "Description of the OAM return code";
                                    }

                                } // container response-packet

                            } // list probe

                            container summary {
                                description "Test run summary data";

                                container statistics {
                                    description "Test run summary statistics";

                                    container packets {
                                        description "Packet statistics for the specified test run";

                                        leaf sent {
                                            type uint32;
                                            units "packets";
                                            description "Indicates the number of packets sent for the specified test run";
                                        }

                                        leaf received {
                                            type uint32;
                                            units "packets";
                                            description "Indicates the number of packets received for the specified test run";
                                        }

                                        leaf loss {
                                            type decimal64 {
                                                range "0.00..100.00";
                                                fraction-digits 2;
                                            }
                                            units "percent";
                                            description "Indicates the number of packet loss percentage for the specified test run";
                                        }

                                    } // container packets

                                    container round-trip-time {
                                        description "Test run round trip time statistics";

                                        leaf minimum {
                                            type uint32;
                                            units "microseconds";
                                            description "Indicates the minimum round trip time for the specified test run";
                                        }

                                        leaf average {
                                            type uint32;
                                            units "microseconds";
                                            description "Indicates the average round trip time for the specified test run";
                                        }

                                        leaf maximum {
                                            type uint32;
                                            units "microseconds";
                                            description "Indicates the maximum round trip time for the specified test run";
                                        }

                                        leaf standard-deviation {
                                            type uint32;
                                            units "microseconds";
                                            description
                                                "Indicates the standard deviation for the round trip times for the
                                                 specified test run";
                                        }

                                    } // container round-trip-time

                                } // container statistics

                            } // container summary

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-te

            } // container lsp-ping

            container lsp-trace {
                description "Perform a Label Switched Path (LSP) trace test";

                action bgp-label {
                    description "Perform a BGP-label LSP trace test";

                    input {

                        leaf prefix {
                            type types-sros:ip-prefix;
                            mandatory true;
                            description "Destination IP prefix for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action bgp-label

                action ldp {
                    description "Perform an LDP LSP trace test";

                    input {

                        leaf prefix {
                            type types-sros:ip-prefix;
                            mandatory true;
                            description "Destination IP prefix for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action ldp

                action rsvp-te {
                    description "Perform an RSVP-TE LSP trace test";

                    input {

                        leaf lsp-name {
                            type leafref {
                                path "/state:state/state:router/state:mpls/state:lsp/state:lsp-name";
                                require-instance "false";
                            }
                            mandatory true;
                            description "Name of the LSP to test";
                        }

                        leaf path {
                            type leafref {
                                path "/state:state/state:router/state:mpls/state:path/state:path-name";
                                require-instance "false";
                            }
                            description "Name of the MPLS path to test";
                        }

                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf lsp-name {
                                    type types-sros:named-item-64;
                                    description "The name of the LSP to be tested";
                                }

                                leaf path {
                                    type types-sros:named-item-64;
                                    description "The name of the MPLS path to be tested";
                                }

                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action rsvp-te

                action sr-isis {
                    description "Perform an SR-ISIS LSP trace test";

                    input {

                        leaf prefix {
                            type types-sros:ip-prefix;
                            mandatory true;
                            description "Destination IP prefix for the test";
                        }

                        leaf igp-instance {
                            type uint32 {
                                range "0..127";
                            }
                            default "0";
                            description "IGP instance for the SR-ISIS test";
                        }

                        leaf flex-algo {
                            type uint32 {
                                range "128..255";
                            }
                            description "Segment Routing Flexible Algorithm for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf flex-algo {
                                    type uint32 {
                                        range "128..255";
                                    }
                                    description "Segment Routing Flexible Algorithm for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-isis

                action sr-ospf {
                    description "Perform an SR-OSPF LSP trace test";

                    input {

                        leaf prefix {
                            type types-sros:ip-prefix;
                            mandatory true;
                            description "Destination IP prefix for the test";
                        }

                        leaf igp-instance {
                            type uint32 {
                                range "0..31";
                            }
                            default "0";
                            description "IGP instance for the SR-OSPF test";
                        }

                        leaf flex-algo {
                            type uint32 {
                                range "128..255";
                            }
                            description "Segment Routing Flexible Algorithm for the test";
                        }

                        leaf path-destination {
                            type types-sros:ipv4-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ipv4-address;
                                    description "Egress IP next hop address to use with path destination";
                                }

                            }
                        }
                        leaf source-ip-address {
                            type types-sros:ipv4-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf flex-algo {
                                    type uint32 {
                                        range "128..255";
                                    }
                                    description "Segment Routing Flexible Algorithm for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ipv4-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-ospf

                action sr-ospf3 {
                    description "Perform an SR-OSPFv3 LSP trace test";

                    input {

                        leaf prefix {
                            type types-sros:ip-prefix;
                            mandatory true;
                            description "Destination IP prefix for the test";
                        }

                        leaf igp-instance {
                            type uint32 {
                                range "0..31|64..95";
                            }
                            default "0";
                            description "IGP instance for the SR-OSPFv3 test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf prefix {
                                    type types-sros:ip-prefix;
                                    description "The destination IP prefix for the test";
                                }

                                leaf igp-instance {
                                    type uint32 {
                                        range "0..127";
                                    }
                                    description "The IGP instance for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-ospf3

                action sr-policy {
                    description "Perform an SR policy LSP trace test";

                    input {

                        leaf color {
                            type uint32;
                            mandatory true;
                            description "Segment Routing color for the test";
                        }

                        leaf endpoint {
                            type types-sros:ip-address;
                            mandatory true;
                            description "Segment Routing endpoint for the test";
                        }

                        leaf segment-list {
                            type uint32 {
                                range "1..32";
                            }
                            description "Segment Routing segment list for the test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf color {
                                    type uint32;
                                    description "The Segment Routing color for the test";
                                }

                                leaf endpoint {
                                    type types-sros:ip-address;
                                    description "The Segment Routing endpoint for the test";
                                }

                                leaf segment-list {
                                    type uint32 {
                                        range "0..32";
                                    }
                                    description "The Segment Routing segment list for the test";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-policy

                action sr-te {
                    description "Perform an SR-TE LSP trace test";

                    input {

                        leaf lsp-name {
                            type leafref {
                                path "/state:state/state:router/state:mpls/state:lsp/state:lsp-name";
                                require-instance "false";
                            }
                            mandatory true;
                            description "Name of the LSP to test";
                        }

                        leaf path {
                            type leafref {
                                path "/state:state/state:router/state:mpls/state:path/state:path-name";
                                require-instance "false";
                            }
                            description "Name of the MPLS path to test";
                        }

                        leaf path-destination {
                            type types-sros:ip-address;
                            description "IP address of the path destination";
                        }

                        choice path-destination-egress {
                            case case-interface {

                                leaf interface {
                                    type leafref {
                                        path "/state:state/state:router/state:interface/state:interface-name";
                                        require-instance "false";
                                    }
                                    description "Egress router interface to use with path destination";
                                }

                            }
                            case case-next-hop {

                                leaf next-hop {
                                    type types-sros:ip-address;
                                    description "Egress IP next hop address to use with path destination";
                                }

                            }
                        }
                        leaf source-ip-address {
                            type types-sros:ip-address;
                            description "Source IP address";
                        }

                        leaf interval {
                            type uint32 {
                                range "1..10";
                            }
                            units "seconds";
                            default "1";
                            description "Minimum time to expire before next echo request is sent";
                        }

                        leaf size {
                            type uint32 {
                                range "1..9786";
                            }
                            units "bytes";
                            default "1";
                            description "Echo request packet pad size";
                        }

                        leaf fc {
                            type types-sros:fc-name;
                            default "be";
                            description "QoS forwarding class for the sent echo request packet";
                        }

                        leaf profile {
                            type types-qos:profile-in-out;
                            default "out";
                            description "QoS profile for the transmitted echo request packets";
                        }

                        leaf timeout {
                            type uint32 {
                                range "1..10";
                            }
                            units "seconds";
                            default "5";
                            description "Time to wait for a reply after sending an echo request";
                        }

                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        leaf min-ttl {
                            type uint32 {
                                range "1..255";
                            }
                            default "1";
                            description "Initial TTL for the test";
                        }

                        leaf max-ttl {
                            type uint32 {
                                range "1..255";
                            }
                            default "30";
                            description "Maximum TTL";
                        }

                        leaf max-fail {
                            type uint32 {
                                range "1..255";
                            }
                            default "5";
                            description "Maximum consecutive timeouts before terminating test";
                        }

                        leaf probe-count {
                            type uint32 {
                                range "1..10";
                            }
                            default "1";
                            description "Number of OAM trace probes to send per TTL";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            container test-parameters {
                                description "Enter the test-parameters context";

                                leaf lsp-name {
                                    type types-sros:named-item-64;
                                    description "The name of the LSP to be tested";
                                }

                                leaf path {
                                    type types-sros:named-item-64;
                                    description "The name of the MPLS path to be tested";
                                }

                                leaf path-destination {
                                    type types-sros:ip-address;
                                    description "The IP address of the path destination";
                                }

                                choice path-destination-egress {
                                    case case-interface {

                                        leaf interface {
                                            type types-sros:interface-name;
                                            description "The egress router interface, used in conjunction with path-destination";
                                        }

                                    }
                                    case case-next-hop {

                                        leaf next-hop {
                                            type types-sros:ip-address;
                                            description "The egress IP next hop address, used in conjunction with path-destination";
                                        }

                                    }
                                }
                                leaf source-ip-address {
                                    type types-sros:ip-address;
                                    description "Source IP address";
                                }

                                leaf interval {
                                    type uint32 {
                                        range "1..10";
                                    }
                                    units "seconds";
                                    description "Minimum time to expire before the next request is sent";
                                }

                                leaf size {
                                    type uint32 {
                                        range "1..9786";
                                    }
                                    units "bytes";
                                    description "Packet pad size of request";
                                }

                                leaf fc {
                                    type types-sros:fc-name;
                                    description "QoS Forwarding Class for the transmitted request packet(s)";
                                }

                                leaf profile {
                                    type types-qos:profile-in-out;
                                    description "QoS profile for the transmitted request packet(s)";
                                }

                                leaf timeout {
                                    type uint32 {
                                        range "1..10";
                                    }
                                    units "seconds";
                                    description "Time router waits for a reply after sending a request";
                                }

                                leaf downstream-map-tlv {
                                    type enumeration {
                                        enum dsmap                          { value 1; }
                                        enum ddmap                          { value 2; }
                                        enum none                           { value 3; }
                                    }
                                    description "The type of downstream mapping TLV in MPLS echo request PDU";
                                }

                                leaf min-ttl {
                                    type uint32 {
                                        range "1..255";
                                    }
                                    description "The initial time-to-live value for the test";
                                }

                                leaf max-ttl {
                                    type uint32 {
                                        range "1..255";
                                    }
                                    description "The maximum time-to-live value for the test";
                                }

                                leaf max-fail {
                                    type uint32 {
                                        range "1..255";
                                    }
                                    description "The maximum number of consecutive timeouts allowed before terminating test";
                                }

                                leaf probe-count {
                                    type uint32 {
                                        range "1..10";
                                    }
                                    description "The number of OAM trace probes to send per TTL";
                                }

                            } // container test-parameters

                            container request-packet {
                                description "Enter the request-packet context";

                                leaf size {
                                    type uint32;
                                    units "bytes";
                                    description "Indicates the number of bytes of each request packet sent";
                                }

                                leaf source-address {
                                    type types-sros:ip-address;
                                    description "Indicates the source address of the test run";
                                }

                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    leaf mapping-tlv-index {
                                        type uint32;
                                        description
                                            "The index value identifies one RFC 4379 Downstream Mapping
                                             TLV (or one RFC 6424 Downstream Detailed Mapping TLV) within
                                             the first request packet sent for the specified test run";
                                    }

                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    leaf ip-address {
                                        type types-sros:ip-address;
                                        description
                                            "The Downstream IP Address field in the specified RFC 4379 Downstream Mapping TLV (or the
                                             Downstream Address field in the specified RFC 6424 Downstream Detailed
                                             Mapping TLV)";
                                    }

                                    leaf interface-address {
                                        type types-sros:ip-address;
                                        description
                                            "The value of the Downstream Interface Address field in the specified
                                             RFC 4379 Downstream Mapping TLV (or RFC 6424 Downstream Detailed Mapping TLV)";
                                    }

                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        leaf label-index {
                                            type uint32 {
                                                range "1..max";
                                            }
                                            description
                                                "The index value identifies one RFC 4379 Downstream Mapping (or one
                                                 RFC 6424 Downstream Detailed Mapping) {Downstream Label, Protocol} pair";
                                        }

                                        leaf label {
                                            type int32;
                                            description
                                                "The value in the Downstream Label field of the specified RFC 4379 Downstream
                                                 Mapping TLV or RFC 6424 Downstream Detailed Mapping TLV";
                                        }

                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            list hop {
                                key "hop-index";
                                description "Per-hop test results";

                                leaf hop-index {
                                    type uint32 {
                                        range "1..max";
                                    }
                                    description "The hop index of the test results";
                                }

                                list probe {
                                    key "probe-index";
                                    description "Probe data for the specified test run";

                                    leaf probe-index {
                                        type uint32 {
                                            range "1..10";
                                        }
                                        description "The probe index of lsp-trace reply, in the context of a hop";
                                    }

                                    list probe-instance {
                                        key "probe-instance-index";
                                        description "Probe instance of a probe, in the contex of a hop";

                                        leaf probe-instance-index {
                                            type uint32 {
                                                range "1..4294967295";
                                            }
                                            description "Index of probes with the specified test run";
                                        }

                                        leaf egress-interface {
                                            type types-sros:interface-name;
                                            description "The interface name this probe was transmitted from";
                                        }

                                        leaf round-trip-time {
                                            type uint32;
                                            units "microseconds";
                                            description "Indicates the round trip time for the probe";
                                        }

                                        leaf status {
                                            type types-oam:response-status;
                                            description "The OAM response status code for the specified test";
                                        }

                                        container response-packet {
                                            description "Data from packet received as a response to transmitted probe";

                                            leaf size {
                                                type uint32;
                                                units "bytes";
                                                description "Indicates the number of bytes in the response packet for the probe";
                                            }

                                            leaf source-address {
                                                type types-sros:ip-address;
                                                description
                                                    "Indicates the source address in the response packet for the specified
                                                     probe";
                                            }

                                            leaf return-code {
                                                type int32;
                                                description "Indicates the OAM return code received in the probe response";
                                            }

                                            leaf return-code-string {
                                                type types-oam:lsp-ping-trace-return-code;
                                                description "Description of the return-code";
                                            }

                                            leaf return-subcode {
                                                type uint32;
                                                description
                                                    "Indicates the stack-depth where processing was terminated with
                                                     the value in the return-code";
                                            }

                                            list downstream-mapping-tlv {
                                                key "mapping-tlv-index";
                                                description
                                                    "Content of the RFC 4379 Downstream Mapping TLV
                                                     (or one RFC 6424 Downstream Detailed Mapping TLV) within
                                                     the reply PDU";

                                                leaf mapping-tlv-index {
                                                    type uint32;
                                                    description
                                                        "The index value identifies a RFC 4379 Downstream Mapping TLV
                                                         (or one RFC 6424 Downstream Detailed Mapping TLV) within
                                                         the reply PDU";
                                                }

                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                leaf interface-address {
                                                    type types-sros:ip-address;
                                                    description
                                                        "The value of the Downstream Interface Address field in the specified
                                                         RFC 4379 Downstream Mapping TLV (or RFC 6424 Downstream Detailed Mapping TLV)";
                                                }

                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                leaf ingress-interface {
                                                    type types-sros:interface-name;
                                                    description
                                                        "The ingress interface number reported by the replying node.
                                                         This value is copied from the Downstream Interface Address field";
                                                }

                                                list mpls-label-stack-entry {
                                                    key "label-index";
                                                    description "The information of a single downstream label within a returned Downstream L2 Mapping TLV";

                                                    leaf label-index {
                                                        type uint32 {
                                                            range "1..max";
                                                        }
                                                        description "The index value identifies a downstream label entry within a specific L2 mapping entry";
                                                    }

                                                    leaf label {
                                                        type int32;
                                                        description
                                                            "The value in the Downstream Label field of the specified RFC 4379 Downstream
                                                             Mapping TLV or RFC 6424 Downstream Detailed Mapping TLV";
                                                    }

                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                list fec-stack-entry {
                                                    key "fec-index";
                                                    description
                                                        "Content of RFC 6424 FEC (Forwarding Equivalence Class) Stack
                                                         Change sub-TLV within the specified Downstream Detailed Mapping TLV
                                                         present in the reply PDU";

                                                    leaf fec-index {
                                                        type uint32 {
                                                            range "1..8";
                                                        }
                                                        description "The index value of one RFC 6424 FEC Stack Change sub-TLV";
                                                    }

                                                    leaf operation-type {
                                                        type enumeration {
                                                            enum push                           { value 1; }
                                                            enum pop                            { value 2; }
                                                        }
                                                        description
                                                            "The value of the Operation Type field in
                                                             RFC 6424 FEC Stack Change sub-TLV";
                                                    }

                                                    leaf sub-type {
                                                        type types-sros:named-item-or-empty;
                                                        description "The value of Subtype field in RFC 4379 FEC-type-specific sub-TLV";
                                                    }

                                                    leaf prefix {
                                                        type types-sros:ip-address;
                                                        description
                                                            "The value of FEC-type-specific IP prefix (or IP address) field
                                                             in RFC 6424 FEC Stack Change sub-TLV";
                                                    }

                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sr-te

            } // container lsp-trace

            container saa {
                description "Enter the saa context";

                list owner {
                    key "owner-name test";
                    description "SAA owner name";

                    leaf owner-name {
                        type leafref {
                            path "/state:state/state:saa/state:owner[state:test=current()/../test]/state:owner-name";
                        }
                        description "Name of the owner of SAA test to be stopped or started";
                    }

                    leaf test {
                        type leafref {
                            path "/state:state/state:saa/state:owner[state:owner-name=current()/../owner-name]/state:test";
                        }
                        description "Name of the SAA test to be stopped or started";
                    }

                    action start {
                        description "Start the SAA test";

                        input {

                            leaf accounting {
                                type boolean;
                                default "true";
                                description "Disable recording results in accounting policy";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action start

                    action stop {
                        description "Stop the SAA test";

                        input {

                            leaf accounting {
                                type boolean;
                                default "true";
                                description "Disable recording results in accounting policy";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stop

                } // list owner

            } // container saa

            container service-activation-testhead {
                description "Start or stop Service Activation Testhead service test";

                list service-test {
                    key "service-test-name";
                    description "Service test name";

                    leaf service-test-name {
                        type leafref {
                            path "/state:state/state:test-oam/state:service-activation-testhead/state:service-test/state:test-name";
                        }
                        description "Name of the service test to be started or stopped";
                    }

                    action start {
                        description "Start OAM SATH service test";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action start

                    action stop {
                        description "Stop OAM SATH service test";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stop

                } // list service-test

            } // container service-activation-testhead

        } // container oam

        action ping {
            description "Trigger ping of address or dns-name via machine interface";

            input {

                choice ping-type {
                    mandatory true;
                    case case-ip-or-dns {

                        leaf destination {
                            type union {
                                type types-sros:ip-address-with-zone;
                                type types-sros:string-not-all-spaces {
                                    length "1..128";
                                }
                            }
                            mandatory true;
                            description "Destination IP address or DNS name";
                        }

                        choice routing-options {
                            case case-bypass-routing {

                                leaf bypass-routing {
                                    type empty;
                                    description "Bypass routing table when sending ping request to host";
                                }

                            }
                            case case-interface {

                                leaf interface {
                                    type types-sros:interface-name;
                                    description "Sending interface name";
                                }

                            }
                            case case-next-hop {

                                leaf next-hop-address {
                                    type types-sros:ip-address;
                                    description "Next-hop address to send packet, ignoring routing table";
                                }

                            }
                            case case-subscriber {

                                leaf subscriber {
                                    type types-subscriber-mgmt:subscriber-id;
                                    description "Subscriber ID for sending ICMP Echo Request packets";
                                }

                            }
                        }
                        leaf router-instance {
                            type string;
                            default "Base";
                            description "Router name or VPRN service name";
                        }

                        leaf source-address {
                            type types-sros:ip-address;
                            description "Source IP address used in the ICMP Echo Request packet";
                        }

                    }
                    case case-srv6-policy {

                        leaf srv6-policy {
                            type empty;
                            mandatory true;
                            description "Ping a Segment Routing IPv6 policy";
                        }

                        leaf color {
                            type uint32;
                            mandatory true;
                            description "Color identifier of the Segment Routing IPv6 policy";
                        }

                        leaf endpoint {
                            type types-sros:ipv6-unicast-or-zero-address;
                            mandatory true;
                            description "Endpoint identifier of the Segment Routing IPv6 policy to be pinged";
                        }

                        leaf segment-list {
                            type uint32 {
                                range "1..32";
                            }
                            description "Segment Routing IPv6 segment list to be pinged";
                        }

                        choice choice-candidate-path {
                            case case-candidate-path {

                                leaf candidate-path {
                                    type empty;
                                    mandatory true;
                                    description "Ping candidate path of the SRv6 policy";
                                }

                                leaf protocol-owner {
                                    type enumeration {
                                        enum bgp                            { value 1; }
                                        enum static                         { value 2; }
                                    }
                                    mandatory true;
                                    description "Protocol owner";
                                }

                                leaf preference {
                                    type uint32;
                                    default "100";
                                    description "SRv6 policy candidate path preference";
                                }

                                leaf distinguisher {
                                    type uint32 {
                                        range "1..4294967295";
                                    }
                                    description "SRv6 policy candidate path distinguisher";
                                }

                            }
                        }
                    }
                }
                leaf count {
                    type uint32 {
                        range "1..100000";
                    }
                    units "packets";
                    default "5";
                    description "Number of ping requests to send to the remote host";
                }

                leaf output-format {
                    type enumeration {
                        enum summary                        { value 1; }
                        enum detail                         { value 2; }
                    }
                    default "detail";
                    description "Output format";
                }

                leaf do-not-fragment {
                    type empty;
                    description "Do not fragment the request frame";
                }

                leaf fc {
                    type types-sros:fc-name;
                    default "nc";
                    description "Forwarding class option for the transmitted packet";
                }

                leaf interval {
                    type union {
                        type uint32 {
                            range "1..10000";
                        }
                        type decimal64 {
                            range "0.01..100.00";
                            fraction-digits 2;
                        }
                    }
                    units "seconds";
                    default "1";
                    description "Time between consecutive ping requests";
                }

                leaf pattern {
                    type union {
                        type enumeration {
                            enum sequential                     { value -1; }
                        }
                        type int32 {
                            range "0..65535";
                        }
                    }
                    default "sequential";
                    description "Pattern string to include in the packet";
                }

                leaf size {
                    type uint32 {
                        range "0..16384";
                    }
                    units "bytes";
                    default "56";
                    description "Request packet size including ICMP header and payload";
                }

                leaf timeout {
                    type uint32 {
                        range "1..10";
                    }
                    units "seconds";
                    default "5";
                    description "Wait time for the ICMP Echo Reply packet";
                }

                leaf tos {
                    type uint32 {
                        range "0..255";
                    }
                    default "0";
                    description "Type of Service (ToS) bits in the IP header";
                }

                leaf ttl {
                    type uint32 {
                        range "1..128";
                    }
                    default "64";
                    description "Time to Live (TTL) included in the request packet";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                container results {
                    description "Enter the results context";

                    container test-parameters {
                        description "Enter the test-parameters context";

                        choice ping-type {
                            case case-ip-or-dns {

                                leaf destination {
                                    type union {
                                        type types-sros:ip-address-with-zone;
                                        type types-sros:string-not-all-spaces {
                                            length "1..128";
                                        }
                                    }
                                    description "IP address or DNS name that was pinged.";
                                }

                                choice routing-options {
                                    case case-bypass-routing {

                                        leaf bypass-routing {
                                            type boolean;
                                            description
                                                "Bypass the routing table when sending to a host on a directly attached
                                                 network.";
                                        }

                                    }
                                    case case-interface {

                                        leaf interface {
                                            type types-sros:interface-name;
                                            description "Sending interface for the ICMP Echo Request packet(s).";
                                        }

                                    }
                                    case case-next-hop {

                                        leaf next-hop-address {
                                            type types-sros:ip-address;
                                            description "Next hop IP address used when sending ICMP Echo Request packet(s).";
                                        }

                                    }
                                    case case-subscriber {

                                        leaf subscriber {
                                            type types-subscriber-mgmt:subscriber-id;
                                            description "Subscriber-id used when sending ICMP Echo Request packet(s).";
                                        }

                                    }
                                }
                                leaf router-instance {
                                    type types-sros:router-instance-base-management-vprn-loose;
                                    description "Router used for the test ('Base', 'management', 'vpls-management', or a VPRN service name).";
                                }

                                leaf source-address {
                                    type types-sros:ip-address;
                                    description
                                        "Source IP address that was loaded into the IP header of the ICMP Echo
                                         Request packet(s).";
                                }

                            }
                            case case-srv6-policy {

                                leaf srv6-policy {
                                    type boolean;
                                    description "ping a Segment Routing IPv6 policy";
                                }

                                leaf color {
                                    type uint32;
                                    description "Color identifier of the pinged Segment Routing IPv6 policy";
                                }

                                leaf endpoint {
                                    type types-sros:ipv6-unicast-or-zero-address;
                                    description "Endpoint identifier of the pinged Segment Routing IPv6 policy";
                                }

                                leaf segment-list {
                                    type uint32 {
                                        range "0..32";
                                    }
                                    description "Segment list of the pinged Segment Routing IPv6 policy.  Unspecified: system-selected segment list.";
                                }

                                choice choice-candidate-path {
                                    case case-candidate-path {

                                        leaf candidate-path {
                                            type boolean;
                                            description "Ping a Segment Routing IPv6 policy candidate path";
                                        }

                                        leaf protocol-owner {
                                            type enumeration {
                                                enum none                           { value 0; }
                                                enum bgp                            { value 1; }
                                                enum static                         { value 2; }
                                            }
                                            description "The owner of the pinged SRv6 policy candidate path";
                                        }

                                        leaf preference {
                                            type uint32;
                                            description "Preference identifier of the pinged SRv6 policy candidate path";
                                        }

                                        leaf distinguisher {
                                            type uint32;
                                            description "Route distinguisher of the pinged SRv6 policy candidate path";
                                        }

                                    }
                                }
                            }
                        }
                        leaf count {
                            type uint32 {
                                range "1..100000";
                            }
                            units "packets";
                            description "Number of ICMP Echo Request packet(s) sent.";
                        }

                        leaf output-format {
                            type enumeration {
                                enum summary                        { value 1; }
                                enum detail                         { value 2; }
                            }
                            description
                                "If detail output was active, extra information was returned in error
                                 cases";
                        }

                        leaf do-not-fragment {
                            type boolean;
                            description
                                "ICMP Echo Request packet(s) were not allowed to be fragmented (valid for
                                 IPv4 only).";
                        }

                        leaf fc {
                            type types-sros:fc-name;
                            description "Forwarding Class for the transmitted ICMP Echo Request packet(s).";
                        }

                        leaf interval {
                            type union {
                                type uint32 {
                                    range "1..10000";
                                }
                                type decimal64 {
                                    range "0.01..100.00";
                                    fraction-digits 2;
                                }
                            }
                            units "seconds";
                            description "Interval between ICMP Echo Request packets sent.";
                        }

                        leaf pattern {
                            type union {
                                type enumeration {
                                    enum sequential                     { value -1; }
                                }
                                type int32 {
                                    range "0..65535";
                                }
                            }
                            description
                                "Two byte value used to pad the ICMP Echo Request packet(s). 'sequential'
                                 indicates bytes increasing by one.";
                        }

                        leaf size {
                            type uint32 {
                                range "0..16384";
                            }
                            units "bytes";
                            description
                                "Number of bytes in the combined ICMP Header (8 bytes) and ICMP Payload
                                 (variable size) of the ICMP Echo Request packet(s).";
                        }

                        leaf timeout {
                            type uint32 {
                                range "1..10";
                            }
                            units "seconds";
                            description
                                "Maximum time (in seconds) that was allowed for ICMP Echo Reply packet(s).
                                 The timer was started when the last ICMP Echo Request was sent.";
                        }

                        leaf tos {
                            type uint32 {
                                range "0..255";
                            }
                            description
                                "Type of Service value to be loaded into the DSCP and ECN fields of the IP
                                 header of the ICMP Echo Request packet(s).";
                        }

                        leaf ttl {
                            type uint32 {
                                range "1..128";
                            }
                            description
                                "Time To Live value (IPv4) or Hop Limit value (IPv6) to be loaded into the
                                 IP header of the ICMP Echo Request packet(s).";
                        }

                    } // container test-parameters

                    list probe {
                        key "probe-index";
                        description "Probe data for the specified test run.";

                        leaf probe-index {
                            type uint32 {
                                range "1..max";
                            }
                            description "Index of probes with the specified test run.";
                        }

                        leaf status {
                            type types-oam:response-status;
                            description "The OAM response status code for the specified test.";
                        }

                        leaf round-trip-time {
                            type uint32;
                            units "microseconds";
                            description "Indicates the round trip time for the specified probe.";
                        }

                        container response-packet {
                            description "Data from packet received as a response to transmitted probe.";

                            leaf size {
                                type uint32;
                                units "bytes";
                                description
                                    "Indicates the number of bytes in the response packet for the specified
                                     probe.";
                            }

                            leaf source-address {
                                type types-sros:ip-address-with-zone;
                                description
                                    "Indicates the source address in the response packet for the specified
                                     probe.";
                            }

                            leaf icmp-sequence-number {
                                type uint32;
                                description
                                    "Indicates the ICMP sequence number in the response packet for the
                                     specified probe.";
                            }

                            leaf ttl {
                                type uint32;
                                description
                                    "Indicates the time to live in the response packet for the specified
                                     probe.";
                            }

                        } // container response-packet

                    } // list probe

                    container summary {
                        description "Test run summary data.";

                        container statistics {
                            description "Test run summary statistics.";

                            container packets {
                                description "Packet statistics for the specified test run.";

                                leaf sent {
                                    type uint32;
                                    units "packets";
                                    description "Indicates the number of packets sent for the specified test run.";
                                }

                                leaf received {
                                    type uint32;
                                    units "packets";
                                    description "Indicates the number of packets received for the specified test run.";
                                }

                                leaf loss {
                                    type decimal64 {
                                        range "0.00..100.00";
                                        fraction-digits 2;
                                    }
                                    units "percent";
                                    description
                                        "Indicates the number of packet loss percentage for the specified test
                                         run.";
                                }

                            } // container packets

                            container round-trip-time {
                                description "Test run round trip time statistics.";

                                leaf minimum {
                                    type uint32;
                                    units "microseconds";
                                    description "Indicates the minimum round trip time for the specified test run.";
                                }

                                leaf average {
                                    type uint32;
                                    units "microseconds";
                                    description "Indicates the average round trip time for the specified test run.";
                                }

                                leaf maximum {
                                    type uint32;
                                    units "microseconds";
                                    description "Indicates the maximum round trip time for the specified test run.";
                                }

                                leaf standard-deviation {
                                    type uint32;
                                    units "microseconds";
                                    description
                                        "Indicates the standard deviation for the round trip times for the
                                         specified test run.";
                                }

                            } // container round-trip-time

                        } // container statistics

                    } // container summary

                } // container results

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action ping

        action pyexec {
            description "Perform pyexec action";

            input {

                leaf url {
                    type union {
                        type string;
                        type types-sros:local-file-url;
                        type types-sros:ftp-url;
                    }
                    mandatory true;
                    description "The name of python script policy or location of the script to be executed.";
                }

                leaf argument-01 {
                    type string;
                    description "First argument.";
                }

                leaf argument-02 {
                    type string;
                    description "Second argument.";
                }

                leaf argument-03 {
                    type string;
                    description "Third argument.";
                }

                leaf argument-04 {
                    type string;
                    description "Fourth argument.";
                }

                leaf argument-05 {
                    type string;
                    description "Fifth argument.";
                }

                leaf argument-06 {
                    type string;
                    description "Sixth argument.";
                }

                leaf argument-07 {
                    type string;
                    description "Seventh argument.";
                }

                leaf argument-08 {
                    type string;
                    description "Eight argument.";
                }

                leaf argument-09 {
                    type string;
                    description "Ninth argument.";
                }

                leaf argument-10 {
                    type string;
                    description "Tenth argument.";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                container results {
                    description "Pyexec action results";

                    leaf pyexec-output-block {
                        type string;
                        description "Standard output of executed Python script.";
                    }

                } // container results

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action pyexec

        action traceroute {
            description "Trigger traceroute via machine interface";

            input {

                choice traceroute-type {
                    mandatory true;
                    case case-ip-or-dns {

                        leaf destination {
                            type union {
                                type types-sros:ip-unicast-address;
                                type types-sros:string-not-all-spaces {
                                    length "1..128";
                                }
                            }
                            mandatory true;
                            description "Destination IP address or DNS name";
                        }

                        leaf router-instance {
                            type string;
                            default "Base";
                            description "Router name or VPRN service name";
                        }

                        leaf source-address {
                            type types-sros:ip-address;
                            description "Source address of the probe packets";
                        }

                    }
                    case case-srv6-policy {

                        leaf srv6-policy {
                            type empty;
                            mandatory true;
                            description "Trace an SRv6 policy";
                        }

                        leaf color {
                            type uint32;
                            mandatory true;
                            description "Color ID of the SRv6 policy to trace";
                        }

                        leaf endpoint {
                            type types-sros:ipv6-unicast-or-zero-address;
                            mandatory true;
                            description "Endpoint of the SRv6 policy to trace";
                        }

                        leaf segment-list {
                            type uint32 {
                                range "1..32";
                            }
                            description "SR IPv6 segment list to trace";
                        }

                        choice choice-candidate-path {
                            case case-candidate-path {

                                leaf candidate-path {
                                    type empty;
                                    mandatory true;
                                    description "Trace route of the candidate path of the SRv6 policy";
                                }

                                leaf protocol-owner {
                                    type enumeration {
                                        enum bgp                            { value 1; }
                                        enum static                         { value 2; }
                                    }
                                    mandatory true;
                                    description "Protocol owner";
                                }

                                leaf preference {
                                    type uint32;
                                    default "100";
                                    description "SRv6 policy candidate path preference";
                                }

                                leaf distinguisher {
                                    type uint32 {
                                        range "1..4294967295";
                                    }
                                    description "SRv6 policy candidate path distinguisher";
                                }

                            }
                        }
                    }
                }
                leaf decode {
                    type enumeration {
                        enum none                           { value 0; }
                        enum original-datagram              { value 1; }
                    }
                    default "none";
                    description "Perform original datagram parsing functions";
                }

                leaf dest-port {
                    type uint32 {
                        range "1..65535";
                    }
                    default "33434";
                    description "Transport protocol destination port number";
                }

                leaf dest-port-udp-fixed {
                    type empty;
                    description "Avoid increment of destination port number for UDP test";
                }

                leaf detail {
                    type empty;
                    description "Display MPLS label stack information or TCP port status";
                }

                leaf min-ttl {
                    type uint32 {
                        range "1..255";
                    }
                    default "1";
                    description "First hop traceroute probes using the TTL value";
                }

                leaf ttl {
                    type uint32 {
                        range "1..255";
                    }
                    default "30";
                    description "Maximum number of hops (TTL) to probe";
                }

                leaf numeric {
                    type empty;
                    description "Display IP addresses instead of DNS names";
                }

                leaf probe-count {
                    type uint32 {
                        range "1..10";
                    }
                    default "3";
                    description "Number of probes to send per hop";
                }

                leaf protocol {
                    type enumeration {
                        enum udp                            { value 1; }
                        enum tcp                            { value 2; }
                    }
                    default "udp";
                    description "Packet type to send";
                }

                leaf size {
                    type uint32 {
                        range "0..9786";
                    }
                    units "bytes";
                    default "0";
                    description "Number of pad bytes in each transmitted packet";
                }

                leaf tos {
                    type uint32 {
                        range "0..255";
                    }
                    default "0";
                    description "Type of Service (ToS) bits in the IP header";
                }

                leaf wait {
                    type uint32 {
                        range "10..60000";
                    }
                    units "milliseconds";
                    default "5000";
                    description "Time to wait for a response to the probe";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                container results {
                    description "Enter the results context";

                    container test-parameters {
                        description "Enter the test-parameters context";

                        choice traceroute-type {
                            case case-ip-or-dns {

                                leaf destination {
                                    type union {
                                        type types-sros:ip-address;
                                        type types-sros:string-not-all-spaces {
                                            length "1..128";
                                        }
                                    }
                                    description "The destination IP address or DNS name";
                                }

                                leaf router-instance {
                                    type types-sros:router-instance-base-management-vprn-loose;
                                    description "Router instance used for the traceroute (i.e. 'Base', 'management', 'vpls-management' or a VPRN service name)";
                                }

                                leaf source-address {
                                    type types-sros:ip-address;
                                    description "The IP source address to use for the test";
                                }

                            }
                            case case-srv6-policy {

                                leaf srv6-policy {
                                    type boolean;
                                    description "Trace a Segment Routing IPv6 policy";
                                }

                                leaf color {
                                    type uint32;
                                    description "Color identifier of the traced Segment Routing IPv6 policy";
                                }

                                leaf endpoint {
                                    type types-sros:ipv6-unicast-or-zero-address;
                                    description "Endpoint identifier of the traced Segment Routing IPv6 policy";
                                }

                                leaf segment-list {
                                    type uint32 {
                                        range "0..32";
                                    }
                                    description "The segment list of the traced Segment Routing IPv6 policy";
                                }

                                choice choice-candidate-path {
                                    case case-candidate-path {

                                        leaf candidate-path {
                                            type boolean;
                                            description "Trace a Segment Routing IPv6 policy candidate path";
                                        }

                                        leaf protocol-owner {
                                            type enumeration {
                                                enum none                           { value 0; }
                                                enum bgp                            { value 1; }
                                                enum static                         { value 2; }
                                            }
                                            description "The owner of the traced SRv6 policy candidate path";
                                        }

                                        leaf preference {
                                            type uint32;
                                            description "Preference identifier of the traced SRv6 policy candidate path";
                                        }

                                        leaf distinguisher {
                                            type uint32;
                                            description "Route distinguisher of the traced SRv6 policy candidate path";
                                        }

                                    }
                                }
                            }
                        }
                        leaf decode {
                            type enumeration {
                                enum none                           { value 0; }
                                enum original-datagram              { value 1; }
                            }
                            description "Decode and display additional fields in replies received";
                        }

                        leaf dest-port {
                            type uint32 {
                                range "1..65535";
                            }
                            description
                                "For a TCP test, the destination TCP port number to send.
                                 For a UDP test, the base or only destination UDP port number to send (see dest-port-udp-fixed)";
                        }

                        leaf dest-port-udp-fixed {
                            type boolean;
                            description
                                "For a UDP test, 'true' uses the same destination UDP port number in each
                                 transmitted packet (i.e. the port number is not incremented)";
                        }

                        leaf detail {
                            type boolean;
                            description "Display MPLS label stack information (if available)";
                        }

                        leaf min-ttl {
                            type uint32 {
                                range "1..255";
                            }
                            description "The minimum number of hops to probe";
                        }

                        leaf ttl {
                            type uint32 {
                                range "1..255";
                            }
                            description "The maximum number of hops to probe";
                        }

                        leaf numeric {
                            type boolean;
                            description "'true' avoids looking up DNS names when displaying results";
                        }

                        leaf probe-count {
                            type uint32 {
                                range "1..10";
                            }
                            description "The number of probes to send per hop";
                        }

                        leaf protocol {
                            type enumeration {
                                enum udp                            { value 1; }
                                enum tcp                            { value 2; }
                            }
                            description "Send UDP packets or TCP-SYN packets";
                        }

                        leaf size {
                            type uint32 {
                                range "0..9786";
                            }
                            units "bytes";
                            description "The number of pad bytes in each transmitted packet";
                        }

                        leaf tos {
                            type uint32 {
                                range "0..255";
                            }
                            description "The IPv4 Type of Service or IPv6 Traffic Class in each transmitted packet";
                        }

                        leaf wait {
                            type uint32 {
                                range "10..60000";
                            }
                            units "milliseconds";
                            description "The time (in milliseconds) to wait for a response to a packet";
                        }

                    } // container test-parameters

                    list hop {
                        key "hop-index";
                        description "Per-hop (also known as per-TTL) test results";

                        leaf hop-index {
                            type uint32 {
                                range "1..max";
                            }
                            description "The hop index of the test results";
                        }

                        list probe {
                            key "probe-index";
                            description "Per-probe test results";

                            leaf probe-index {
                                type uint32 {
                                    range "1..max";
                                }
                                description "Index of the probe within the specified hop for the test";
                            }

                            leaf status {
                                type types-oam:response-status;
                                description "The status of the probe (e.g. response-received, request-timed-out)";
                            }

                            leaf round-trip-time {
                                type uint32;
                                units "microseconds";
                                description "The round trip time for the specified probe and response";
                            }

                            leaf size {
                                type uint32;
                                units "bytes";
                                description "The number of bytes in the transmitted packet (zero if no packet was sent)";
                            }

                            container response-packet {
                                description "Test results copied (or derived) from a response packet";

                                leaf icmp-type {
                                    type uint32 {
                                        range "0..255";
                                    }
                                    description
                                        "The ICMP or ICMPv6 Type in the received response.
                                         icmp-type = 0 AND icmp-code = 0 indicates no Type and Code
                                         is available";
                                }

                                leaf icmp-code {
                                    type uint32 {
                                        range "0..255";
                                    }
                                    description
                                        "The ICMP or ICMPv6 Code in the received response.
                                         icmp-type = 0 AND icmp-code = 0 indicates no Type and Code
                                         is available";
                                }

                                leaf mtu-exceeded {
                                    type uint32;
                                    units "bytes";
                                    description
                                        "The MTU (Maximum Transmission Unit) in the received response.
                                         When the MTU is non-zero, it indicates the MTU exceeded by
                                         a transmitted packet .";
                                }

                                leaf source-address {
                                    type types-sros:ip-address;
                                    description
                                        "The IP source address in the response packet (i.e. the address of the
                                         replying node)";
                                }

                                leaf source-host-name {
                                    type string {
                                        length "0..255";
                                    }
                                    description "The host name looked up (in DNS) using the IP address of the replying node";
                                }

                                leaf tcp-port-status {
                                    type enumeration {
                                        enum none                           { value 1; }
                                        enum tcp-port-open                  { value 2; }
                                        enum tcp-port-closed                { value 3; }
                                    }
                                    description
                                        "The operational state of the probed TCP port on the
                                         test's destination node. 'none' is returned if the test's protocol
                                         is UDP, or the replying node is not the test's destination";
                                }

                                list mpls-label-stack-entry {
                                    key "index";
                                    description "The information read from an RFC 4950 MPLS Label Stack Object in the response packet";

                                    leaf index {
                                        type uint32 {
                                            range "1..max";
                                        }
                                        description "Index of an RFC 4950 MPLS Label Stack Entry within the MPLS Label Stack Object";
                                    }

                                    leaf label {
                                        type types-sros:mpls-label-full-range;
                                        description "The Label field within the specified RFC 4950 MPLS Label Stack Entry";
                                    }

                                    leaf traffic-class {
                                        type uint32 {
                                            range "0..7";
                                        }
                                        description "The Experimental field within the specified RFC 4950 MPLS Label Stack Entry (subsequently renamed to Traffic Class)";
                                    }

                                    leaf bottom-of-stack {
                                        type uint32 {
                                            range "0..1";
                                        }
                                        description "The Bottom of Stack field within the specified RFC 4950 MPLS Label Stack Entry";
                                    }

                                    leaf ttl {
                                        type uint32 {
                                            range "0..255";
                                        }
                                        description "The TTL field within the specified RFC 4950 MPLS Label Stack Entry";
                                    }

                                } // list mpls-label-stack-entry

                                container original-datagram {
                                    description "Information copied from the Original Datagram field within the ICMPv6 response packet";

                                    list header {
                                        key "header-index";
                                        description "information copied from the headers within the Original Datagram field within the ICMPv6 response packet";

                                        leaf header-index {
                                            type uint32 {
                                                range "1..max";
                                            }
                                            description "The sequence number of the header within the Original Datagram field within the ICMPv6 response packet";
                                        }

                                        choice header-type-choice {
                                            case ipv6-case {

                                                container ipv6-header {
                                                    description "An IPv6 header within the Original Datagram field within the ICMPv6 response packet";

                                                    leaf destination-address {
                                                        type types-sros:ip-address;
                                                        description "The destination address field within the IPv6 header within the Original Datagram field within the ICMPv6 response packet";
                                                    }

                                                    leaf dscp {
                                                        type types-sros:named-item-or-empty;
                                                        description "The Differentiated Services Code Point (DSCP) field within the IPv6 header within the Original Datagram field within the ICMPv6 response packet";
                                                    }

                                                    leaf hop-limit {
                                                        type uint32 {
                                                            range "0..255";
                                                        }
                                                        description "The Hop Limit field within the IPv6 header within the Original Datagram field within the ICMPv6 response packet";
                                                    }

                                                    leaf source-address {
                                                        type types-sros:ip-address;
                                                        description "The source address field within the IPv6 header within the Original Datagram field within the ICMPv6 response packet";
                                                    }

                                                } // container ipv6-header

                                            }
                                            case srv6-case {

                                                container srv6-header {
                                                    description "An SRv6 header within the Original Datagram field within the ICMPv6 response packet";

                                                    leaf segments-left {
                                                        type uint32 {
                                                            range "0..255";
                                                        }
                                                        description "The Segments Left field within the SRv6 header within the Original Datagram field within the ICMPv6 response packet";
                                                    }

                                                    list segment-list {
                                                        key "segment-index";
                                                        description "Segment List addresses copied from the SRv6 header within the Original Datagram field within the ICMPv6 response packet";

                                                        leaf segment-index {
                                                            type uint32;
                                                            description "The sequence number of the Segment address within the SRv6 header within the Original Datagram field within the ICMPv6 response packet";
                                                        }

                                                        leaf segment-address {
                                                            type types-sros:ip-address;
                                                            description "A Segment address within the SRv6 header within the Original Datagram field within the ICMPv6 response packet";
                                                        }

                                                    } // list segment-list

                                                } // container srv6-header

                                            }
                                        }
                                    } // list header

                                } // container original-datagram

                            } // container response-packet

                        } // list probe

                    } // list hop

                } // container results

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action traceroute

    } // container global-operations

}
