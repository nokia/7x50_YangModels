module nokia-sr-openconfig-bfd-deviations {

    namespace "urn:nokia.com:sros:ns:yang:sr:openconfig-bfd-deviations";

    prefix "nokia-oc-bfd-devs";

    import nokia-sros-yang-extensions     { prefix "sros-ext"; }
    import openconfig-bfd                 { prefix "oc-bfd"; }
    import openconfig-extensions          { prefix "oc-ext"; }
    import openconfig-if-types            { prefix "oc-ift"; }
    import openconfig-inet-types          { prefix "oc-inet"; }
    import openconfig-interfaces          { prefix "oc-if"; }
    import openconfig-policy-types        { prefix "oc-pol-types"; }
    import openconfig-types               { prefix "oc-types"; }

    sros-ext:sros-major-release "rel23";
    organization "Nokia";
    contact
        "Nokia SR OS Support
         Web: <http://www.nokia.com>";
    description
        "This module contains the list of deviations against the openconfig-bfd
          module for the Nokia SR OS based routers.

         Copyright 2016 Nokia. All rights reserved. Reproduction of this document
         is authorized on the condition that the foregoing copyright notice is included.

         This nokia-sr-openconfig-bfd-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-03-17";

    deviation /oc-bfd:bfd/oc-bfd:interfaces/oc-bfd:interface/oc-bfd:config/oc-bfd:enabled {
        deviate add {
            default "false";
        }
    }

    deviation /oc-bfd:bfd/oc-bfd:interfaces/oc-bfd:interface/oc-bfd:config/oc-bfd:local-address {
        deviate not-supported;
    }

    deviation /oc-bfd:bfd/oc-bfd:interfaces/oc-bfd:interface/oc-bfd:config/oc-bfd:desired-minimum-tx-interval {
        deviate replace {
            type uint32 {
                range "10000..100000000";
            }
        }
        deviate add {
            default "100000";
        }
    }

    deviation /oc-bfd:bfd/oc-bfd:interfaces/oc-bfd:interface/oc-bfd:config/oc-bfd:required-minimum-receive {
        deviate replace {
            type uint32 {
                range "10000..100000000";
            }
        }
        deviate add {
            default "100000";
        }
    }

    deviation /oc-bfd:bfd/oc-bfd:interfaces/oc-bfd:interface/oc-bfd:config/oc-bfd:detection-multiplier {
        deviate replace {
            type uint16 {
                range "1..20";
            }
        }
        deviate add {
            default "3";
        }
    }

    deviation /oc-bfd:bfd/oc-bfd:interfaces/oc-bfd:interface/oc-bfd:state/oc-bfd:enabled {
        deviate add {
            default "false";
        }
    }

    deviation /oc-bfd:bfd/oc-bfd:interfaces/oc-bfd:interface/oc-bfd:state/oc-bfd:local-address {
        deviate not-supported;
    }

    deviation /oc-bfd:bfd/oc-bfd:interfaces/oc-bfd:interface/oc-bfd:state/oc-bfd:desired-minimum-tx-interval {
        deviate replace {
            type uint32 {
                range "10000..100000000";
            }
        }
        deviate add {
            default "100000";
        }
    }

    deviation /oc-bfd:bfd/oc-bfd:interfaces/oc-bfd:interface/oc-bfd:state/oc-bfd:required-minimum-receive {
        deviate replace {
            type uint32 {
                range "10000..100000000";
            }
        }
        deviate add {
            default "100000";
        }
    }

    deviation /oc-bfd:bfd/oc-bfd:interfaces/oc-bfd:interface/oc-bfd:state/oc-bfd:detection-multiplier {
        deviate replace {
            type uint16 {
                range "1..20";
            }
        }
        deviate add {
            default "3";
        }
    }

    deviation /oc-bfd:bfd/oc-bfd:interfaces/oc-bfd:interface/oc-bfd:interface-ref/oc-bfd:config {
        deviate delete {
            oc-ext:telemetry-on-change;
        }
    }

    deviation /oc-bfd:bfd/oc-bfd:interfaces/oc-bfd:interface/oc-bfd:micro-bfd-sessions/oc-bfd:micro-bfd-session/oc-bfd:state/oc-bfd:remote-authentication-enabled {
        deviate not-supported;
    }

    deviation /oc-bfd:bfd/oc-bfd:interfaces/oc-bfd:interface/oc-bfd:peers/oc-bfd:peer/oc-bfd:state/oc-bfd:remote-authentication-enabled {
        deviate not-supported;
    }

}
