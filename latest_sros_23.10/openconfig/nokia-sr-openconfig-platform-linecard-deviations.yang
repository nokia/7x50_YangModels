module nokia-sr-openconfig-platform-linecard-deviations {

    namespace "urn:nokia.com:sros:ns:yang:sr:openconfig-platform-linecard-deviations";

    prefix "nokia-oc-linecard-devs";

    import nokia-sros-yang-extensions     { prefix "sros-ext"; }
    import openconfig-extensions          { prefix "oc-ext"; }
    import openconfig-platform            { prefix "oc-platform"; }
    import openconfig-platform-linecard   { prefix "oc-linecard"; }
    import openconfig-platform-types      { prefix "oc-platform-types"; }

    sros-ext:sros-major-release "rel23";
    organization "Nokia";
    contact
        "Nokia SR OS Support
         Web: <http://www.nokia.com>";
    description
        "This module contains the list of deviations against the openconfig-platform-linecard
          module for the Nokia SR OS based routers.

         Copyright 2016 Nokia. All rights reserved. Reproduction of this document
         is authorized on the condition that the foregoing copyright notice is included.

         This nokia-sr-openconfig-platform-linecard-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-05-10";

    deviation /oc-platform:components/oc-platform:component/oc-linecard:linecard/oc-linecard:config {
        deviate not-supported;
    }

    deviation /oc-platform:components/oc-platform:component/oc-linecard:linecard {
        deviate replace {
            config false;
        }
    }

}
