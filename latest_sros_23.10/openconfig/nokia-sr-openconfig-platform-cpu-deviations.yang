module nokia-sr-openconfig-platform-cpu-deviations {

    namespace "urn:nokia.com:sros:ns:yang:sr:openconfig-platform-cpu-deviations";

    prefix "nokia-oc-cpu-devs";

    import nokia-sros-yang-extensions     { prefix "sros-ext"; }
    import openconfig-extensions          { prefix "oc-ext"; }
    import openconfig-platform            { prefix "oc-platform"; }
    import openconfig-platform-cpu        { prefix "oc-cpu"; }
    import openconfig-system              { prefix "oc-sys"; }
    import openconfig-types               { prefix "oc-types"; }

    sros-ext:sros-major-release "rel23";
    organization "Nokia";
    contact
        "Nokia SR OS Support
         Web: <http://www.nokia.com>";
    description
        "This module contains the list of deviations against the openconfig-platform-cpu
          module for the Nokia SR OS based routers.

         Copyright 2016 Nokia. All rights reserved. Reproduction of this document
         is authorized on the condition that the foregoing copyright notice is included.

         This nokia-sr-openconfig-platform-cpu-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2018-11-21";





    deviation /oc-platform:components/oc-platform:component/oc-platform:cpu/oc-cpu:utilization {
        deviate not-supported;
    }

}
