module nokia-types-redundancy {

    yang-version "1.1";

    namespace "urn:nokia.com:sros:ns:yang:sr:types-redundancy";

    prefix "types-redundancy";

    import ietf-yang-types                { prefix "yang"; }
    import nokia-sros-yang-extensions     { prefix "sros-ext"; }

    sros-ext:sros-major-release "rel23";
    organization "Nokia";
    contact
        "Nokia SR OS Support
         Web: <http://www.nokia.com>";
    description
        "Common redundancy types data types used in the SR OS management system.

         Copyright 2016 Nokia. All rights reserved. Reproduction of this document
         is authorized on the condition that the foregoing copyright notice is included.

         This nokia-types-redundancy YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-08-18";

    typedef tunnel-group-id {
        type uint32 {
            range "1..64";
        }
        description "The identification number of a tunnel group.";
    }

    typedef tunnel-group-master-state {
        type enumeration {
            enum discovery {
                value 1;
                description "No election during initial peer discovery interval.";
            }
            enum not-eligible {
                value 2;
                description "No election, and not eligible for mastership.";
            }
            enum eligible {
                value 3;
                description "No election, but eligible for mastership.";
            }
            enum standby {
                value 4;
                description "Elected standby.";
            }
            enum master {
                value 5;
                description "Elected master.";
            }
        }
        description
            "Indicates the result of the mastership election between
             this tunnel group entity and its peer.";
    }

    typedef mc-ipsec-activity-state {
        type enumeration {
            enum discovery {
                value 1;
                description "No election during initial peer discovery interval.";
            }
            enum not-eligible {
                value 2;
                description "No election, and not eligible to be active.";
            }
            enum eligible {
                value 3;
                description "No election, but eligible to be active.";
            }
            enum standby {
                value 4;
                description "Elected standby.";
            }
            enum active {
                value 5;
                description "Elected active.";
            }
            enum unkown {
                value 6;
                description "Domain adjacency peer is unreachable (not applicable to tunnel-groups or domains)";
            }
        }
        description
            "Indicates the result of the activity election between
             the local and remote multichassis IPsec entity.";
    }

    typedef tunnel-group-protection-status {
        type enumeration {
            enum nominal {
                value 1;
                description "Forcing a mastership switchover may impact traffic.";
            }
            enum not-ready {
                value 2;
                description "Forcing a mastership switchover may significantly impact traffic.";
            }
        }
        description
            "Indicates the readiness of the tunnel group to perform
             a forced switchover of mastership from the current
             master chassis to the standby chassis.";
    }

    typedef mc-application {
        type enumeration {
            enum igmp                           { value 0; }
            enum igmp-snooping                  { value 1; }
            enum sub-mgmt-ipoe                  { value 2; }
            enum srrp                           { value 3; }
            enum mc-ring                        { value 4; }
            enum mld-snooping                   { value 5; }
            enum dhcp-server                    { value 6; }
            enum sub-host-trk                   { value 7; }
            enum sub-mgmt-pppoe                 { value 8; }
            enum ipsec                          { value 9; }
            enum mld                            { value 10; }
            enum python                         { value 11; }
            enum l2tp                           { value 12; }
            enum diam-proxy                     { value 13; }
            enum pim-snpg-sap                   { value 14; }
            enum pim-snpg-sdp                   { value 15; }
            enum diam-node                      { value 16; }
            enum nat                            { value 17; }
            enum sub-mgmt-wlan-gw               { value 18; }
        }
        description "application that uses multi-chassis synchronization";
    }

    typedef sync-status {
        type enumeration {
            enum unknown                        { value 0; }
            enum fail                           { value 1; }
            enum in-progress                    { value 2; }
            enum success                        { value 3; }
        }
        description "The results of the synchronization operation.";
    }

    typedef date-and-time-or-never {
        type union {
            type enumeration {
                enum never                          { value -1; }
            }
            type yang:date-and-time;
        }
        default "never";
        description "Specifies date and time with possibility to get as never.";
    }

}
