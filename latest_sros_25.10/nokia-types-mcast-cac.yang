module nokia-types-mcast-cac {

    yang-version "1.1";

    namespace "urn:nokia.com:sros:ns:yang:sr:types-mcast-cac";

    prefix "types-mcast-cac";

    import nokia-sros-yang-extensions     { prefix "sros-ext"; }

    sros-ext:sros-major-release "rel25";
    organization "Nokia";
    contact
        "Nokia SR OS Support
         Web: <http://www.nokia.com>";
    description
        "Common MCAC data types used in the SR OS management system.

         Copyright 2016 Nokia. All rights reserved. Reproduction of this document
         is authorized on the condition that the foregoing copyright notice is included.

         This nokia-types-mcast-cac YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    typedef router-application {
        type enumeration {
            enum igmp                           { value 1; }
            enum pim                            { value 2; }
            enum mld                            { value 4; }
        }
        description ".";
    }

    typedef service-application {
        type enumeration {
            enum igmp-snooping                  { value 3; }
        }
        description ".";
    }

    typedef policy-action {
        type enumeration {
            enum accept                         { value 1; }
            enum discard                        { value 2; }
        }
    }

    typedef channel-type {
        type enumeration {
            enum optional                       { value 1; }
            enum mandatory                      { value 2; }
        }
    }

    typedef bandwidth-limit {
        type union {
            type int32 {
                range "0..max";
            }
            type enumeration {
                enum unlimited                      { value -1; }
            }
        }
        default "unlimited";
        description "Bandwidth limit, the value -1 means unlimited";
    }

    typedef bandwidth {
        type uint32;
        units "kilobps";
        description ".";
    }

    typedef constraints-level {
        type uint32 {
            range "1..8";
        }
    }

}
