submodule nokia-conf-routing-options {

    yang-version "1.1";

    belongs-to nokia-conf { prefix "conf"; }

    import nokia-sros-yang-extensions     { prefix "sros-ext"; }
    import nokia-types-sros               { prefix "types-sros"; }

    include nokia-conf-groups;

    sros-ext:sros-major-release "rel25";
    organization "Nokia";
    contact
        "Nokia SR OS Support
         Web: <http://www.nokia.com>";
    description
        "Nokia YANG Data model to configure routing options attributes on SR OS based routers.

         Copyright 2016 Nokia. All rights reserved. Reproduction of this document
         is authorized on the condition that the foregoing copyright notice is included.

         This nokia-conf-routing-options YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-08-12";

    grouping conf-routing-options {
        container routing-options {
            description "Enter the routing-options context";

            leaf ip-fast-reroute {
                type boolean;
                default "false";
                description "Enable IP fast reroute capability";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }


            container flexible-algorithm-definitions {
                description "Enter the flexible-algorithm-definitions context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list flex-algo {
                    key "flex-algo-name";
                    max-elements 256;
                    description "Enter the flex-algo list instance";

                    leaf flex-algo-name {
                        type types-sros:named-item;
                        description "Flexible Algorithm Definition (FAD) name";
                    }

                    leaf admin-state {
                        type types-sros:admin-state;
                        default "disable";
                        description "Administrative state of the FAD";
                    }

                    leaf description {
                        type types-sros:description;
                        description "Text description";
                    }

                    leaf flags-tlv {
                        type boolean;
                        sros-ext:auto-restart-to-modify;
                        default "true";
                        description "Advertise the FAD Flags TLV";
                    }

                    leaf metric-type {
                        type enumeration {
                            enum igp                            { value 0; }
                            enum delay                          { value 1; }
                            enum te-metric                      { value 2; }
                        }
                        sros-ext:auto-restart-to-modify;
                        default "igp";
                        description "FAD metric type";
                    }

                    leaf priority {
                        type int32 {
                            range "0..255";
                        }
                        sros-ext:auto-restart-to-modify;
                        default "100";
                        description "FAD priority";
                    }

                    leaf-list apply-groups {
                        type leafref {
                            path "../../../../groups/group/name";
                        }
                        max-elements 8;
                        ordered-by user;
                        sros-ext:auto-restart-to-modify;
                        description "Apply a configuration group at this level";
                    }

                    leaf-list apply-groups-exclude {
                        type leafref {
                            path "../../../../groups/group/name";
                        }
                        max-elements 8;
                        ordered-by user;
                        sros-ext:auto-restart-to-modify;
                        description "Exclude a configuration group at this level";
                    }

                    container exclude {
                        sros-ext:auto-restart-to-modify;
                        description "Enter the exclude context";

                        list admin-group {
                            key "group-name";
                            description "Add a list entry for admin-group";

                            leaf group-name {
                                type leafref {
                                    path "../../../../../if-attribute/admin-group/group-name";
                                }
                                description "Administrative group name";
                            }

                        } // list admin-group

                    } // container exclude

                    container include-any {
                        sros-ext:auto-restart-to-modify;
                        description "Enter the include-any context";

                        list admin-group {
                            key "group-name";
                            description "Add a list entry for admin-group";

                            leaf group-name {
                                type leafref {
                                    path "../../../../../if-attribute/admin-group/group-name";
                                }
                                description "Administrative group name";
                            }

                        } // list admin-group

                    } // container include-any

                    container include-all {
                        sros-ext:auto-restart-to-modify;
                        description "Enter the include-all context";

                        list admin-group {
                            key "group-name";
                            description "Add a list entry for admin-group";

                            leaf group-name {
                                type leafref {
                                    path "../../../../../if-attribute/admin-group/group-name";
                                }
                                description "Administrative group name";
                            }

                        } // list admin-group

                    } // container include-all


                } // list flex-algo

            } // container flexible-algorithm-definitions

            container if-attribute {
                description "Enter the if-attribute context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list admin-group {
                    key "group-name";
                    max-elements 256;
                    description "Enter the admin-group list instance";

                    leaf group-name {
                        type types-sros:named-item;
                        description "Interface group name";
                    }

                    leaf value {
                        type uint32 {
                            range "0..255";
                        }
                        sros-ext:immutable;
                        mandatory true;
                        description "Integer value associated with the group";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list admin-group

                list srlg-group {
                    key "name";
                    max-elements 1024;
                    description "Enter the srlg-group list instance";

                    leaf name {
                        type types-sros:named-item;
                        description "SRLG name";
                    }

                    leaf value {
                        type int64 {
                            range "0..4294967295";
                        }
                        sros-ext:immutable;
                        mandatory true;
                        description "Integer value associated with the SRLG";
                    }

                    leaf penalty-weight {
                        type uint32 {
                            range "0..65535";
                        }
                        default "0";
                        description "Integer value of the penalty weight assigned to SRLG";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list srlg-group

            } // container if-attribute

            container policy-accounting {
                description "Enter the policy-accounting context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list policy-acct-template {
                    key "name";
                    max-elements 1024;
                    description "Enter the policy-acct-template list instance";

                    leaf name {
                        type types-sros:named-item;
                        description "Policy accounting template name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list source-class {
                        key "index";
                        max-elements 255;
                        description "Add a list entry for source-class";

                        leaf index {
                            type types-sros:class-index;
                            description "Source-class index";
                        }

                    } // list source-class

                    list dest-class {
                        status obsolete;
                        key "index";
                        max-elements 255;
                        description "Enter the dest-class list instance";

                        leaf index {
                            status obsolete;
                            type types-sros:class-index;
                            description "Dest-class index to use with the template";
                        }

                        leaf policer {
                            status obsolete;
                            type leafref {
                                path "../../policer/policer-id";
                            }
                            description "Policer index to use with the template";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                    } // list dest-class

                    list destination-class {
                        key "index";
                        max-elements 255;
                        description "Enter the destination-class list instance";

                        leaf index {
                            type types-sros:class-index;
                            description "Destination class index";
                        }

                        leaf policer {
                            type leafref {
                                path "../../policer/policer-id";
                            }
                            description "Policer ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list destination-class

                    list policer {
                        key "policer-id";
                        description "Enter the policer list instance";

                        leaf policer-id {
                            type uint32 {
                                range "1..63";
                            }
                            description "Policer ID";
                        }

                        leaf peak-rate {
                            type union {
                                type int64 {
                                    range "1..6400000000";
                                }
                                type enumeration {
                                    enum max                            { value -1; }
                                }
                            }
                            default "max";
                            description "Peak rate of the policy accounting policer";
                        }

                        leaf max-burst-size {
                            type union {
                                type int32 {
                                    range "0..16777216";
                                }
                                type enumeration {
                                    enum auto                           { value -1; }
                                }
                            }
                            units "bytes";
                            default "auto";
                            description "Exceed threshold to drop packets from PIR leaky bucket";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list policer

                } // list policy-acct-template

            } // container policy-accounting

            container admin-tags {
                description "Enter the admin-tags context";

                list admin-tag {
                    key "tag";
                    max-elements 256;
                    description "Add a list entry for admin-tag";

                    leaf tag {
                        type string {
                            length "1..32";
                        }
                        description "Administrative tag value";
                    }

                } // list admin-tag

                list route-admin-tag-policy {
                    key "policy-name";
                    max-elements 2048;
                    description "Enter the route-admin-tag-policy list instance";

                    leaf policy-name {
                        type string {
                            length "1..64";
                        }
                        description "Name of the route admin tag policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list exclude {
                        key "tag";
                        max-elements 8;
                        description "Add a list entry for exclude";

                        leaf tag {
                            type leafref {
                                path "../../../admin-tag/tag";
                            }
                            description "Administrative tag value";
                        }

                    } // list exclude

                    list include {
                        key "tag";
                        max-elements 8;
                        description "Add a list entry for include";

                        leaf tag {
                            type leafref {
                                path "../../../admin-tag/tag";
                            }
                            description "Administrative tag value";
                        }

                    } // list include

                } // list route-admin-tag-policy

            } // container admin-tags

            container route-next-hop-policy {
                description "Enter the route-next-hop-policy context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list template {
                    key "template-name";
                    description "Enter the template list instance";

                    leaf template-name {
                        type types-sros:named-item;
                        description "Template name";
                    }

                    leaf description {
                        type types-sros:description;
                        description "Text description";
                    }

                    leaf srlg {
                        type boolean;
                        default "false";
                        description "Select next hops from the SRLG";
                    }

                    leaf nh-type {
                        type enumeration {
                            enum ip                             { value 1; }
                            enum tunnel                         { value 2; }
                        }
                        default "ip";
                        description "Preferred next hop";
                    }

                    leaf protection-type {
                        type enumeration {
                            enum link                           { value 1; }
                            enum node                           { value 2; }
                        }
                        default "node";
                        description "Protection type used";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list exclude-group {
                        key "group-name";
                        max-elements 32;
                        description "Add a list entry for exclude-group";

                        leaf group-name {
                            type leafref {
                                path "../../../../if-attribute/admin-group/group-name";
                            }
                            description "Administrative group name";
                        }

                    } // list exclude-group

                    list include-group {
                        key "group-name";
                        max-elements 32;
                        description "Enter the include-group list instance";

                        leaf group-name {
                            type leafref {
                                path "../../../../if-attribute/admin-group/group-name";
                            }
                            description "Administrative group name";
                        }

                        leaf preference {
                            type int32 {
                                range "1..255";
                            }
                            default "255";
                            description "Preference number for the admin group";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list include-group

                } // list template

            } // container route-next-hop-policy

        } // container routing-options

    } // grouping conf-routing-options

}
