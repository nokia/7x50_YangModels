submodule nokia-conf-submgt-wlangw {

    yang-version "1.1";

    belongs-to nokia-conf { prefix "conf"; }

    import nokia-sros-yang-extensions     { prefix "sros-ext"; }
    import nokia-types-isa                { prefix "types-isa"; }
    import nokia-types-nat                { prefix "types-nat"; }
    import nokia-types-sros               { prefix "types-sros"; }
    import nokia-types-wlangw             { prefix "types-wlangw"; }

    include nokia-conf-groups;

    sros-ext:sros-major-release "rel25";
    organization "Nokia";
    contact
        "Nokia SR OS Support
         Web: <http://www.nokia.com>";
    description
        "Nokia YANG Data model to configure subscriber management WLAN Gateway on SR OS based routers.

         Copyright 2016 Nokia. All rights reserved. Reproduction of this document
         is authorized on the condition that the foregoing copyright notice is included.

         This nokia-conf-submgt-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-08-12";

    grouping conf-submgt-wlangw-wlan-gw {
        container wlan-gw {
            description "Enter the wlan-gw context";

            leaf virtual-chassis-identifier {
                type types-sros:string-not-all-spaces {
                    length "1..16";
                }
                description "WLAN Gateway virtual chassis ID or dual homing key";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }


            container queries {
                description "Enter the queries context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list ue {
                    key "name";
                    max-elements 1024;
                    description "Enter the ue list instance";

                    leaf name {
                        type types-sros:named-item;
                        description "UE query name";
                    }

                    leaf bridge-domain {
                        type uint32 {
                            range "0..4294967294";
                        }
                        description "Bridge Domain to match for UEs";
                    }

                    leaf custom-user-group {
                        type types-sros:named-item-or-empty;
                        description "Name of the custom user group";
                    }

                    leaf mac-address {
                        type types-sros:mac-address;
                        description "MAC address to use for matching on UEs";
                    }

                    leaf vlan {
                        type types-sros:qtag-full-range;
                        description "VLAN tag within the tunnel to match for UEs";
                    }

                    leaf soft-quota-exhausted {
                        type boolean;
                        default "false";
                        description "Send interim update message when the quota is reached";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container address {
                        description "Enter the address context";

                        leaf type {
                            type types-wlangw:ue-address-type;
                            description "Address type to match for UEs";
                        }

                        leaf ipv4 {
                            type types-sros:ipv4-unicast-address;
                            description "IPv4 address to match for UEs";
                        }

                        leaf dhcp6-na {
                            type types-sros:ipv6-unicast-without-local-address;
                            description "DHCPv6 IA-NA address to match for UEs";
                        }

                        leaf slaac {
                            type types-sros:ipv6-unicast-without-local-address;
                            description "SLAAC prefix to match for UEs";
                        }

                    } // container address

                    container connection-state {
                        presence "Enable the connection-state context";
                        description "Enable the connection-state context";

                        leaf data-triggered {
                            type boolean;
                            default "true";
                            description "Enable matching on UEs in a data-triggered state";
                        }

                        leaf dhcp-triggered {
                            type boolean;
                            default "true";
                            description "Enable matching on UEs in DHCP-triggered state";
                        }

                        leaf ip-assigned {
                            type boolean;
                            default "true";
                            description "Match on UEs in an IP-assigned state";
                        }

                        leaf authorized-only {
                            type boolean;
                            default "true";
                            description "Enable matching on UEs in an authorized state";
                        }

                        leaf ip-assigned-authorized {
                            type boolean;
                            default "true";
                            description "Match on UEs in an IP-assigned and authorized state";
                        }

                        leaf already-signed-in {
                            type boolean;
                            default "true";
                            description "Enable matching on UEs that are already signed in";
                        }

                        leaf portal {
                            type boolean;
                            default "true";
                            description "Controls whether the query returns UEs in portal state";
                        }

                        leaf dsm {
                            type boolean;
                            default "true";
                            description "Controls whether the query returns UEs in DSM state";
                        }

                        leaf esm {
                            type boolean;
                            default "true";
                            description "Controls whether the query returns UEs in ESM state";
                        }

                        leaf l2 {
                            type boolean;
                            default "true";
                            description "Match on Layer-2 wholesale state for UEs";
                        }

                        leaf gtp-authorized {
                            type boolean;
                            default "true";
                            description "Enable matching on UEs in GTP-authorized state";
                        }

                        leaf delete-pending {
                            type boolean;
                            default "true";
                            description "Enable matching on UEs in a delete-pending state";
                        }

                        leaf cross-connect {
                            type boolean;
                            default "true";
                            description "Enable matching on cross-connected UEs";
                        }

                    } // container connection-state

                    container tunnel {
                        description "Enter the tunnel context";

                        leaf router-instance {
                            type string;
                            description "Router instance of tunnels to match for UEs";
                        }

                        leaf remote-address {
                            type types-sros:ip-unicast-or-linklocal-without-site-or-unique-local-address;
                            description "IP address as remote tunnel endpoint to match for UEs";
                        }

                        leaf local-address {
                            type types-sros:ip-unicast-or-linklocal-without-site-or-unique-local-address;
                            description "IP address as local tunnel endpoint to match for UEs";
                        }

                        leaf encapsulation {
                            type types-wlangw:encapsulation;
                            description "Tunnel type to match for active UEs";
                        }

                    } // container tunnel

                    container wlan-gw-group {
                        presence "Enable the wlan-gw-group context";
                        description "Enable the wlan-gw-group context";

                        leaf id {
                            type types-isa:wlan-gw-group-id;
                            mandatory true;
                            description "WLAN-GW ISA group ID";
                        }

                        leaf member {
                            type types-nat:bb-group-member {
                                range "1..1024";
                            }
                            description "The member of the WLAN-GW ISA group";
                        }

                    } // container wlan-gw-group

                } // list ue

                list tunnel {
                    key "name";
                    max-elements 1024;
                    description "Enter the tunnel list instance";

                    leaf name {
                        type types-sros:named-item;
                        description "Tunnel query name";
                    }

                    leaf calculate-counts {
                        type boolean;
                        default "false";
                        description "Count the number of tunnels matching the criteria";
                    }

                    leaf access-point-mac-address-learning-status {
                        type enumeration {
                            enum failed                         { value 1; }
                            enum succeeded                      { value 2; }
                        }
                        description "Matching criteria of tunnels based on learning status";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container encapsulation {
                        presence "Enable the encapsulation context";
                        description "Enable the encapsulation context";

                        leaf gre {
                            type boolean;
                            default "true";
                            description "Controls whether the query returns Soft GRE tunnels";
                        }

                        leaf l2tp {
                            type boolean;
                            default "true";
                            description "Controls whether the query returns Soft L2TPv3 tunnels";
                        }

                        leaf l2 {
                            type boolean;
                            default "true";
                            description "Enable matching on Layer 2 tunnels";
                        }

                        leaf vxlan {
                            type boolean;
                            default "true";
                            description "Controls whether the query returns VXLAN tunnels";
                        }

                    } // container encapsulation

                    container l2 {
                        description "Enter the l2 context";

                        leaf sap {
                            type types-sros:sap;
                            description "Value to match the L2-AP Access Point of the tunnel";
                        }

                        leaf inner-vlan {
                            type types-sros:qtag-full-range;
                            description "Value to match the Layer 2 access point of the tunnel";
                        }

                        leaf outer-vlan {
                            type types-sros:qtag-full-range;
                            description "Layer 2 access point matching with a specified S-VLAN";
                        }

                    } // container l2

                    container l3 {
                        description "Enter the l3 context";

                        leaf router-instance {
                            type string;
                            description "Router instance to match";
                        }

                        leaf remote-address {
                            type types-sros:ip-unicast-or-linklocal-without-site-or-unique-local-address;
                            description "IP address as remote endpoint to match";
                        }

                        leaf local-address {
                            type types-sros:ip-unicast-or-linklocal-without-site-or-unique-local-address;
                            description "IP address as local endpoint to match";
                        }

                        leaf address-type {
                            type enumeration {
                                enum ipv4                           { value 1; }
                                enum ipv6                           { value 2; }
                            }
                            description "Address type to match";
                        }

                    } // container l3

                    container ues {
                        description "Enter the ues context";

                        leaf custom-user-group {
                            type types-sros:named-item-or-empty;
                            description "Name of the custom user group";
                        }

                        leaf maximum {
                            type uint32;
                            description "Maximum number of UEs";
                        }

                        leaf minimum {
                            type uint32;
                            default "1";
                            description "Minimum number of UEs";
                        }

                        container state {
                            presence "Enable the state context";
                            description "Enable the state context";

                            leaf migrant {
                                type boolean;
                                default "true";
                                description "Match on tunnels with migrant UEs";
                            }

                            leaf dsm {
                                type boolean;
                                default "true";
                                description "Match on DSM UEs";
                            }

                            leaf esm {
                                type boolean;
                                default "true";
                                description "Match on ESM UEs";
                            }

                            leaf l2 {
                                type boolean;
                                default "true";
                                description "Match on tunnels with L2W UEs";
                            }

                            leaf cross-connect {
                                type boolean;
                                default "true";
                                description "Match on tunnels with cross-connect UEs";
                            }

                        } // container state

                    } // container ues

                } // list tunnel

            } // container queries

        } // container wlan-gw

    } // grouping conf-submgt-wlangw-wlan-gw

}
