submodule nokia-conf-system-login-control {

    yang-version "1.1";

    belongs-to nokia-conf { prefix "conf"; }

    import nokia-sros-yang-extensions     { prefix "sros-ext"; }
    import nokia-types-sros               { prefix "types-sros"; }

    include nokia-conf-groups;

    sros-ext:sros-major-release "rel25";
    organization "Nokia";
    contact
        "Nokia SR OS Support
         Web: <http://www.nokia.com>";
    description
        "Nokia YANG Data model to configure system login-control parameters on SR OS based routers.

         Copyright 2016 Nokia. All rights reserved. Reproduction of this document
         is authorized on the condition that the foregoing copyright notice is included.

         This nokia-conf-system-login-control YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-08-12";

    grouping conf-system-login-control {
        container login-control {
            description "Enter the login-control context";

            leaf exponential-backoff {
                type boolean;
                default "false";
                description "Enable exponential-backoff of the login prompt";
            }

            leaf idle-timeout {
                type union {
                    type enumeration {
                        enum none                           { value 9999; }
                    }
                    type int64 {
                        range "1..1440";
                    }
                }
                units "minutes";
                default "30";
                description "Idle timeout for console, FTP, Telnet, and SSH sessions";
            }

            leaf login-banner {
                type boolean;
                default "false";
                description "Display the SR OS login banner";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container login-scripts {
                description "Enter the login-scripts context";

                leaf global-script {
                    type types-sros:string-not-all-spaces {
                        length "1..180";
                    }
                    description "URL of the global CLI login script";
                }

                container per-user-script {
                    description "Enter the per-user-script context";

                    leaf user-directory {
                        type types-sros:string-not-all-spaces {
                            length "1..180";
                        }
                        description "Directory name of user-defined login script";
                    }

                    leaf file-name {
                        type types-sros:filename;
                        description "File name of the per-user login script";
                    }

                } // container per-user-script

            } // container login-scripts

            container motd {
                description "Enter the motd context";

                choice motd {
                    case url {

                        leaf url {
                            type types-sros:string-not-all-spaces {
                                length "1..180";
                            }
                            description "Location of the message of the day";
                        }

                    }
                    case text {

                        leaf text {
                            type types-sros:string-not-all-spaces {
                                length "1..900";
                            }
                            description "Message of the day displayed after a succesfull login";
                        }

                    }
                }
            } // container motd

            container pre-login-message {
                description "Enter the pre-login-message context";

                leaf message {
                    type types-sros:string-not-all-spaces {
                        length "1..900";
                    }
                    description "Pre-login message displayed before the login prompt";
                }

                leaf name {
                    type boolean;
                    default "false";
                    description "Display the system name after the pre-login message";
                }

            } // container pre-login-message

            container ftp {
                description "Enter the ftp context";

                leaf inbound-max-sessions {
                    type uint32 {
                        range "0..5";
                    }
                    default "3";
                    description "Maximum number of concurrent inbound FTP sessions";
                }

            } // container ftp

            container ssh {
                description "Enter the ssh context";

                leaf graceful-shutdown {
                    type boolean;
                    default "true";
                    description "Allow graceful shutdown of SSH sessions";
                }

                leaf max-channels-per-connection {
                    type uint32 {
                        range "1..50";
                    }
                    default "5";
                    description "Maximum number of channels per SSH connection";
                }

                leaf inbound-max-sessions {
                    type uint32 {
                        range "0..50";
                    }
                    default "5";
                    description "Maximum number of concurrent inbound sessions";
                }

                leaf outbound-max-sessions {
                    type uint32 {
                        range "0..15";
                    }
                    default "5";
                    description "Maximum number of concurrent outbound sessions";
                }

                leaf ttl-security {
                    type uint32 {
                        range "1..255";
                    }
                    description "Minimum TTL value for incoming packets";
                }

            } // container ssh

            container telnet {
                description "Enter the telnet context";

                leaf graceful-shutdown {
                    type boolean;
                    default "false";
                    description "Allow graceful shutdown of Telnet sessions";
                }

                leaf inbound-max-sessions {
                    type uint32 {
                        range "0..50";
                    }
                    default "5";
                    description "Maximum number of concurrent inbound sessions";
                }

                leaf outbound-max-sessions {
                    type uint32 {
                        range "0..15";
                    }
                    default "5";
                    description "Maximum number of concurrent outbound sessions";
                }

                leaf ttl-security {
                    type uint32 {
                        range "1..255";
                    }
                    description "Minimum TTL value for incoming packets";
                }

            } // container telnet

        } // container login-control

    } // grouping conf-system-login-control

}
