submodule nokia-state-router-bgp {

    yang-version "1.1";

    belongs-to nokia-state { prefix "state"; }

    import ietf-inet-types                { prefix "inet"; }
    import ietf-yang-types                { prefix "yang"; }
    import nokia-sros-yang-extensions     { prefix "sros-ext"; }
    import nokia-types-bgp                { prefix "types-bgp"; }
    import nokia-types-router             { prefix "types-router"; }
    import nokia-types-services           { prefix "types-services"; }
    import nokia-types-sros               { prefix "types-sros"; }

    include nokia-state-router;

    sros-ext:sros-major-release "rel25";
    organization "Nokia";
    contact
        "Nokia SR OS Support
         Web: <http://www.nokia.com>";
    description
        "Nokia YANG Data model with operational state for bgp protocol on SR OS based routers.

         Copyright 2016 Nokia. All rights reserved. Reproduction of this document
         is authorized on the condition that the foregoing copyright notice is included.

         This nokia-state-router-bgp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-08-12";

    grouping state-router-bgp {
        container bgp {
            description "Enter the bgp context";

            container convergence {
                description "Enter the convergence context";

                list family {
                    key "family-type";
                    description "Enter the family list instance";

                    leaf family-type {
                        type enumeration {
                            enum ipv4                           { value 1; }
                            enum vpn-ipv4                       { value 2; }
                            enum ipv6                           { value 3; }
                            enum vpn-ipv6                       { value 5; }
                            enum label-ipv4                     { value 17; }
                            enum label-ipv6                     { value 18; }
                        }
                        description
                            "Specifies the address family for which the
                             bgp convergence selection applies.";
                    }

                    leaf up-peers-when-min-expired {
                        type uint16;
                        description
                            "The number of BGP sessions (configured and dynamic) that support the address family and that were in established state
                             when the win-wait-to-advertise timer expired";
                    }

                    leaf up-peers {
                        type uint32;
                        description
                            "The number of BGP sessions (configured and dynamic) that support the address family and that are currently in the
                             established state";
                    }

                    leaf converged-peers {
                        type uint32;
                        description "The number of peers that have sent an EOR marker for the address family since the last BGP restart";
                    }

                    leaf first-up-peer-time {
                        type yang:timeticks;
                        description
                            "The time when the first session supporting the address family came up, measured from the time that the BGP
                             instance restarted";
                    }

                    leaf last-up-peer-time {
                        type yang:timeticks;
                        description
                            "The time when the last session supporting the address family came up, measured from the time that the BGP
                             instance restarted";
                    }

                    leaf convergence-state {
                        type enumeration {
                            enum waiting {
                                value 1;
                                description "BGP has recently restarted and no sessions have re-established yet";
                            }
                            enum started {
                                value 2;
                                description "BGP has recently restarted and at least one session has re-established with support of the address family";
                            }
                            enum partial {
                                value 3;
                                description "BGP has recently restarted and at least one session has advertised an End-of-RIB marker for the address family.";
                            }
                            enum timeout {
                                value 4;
                                description "BGP has recently restarted and not all non-slow peers advertised an End-of-RIB marker for the address family before the max-wait-to-advertise timer expired";
                            }
                            enum converged {
                                value 5;
                                description "All non-slow peers that support the address family have have advertised the End-of-RIB marker for the address family";
                            }
                        }
                    }

                    leaf convergence-time {
                        type yang:timeticks;
                        description "The elapsed time in seconds, starting from the last BGP restart, to reach the converged state for the address family.";
                    }

                } // list family

            } // container convergence

            container statistics {
                description "Enter the statistics context";

                leaf operational-state {
                    type string;
                }

                leaf peer-groups {
                    type uint32;
                }

                leaf peers {
                    type uint32;
                }

                leaf vpn-peer-groups {
                    type uint32;
                }

                leaf vpn-peers {
                    type uint32;
                }

                leaf total-internal-groups {
                    type uint32;
                }

                leaf max-internal-groups {
                    type uint32;
                }

                leaf bgp-paths {
                    type uint32;
                }

                leaf path-memory {
                    type uint32;
                }

                container routes-per-family {
                    description "Enter the routes-per-family context";

                    container ipv4 {
                        description "Enter the ipv4 context";

                        leaf remote-routes {
                            type uint32;
                        }

                        leaf remote-active-routes {
                            type uint32;
                        }

                        leaf backup-routes {
                            type uint32;
                        }

                    } // container ipv4

                    container ipv6 {
                        description "Enter the ipv6 context";

                        leaf remote-routes {
                            type uint32;
                        }

                        leaf remote-active-routes {
                            type uint32;
                        }

                        leaf backup-routes {
                            type uint32;
                        }

                    } // container ipv6

                    container route-flap-dampening {
                        description "Enter the route-flap-dampening context";

                        container ipv4-ipv6 {
                            description "Enter the ipv4-ipv6 context";

                            leaf suppressed-routes {
                                type uint32;
                            }

                            leaf history-routes {
                                type uint32;
                            }

                            leaf decay-routes {
                                type uint32;
                            }

                        } // container ipv4-ipv6

                        container vpnipv4-vpnipv6 {
                            description "Enter the vpnipv4-vpnipv6 context";

                            leaf local-routes {
                                type uint32;
                            }

                            leaf suppressed-routes {
                                type uint32;
                            }

                            leaf history-routes {
                                type uint32;
                            }

                            leaf decay-routes {
                                type uint32;
                            }

                        } // container vpnipv4-vpnipv6

                    } // container route-flap-dampening

                    container vpn-ipv4 {
                        description "Enter the vpn-ipv4 context";

                        leaf remote-routes {
                            type uint32;
                        }

                        leaf remote-active-routes {
                            type uint32;
                        }

                        leaf backup-routes {
                            type uint32;
                        }

                    } // container vpn-ipv4

                    container vpn-ipv6 {
                        description "Enter the vpn-ipv6 context";

                        leaf remote-routes {
                            type uint32;
                        }

                        leaf remote-active-routes {
                            type uint32;
                        }

                        leaf backup-routes {
                            type uint32;
                        }

                    } // container vpn-ipv6

                    container mvpn-ipv4 {
                        description "Enter the mvpn-ipv4 context";

                        leaf remote-routes {
                            type uint32;
                        }

                        leaf remote-active-routes {
                            type uint32;
                        }

                        leaf backup-routes {
                            type uint32;
                        }

                    } // container mvpn-ipv4

                    container mvpn-ipv6 {
                        description "Enter the mvpn-ipv6 context";

                        leaf remote-routes {
                            type uint32;
                        }

                        leaf remote-active-routes {
                            type uint32;
                        }

                        leaf backup-routes {
                            type uint32;
                        }

                    } // container mvpn-ipv6

                    container mcast-ipv4 {
                        description "Enter the mcast-ipv4 context";

                        leaf remote-routes {
                            type uint32;
                        }

                        leaf remote-active-routes {
                            type uint32;
                        }

                        leaf backup-routes {
                            type uint32;
                        }

                    } // container mcast-ipv4

                    container mcast-ipv6 {
                        description "Enter the mcast-ipv6 context";

                        leaf remote-routes {
                            type uint32;
                        }

                        leaf remote-active-routes {
                            type uint32;
                        }

                        leaf backup-routes {
                            type uint32;
                        }

                    } // container mcast-ipv6

                    container l2-vpn {
                        description "Enter the l2-vpn context";

                        leaf remote-routes {
                            type uint32;
                        }

                        leaf remote-active-routes {
                            type uint32;
                        }

                        leaf backup-routes {
                            type uint32;
                        }

                    } // container l2-vpn

                    container mdt-safi {
                        description "Enter the mdt-safi context";

                        leaf remote-routes {
                            type uint32;
                        }

                        leaf remote-active-routes {
                            type uint32;
                        }

                        leaf backup-routes {
                            type uint32;
                        }

                    } // container mdt-safi

                    container ms-pw {
                        description "Enter the ms-pw context";

                        leaf remote-routes {
                            type uint32;
                        }

                        leaf remote-active-routes {
                            type uint32;
                        }

                        leaf backup-routes {
                            type uint32;
                        }

                    } // container ms-pw

                    container flow-ipv4 {
                        description "Enter the flow-ipv4 context";

                        leaf remote-routes {
                            type uint32;
                        }

                        leaf remote-active-routes {
                            type uint32;
                        }

                        leaf backup-routes {
                            type uint32;
                        }

                    } // container flow-ipv4

                    container flow-ipv6 {
                        description "Enter the flow-ipv6 context";

                        leaf remote-routes {
                            type uint32;
                        }

                        leaf remote-active-routes {
                            type uint32;
                        }

                        leaf backup-routes {
                            type uint32;
                        }

                    } // container flow-ipv6

                    container flow-vpn-ipv4 {
                        description "Enter the flow-vpn-ipv4 context";

                        leaf remote-routes {
                            type uint32;
                        }

                        leaf remote-active-routes {
                            type uint32;
                        }

                        leaf backup-routes {
                            type uint32;
                        }

                    } // container flow-vpn-ipv4

                    container flow-vpn-ipv6 {
                        description "Enter the flow-vpn-ipv6 context";

                        leaf remote-routes {
                            type uint32;
                        }

                        leaf remote-active-routes {
                            type uint32;
                        }

                        leaf backup-routes {
                            type uint32;
                        }

                    } // container flow-vpn-ipv6

                    container route-target {
                        description "Enter the route-target context";

                        leaf remote-routes {
                            type uint32;
                        }

                        leaf remote-active-routes {
                            type uint32;
                        }

                        leaf backup-routes {
                            type uint32;
                        }

                    } // container route-target

                    container mcast-vpn-ipv4 {
                        description "Enter the mcast-vpn-ipv4 context";

                        leaf remote-routes {
                            type uint32;
                        }

                        leaf remote-active-routes {
                            type uint32;
                        }

                        leaf backup-routes {
                            type uint32;
                        }

                    } // container mcast-vpn-ipv4

                    container mcast-vpn-ipv6 {
                        description "Enter the mcast-vpn-ipv6 context";

                        leaf remote-routes {
                            type uint32;
                        }

                        leaf remote-active-routes {
                            type uint32;
                        }

                        leaf backup-routes {
                            type uint32;
                        }

                    } // container mcast-vpn-ipv6

                    container evpn {
                        description "Enter the evpn context";

                        leaf remote-routes {
                            type uint32;
                        }

                        leaf remote-active-routes {
                            type uint32;
                        }

                        leaf backup-routes {
                            type uint32;
                        }

                    } // container evpn

                    container label-ipv4 {
                        description "Enter the label-ipv4 context";

                        leaf remote-routes {
                            type uint32;
                        }

                        leaf remote-active-routes {
                            type uint32;
                        }

                        leaf backup-routes {
                            type uint32;
                        }

                    } // container label-ipv4

                    container label-ipv6 {
                        description "Enter the label-ipv6 context";

                        leaf remote-routes {
                            type uint32;
                        }

                        leaf remote-active-routes {
                            type uint32;
                        }

                        leaf backup-routes {
                            type uint32;
                        }

                    } // container label-ipv6

                    container bgp-ls {
                        description "Enter the bgp-ls context";

                        leaf remote-routes {
                            type uint32;
                        }

                        leaf remote-active-routes {
                            type uint32;
                        }

                        leaf backup-routes {
                            type uint32;
                        }

                    } // container bgp-ls

                    container sr-policy-ipv4 {
                        description "Enter the sr-policy-ipv4 context";

                        leaf remote-routes {
                            type uint32;
                        }

                        leaf remote-active-routes {
                            type uint32;
                        }

                        leaf backup-routes {
                            type uint32;
                        }

                    } // container sr-policy-ipv4

                    container sr-policy-ipv6 {
                        description "Enter the sr-policy-ipv6 context";

                        leaf remote-routes {
                            type uint32;
                        }

                        leaf remote-active-routes {
                            type uint32;
                        }

                        leaf backup-routes {
                            type uint32;
                        }

                    } // container sr-policy-ipv6

                } // container routes-per-family

            } // container statistics

            list group {
                key "group-name";
                description "Enter the group list instance";

                leaf group-name {
                    type types-sros:named-item-64;
                }

            } // list group

            list neighbor {
                key "ip-address";
                description "Enter the neighbor list instance";

                leaf ip-address {
                    type types-sros:ip-address-with-zone;
                }

                container statistics {
                    description "Enter the statistics context";

                    leaf peer-as {
                        type uint32;
                        description "specifies the AS number for dynamic peers.";
                    }

                    leaf peer-port {
                        type int32;
                        description "specifies the peer's port.";
                    }

                    leaf local-port {
                        type int32;
                        description "specifies the local port on this peer.";
                    }

                    leaf session-state {
                        type string {
                            length "0..32";
                        }
                        description "specifies the current BGP state of this peer.";
                    }

                    leaf last-state {
                        type string {
                            length "0..32";
                        }
                        description "specifies the last BGP state of this peer.";
                    }

                    leaf last-event {
                        type string {
                            length "0..32";
                        }
                        description "specifies the last BGP event of this peer.";
                    }

                    leaf last-error {
                        type string {
                            length "0..80";
                        }
                        description "specifies the last error of this peer.";
                    }

                    leaf-list negotiated-family {
                        type string {
                            length "0..16";
                        }
                        description "specifies the family successfully negotiated with the peer.";
                    }

                    leaf operational-local-address {
                        type types-sros:ip-address-with-zone;
                        description "Local IP address used by the neighbor when communicating with BGP peers";
                    }

                    leaf operational-remote-address {
                        type types-sros:ip-address-with-zone;
                        description "Operational IP address used by remote peer for a session.";
                    }

                    leaf peer-identifier {
                        type string {
                            length "0..16";
                        }
                        description "specifies peer's Router-ID.";
                    }

                    leaf established-transitions {
                        type uint32;
                        description "specifies the number of state transitions made by the peer.";
                    }

                    leaf last-established-time {
                        type yang:date-and-time;
                        description "specifies the time when the peer established the BGP session.";
                    }

                    leaf in-update-elapsed-time {
                        type yang:timeticks;
                        description "specifies the time elapsed since the last update was received.";
                    }

                    leaf hold-time-interval {
                        type int32;
                        description "specifies the hold time value negotiated with the peer.";
                    }

                    leaf remaining-idle-hold-time {
                        type uint32;
                        description
                            "specifies how much time is remaining until the Idle hold time
                             period runs out and session establishment can begin again for this peer.";
                    }

                    leaf keep-alive-interval {
                        type int32;
                        description "specifies the keep alive time value negotiated with the peer.";
                    }

                    leaf number-of-update-flaps {
                        type uint32;
                        description "specifies the number of flaps of updates from this peer.";
                    }

                    leaf update-errors {
                        type uint32;
                        description "specifies the number of update errors received from this peer.";
                    }

                    leaf-list negotiated-capability {
                        type string {
                            length "0..16";
                        }
                        description "specifies the capabilities successfully negotiated with the peer.";
                    }

                    leaf received-paths {
                        type uint32;
                        description "specifies the number of paths received from this peer.";
                    }

                    leaf dynamically-configured {
                        type boolean;
                        description "specifies dynamic peer.";
                    }

                    leaf-list convergence-recv-eor {
                        type string {
                            length "0..16";
                        }
                        description "specifies the convergence types that the peer received end of rib marker for.";
                    }

                    leaf-list convergence-sent-eor {
                        type string {
                            length "0..16";
                        }
                        description "specifies the convergence types that the peer sent end of rib marker for.";
                    }

                    leaf convergence-exceeded-min-wait {
                        type enumeration {
                            enum no                             { value 1; }
                            enum yes                            { value 2; }
                            enum unknown                        { value 3; }
                        }
                        description "specifies if the convergence min-wait is exceeded.";
                    }

                    leaf oper-tcp-mss {
                        type int32;
                        description "Specifies the current maximum size of TCP segments that can be sent to the peer.";
                    }

                    leaf rcvd-tcp-mss {
                        type int32;
                        description "Specifies the value of the TCP MSS option received from the remote peer.";
                    }

                    container remote-family {
                        description "Enter the remote-family context";

                        leaf-list family {
                            type string {
                                length "0..16";
                            }
                        }

                    } // container remote-family

                    container local-capability {
                        description "Enter the local-capability context";

                        leaf-list capability {
                            type string {
                                length "0..16";
                            }
                            description "specifies the capability name.";
                        }

                    } // container local-capability

                    container remote-capability {
                        description "Enter the remote-capability context";

                        leaf-list capability {
                            type string {
                                length "0..16";
                            }
                            description "specifies the capability name.";
                        }

                    } // container remote-capability

                    container remote-add-path-capability {
                        description "Enter the remote-add-path-capability context";

                        leaf-list send-capability {
                            type string {
                                length "0..16";
                            }
                            description "specifies the send capability families.";
                        }

                        leaf-list receive-capability {
                            type string {
                                length "0..16";
                            }
                            description "specifies the receive capability families.";
                        }

                    } // container remote-add-path-capability

                    container family-prefix {
                        description "Enter the family-prefix context";

                        container ipv4 {
                            description "Enter the ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ipv4

                        container ipv6 {
                            description "Enter the ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ipv6

                        container vpn-ipv4 {
                            description "Enter the vpn-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container vpn-ipv4

                        container vpn-ipv6 {
                            description "Enter the vpn-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container vpn-ipv6

                        container mvpn-ipv4 {
                            description "Enter the mvpn-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mvpn-ipv4

                        container mvpn-ipv6 {
                            description "Enter the mvpn-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mvpn-ipv6

                        container mcast-ipv4 {
                            description "Enter the mcast-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-ipv4

                        container mcast-ipv6 {
                            description "Enter the mcast-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-ipv6

                        container l2-vpn {
                            description "Enter the l2-vpn context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container l2-vpn

                        container mdt-safi {
                            description "Enter the mdt-safi context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mdt-safi

                        container ms-pw {
                            description "Enter the ms-pw context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ms-pw

                        container flow-ipv4 {
                            description "Enter the flow-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-ipv4

                        container flow-ipv6 {
                            description "Enter the flow-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-ipv6

                        container flow-vpn-ipv4 {
                            description "Enter the flow-vpn-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-vpn-ipv4

                        container flow-vpn-ipv6 {
                            description "Enter the flow-vpn-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-vpn-ipv6

                        container route-target {
                            description "Enter the route-target context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container route-target

                        container mcast-vpn-ipv4 {
                            description "Enter the mcast-vpn-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-vpn-ipv4

                        container mcast-vpn-ipv6 {
                            description "Enter the mcast-vpn-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-vpn-ipv6

                        container evpn {
                            description "Enter the evpn context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container evpn

                        container label-ipv4 {
                            description "Enter the label-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container label-ipv4

                        container label-ipv6 {
                            description "Enter the label-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container label-ipv6

                        container bgp-ls {
                            description "Enter the bgp-ls context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container bgp-ls

                        container sr-policy-ipv4 {
                            description "Enter the sr-policy-ipv4 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container sr-policy-ipv4

                        container sr-policy-ipv6 {
                            description "Enter the sr-policy-ipv6 context";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container sr-policy-ipv6

                    } // container family-prefix

                    container sent {
                        description "Enter the sent context";

                        leaf queues {
                            type uint64;
                        }

                        leaf messages {
                            type uint64;
                        }

                        leaf octets {
                            type uint64;
                        }

                        leaf updates {
                            type uint64;
                        }

                        leaf route-refresh {
                            type uint64;
                        }

                    } // container sent

                    container received {
                        description "Enter the received context";

                        leaf queues {
                            type uint64;
                        }

                        leaf messages {
                            type uint64;
                        }

                        leaf octets {
                            type uint64;
                        }

                        leaf updates {
                            type uint64;
                        }

                        leaf route-refresh {
                            type uint64;
                        }

                    } // container received

                } // container statistics

                container graceful-restart {
                    description "Enter the graceful-restart context";

                    leaf support {
                        type boolean;
                        description "specifies graceful-restart capability signaled by the peer.";
                    }

                    leaf restart-time-requested {
                        type uint32;
                        description "specifies the restart time requested by the peer.";
                    }

                    leaf stale-route-time {
                        type uint32;
                        description "specifies the time value until when stale routes can be used.";
                    }

                    leaf peer-status {
                        type string {
                            length "0..32";
                        }
                        description "specifies the graceful-restart operational status on the peer.";
                    }

                    leaf number-of-restarts {
                        type uint32;
                        description "specifies the number of times the peer has attempted restart.";
                    }

                    leaf last-restart-time {
                        type yang:date-and-time;
                        description "specifies the last time the peer attempted restart.";
                    }

                    container restart-family {
                        description "Enter the restart-family context";

                        leaf-list family {
                            type string {
                                length "0..16";
                            }
                        }

                    } // container restart-family

                    container forwarding-family {
                        description "Enter the forwarding-family context";

                        leaf-list family {
                            type string {
                                length "0..16";
                            }
                        }

                    } // container forwarding-family

                    container negotiated-family {
                        description "Enter the negotiated-family context";

                        leaf-list family {
                            type string {
                                length "0..16";
                            }
                        }

                    } // container negotiated-family

                    container received-end-of-rib-marker {
                        description "Enter the received-end-of-rib-marker context";

                        leaf-list family {
                            type string {
                                length "0..16";
                            }
                        }

                    } // container received-end-of-rib-marker

                    container sent-end-of-rib-marker {
                        description "Enter the sent-end-of-rib-marker context";

                        leaf-list family {
                            type string {
                                length "0..16";
                            }
                        }

                    } // container sent-end-of-rib-marker

                    container notification-family {
                        description "Enter the notification-family context";

                        leaf-list family {
                            type string {
                                length "0..16";
                            }
                        }

                    } // container notification-family

                    container long-lived {
                        description "Enter the long-lived context";

                        list family {
                            key "family-type";
                            description "Enter the family list instance";

                            leaf family-type {
                                type types-bgp:llgr-family-identifiers;
                                description "Specifies the address family for long-lived graceful-restart";
                            }

                            leaf advertised-stale-time-received {
                                type uint32;
                                description "Long Lived stale time received from the peer for this family.";
                            }

                            leaf stale-time-negotiated {
                                type uint32;
                                description "Long Lived stale time negotiated with the peer for this family.";
                            }

                            leaf flags-received {
                                type boolean;
                                description "specifies F-bit recieved  by the peer.";
                            }

                            leaf flags-supported {
                                type boolean;
                                description "specifies F-bit supported  by the peer.";
                            }

                        } // list family

                    } // container long-lived

                } // container graceful-restart

                list prefix-limit {
                    key "family";
                    description "Enter the prefix-limit list instance";

                    leaf family {
                        type types-bgp:ip-family-identifier;
                        description
                            "Specifies the address families for which
                             prefix-limit is configured.";
                    }

                    leaf inherit {
                        type boolean;
                        description
                            "The value of this object specifies if the peer entry in this row, should inherit the operational value of an object,
                             or use the administratively set value.";
                    }

                    leaf excess-inactive {
                        type uint32;
                        description
                            "Specifies the number of routes that have been received from
                             the peer that are in the excess-inactive state";
                    }

                } // list prefix-limit

                container epe-sid {
                    description "Enter the epe-sid context";

                    leaf label {
                        type uint32;
                        description "specifies the sid label";
                    }

                    container statistics {
                        description "Enter the statistics context";

                        leaf packets {
                            type uint64;
                            description "Number of packets for this route.";
                        }

                        leaf octets {
                            type uint64;
                            description "Number of octets for this route.";
                        }

                    } // container statistics

                    list adj-sid {
                        key "index";
                        description "Enter the adj-sid list instance";

                        leaf index {
                            type uint32 {
                                range "1..32";
                            }
                            description "Specifies the adjacency sid index.";
                        }

                        leaf label {
                            type uint32;
                            description "specifies the sid label";
                        }

                        container statistics {
                            description "Enter the statistics context";

                            leaf packets {
                                type uint64;
                                description "Number of packets for this route.";
                            }

                            leaf octets {
                                type uint64;
                                description "Number of octets for this route.";
                            }

                        } // container statistics

                    } // list adj-sid

                } // container epe-sid

            } // list neighbor

            container rib {
                description "Enter the rib context";

                container ipv4-unicast {
                    description "Enter the ipv4-unicast context";

                    container local-rib {
                        description "Enter the local-rib context";

                        list routes {
                            key "prefix neighbor owner router-instance-origin path-id";
                            description "Enter the routes list instance";

                            leaf prefix {
                                type types-sros:ipv4-prefix;
                                description "Route prefix";
                            }

                            leaf neighbor {
                                type types-sros:ip-address-with-zone;
                                description "IP address of BGP neighbor";
                            }

                            leaf owner {
                                type types-router:protocol-type;
                                description "BGP route owner";
                            }

                            leaf router-instance-origin {
                                type uint32;
                                description "Route instance origin value";
                            }

                            leaf path-id {
                                type uint64;
                                description "Path identifier of this route";
                            }

                            leaf attr-id {
                                type uint64;
                                description
                                    "The value represents attribute id of this route. The attribute
                                     defined by this id represents the attribute information of this
                                     route.";
                            }

                            leaf peer-router-id {
                                type types-sros:ip-address;
                                description "The value indicates peer router identifier for this route.";
                            }

                            leaf last-modified-date {
                                type yang:date-and-time;
                                description "Timestamp of when this path was last changed";
                            }

                            leaf used-route {
                                type boolean;
                                description "The value specifies if the route is used by the local BGP speaker.";
                            }

                            leaf valid-route {
                                type boolean;
                                description "This value is true when the route is usable";
                            }

                            leaf best-route {
                                type boolean;
                                description "This value specifies if the route is best or not";
                            }

                            leaf backup-route {
                                type boolean;
                                description "This value specifies if the route is backup route";
                            }

                            leaf group-best {
                                type boolean;
                                description
                                    "This value indicates if this route is group best when
                                     deterministic MED is set.";
                            }

                            leaf sticky-ecmp {
                                type boolean;
                                description
                                    "This value indicates if route is marked as sticky-ecmp by
                                     import policy.";
                            }

                            leaf stale-route {
                                type boolean;
                                description
                                    "This value indicates if route is stale due to BGP graceful
                                     restart.";
                            }

                            leaf unused-weight-only {
                                type boolean;
                                description "Indicates true if the route is unused, but being used for weight calculation";
                            }

                            leaf long-live-gr-stale {
                                type boolean;
                                description
                                    "This value indicates if route is stale due to BGP long live
                                     graceful restart.";
                            }

                            leaf rtm-install-disabled {
                                type boolean;
                                description "This value indicates if the route is not to be installed in routing table.";
                            }

                            leaf tie-break-reason {
                                type enumeration {
                                    enum unknown                        { value -1; }
                                    enum none                           { value 0; }
                                    enum origin                         { value 1; }
                                    enum as-path-length                 { value 2; }
                                    enum next-hop-cost                  { value 3; }
                                    enum med                            { value 4; }
                                    enum local-pref                     { value 5; }
                                    enum aggregator                     { value 6; }
                                    enum originator-id                  { value 7; }
                                    enum cluster-list                   { value 9; }
                                    enum extended-community             { value 10; }
                                    enum aigp                           { value 11; }
                                    enum missing-attribute              { value 12; }
                                    enum rtm-pref                       { value 13; }
                                    enum owner                          { value 14; }
                                    enum eigp-labeled                   { value 15; }
                                    enum vpn-route                      { value 16; }
                                    enum ebgp-route                     { value 17; }
                                    enum peer-ip                        { value 18; }
                                    enum local-peer                     { value 19; }
                                    enum multi-path                     { value 20; }
                                    enum vpn-rd                         { value 21; }
                                    enum next-hop-type                  { value 22; }
                                    enum invalid-route                  { value 23; }
                                    enum origin-validation              { value 24; }
                                    enum long-live-gr-stale             { value 25; }
                                    enum default-originate              { value 26; }
                                    enum rtm-install-disabled           { value 27; }
                                    enum peer-router-id                 { value 28; }
                                    enum path-identifier                { value 29; }
                                    enum d-path-length                  { value 30; }
                                    enum epe-route                      { value 31; }
                                }
                                description "Tie breaker reason for this route.";
                            }

                            leaf multipath-exclusion-reason {
                                type enumeration {
                                    enum none                           { value 0; }
                                    enum not-nexthop-diverse            { value 1; }
                                    enum not-multipath-eligible         { value 2; }
                                    enum max-paths-exceeded             { value 3; }
                                    enum not-same-exact-as-path         { value 4; }
                                    enum not-same-neighbor-as           { value 5; }
                                    enum longer-as-path                 { value 6; }
                                    enum resolving-type                 { value 7; }
                                    enum label-type                     { value 8; }
                                }
                                description "Multipath exclusion reason for this route.";
                            }

                            leaf origin-validation-state {
                                type enumeration {
                                    enum unknown                        { value -1; }
                                    enum not-applicable                 { value 0; }
                                    enum valid                          { value 1; }
                                    enum not-found                      { value 2; }
                                    enum invalid                        { value 3; }
                                }
                                description "Origin validation state of the route.";
                            }

                            leaf route-tag {
                                type uint32;
                                description "Router identifier.";
                            }

                            leaf forwarding-class {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "QoS association of the routes";
                            }

                            leaf priority {
                                type enumeration {
                                    enum high                           { value 0; }
                                    enum low                            { value 1; }
                                }
                                description "Route enqueuing priority.";
                            }

                            leaf rib-priority {
                                type enumeration {
                                    enum normal                         { value 0; }
                                    enum high                           { value 1; }
                                }
                                description "Rib priority.";
                            }

                            leaf source-class {
                                type uint8;
                                description "Source class index of the route.";
                            }

                            leaf destination-class {
                                type uint8;
                                description "Destination class index of the route.";
                            }

                            leaf add-paths-send-limit {
                                type union {
                                    type uint8;
                                    type enumeration {
                                        enum multipath {
                                            value -1;
                                            description "Indicates that the ECMP paths available for this routes will be advertised to peers using add-paths";
                                        }
                                    }
                                }
                                description "The value indicates max number of add paths allowed by the route.";
                            }

                            leaf leakable-route {
                                type boolean;
                                description "This value indicates if route is leak eligible";
                            }

                            leaf leaked-route {
                                type boolean;
                                description "This value indicates if route is leaked from another VRF.";
                            }

                            leaf label-value {
                                type uint32;
                                description "The MPLS label value.";
                            }

                            leaf in-rtm {
                                type boolean;
                                description "This value indicates if route is installed in rtm.";
                            }

                            container invalid-reason {
                                description "Enter the invalid-reason context";

                                leaf rejected-route {
                                    type boolean;
                                    description
                                        "The value indicates if route is temporarily rejected or
                                         rejected by the route policy.";
                                }

                                leaf as-loop {
                                    type boolean;
                                    description
                                        "This value indicates that the route has loops but peer doesn't
                                         have loop detection enabled.";
                                }

                                leaf next-hop-unresolved {
                                    type boolean;
                                    description
                                        "This value indicates that the route is not BGP route or VPN
                                         route and its next hop is not reachable.";
                                }

                                leaf cluster-loop {
                                    type boolean;
                                    description "The value indicate that the route is not valid due to cluster loop.";
                                }

                                leaf d-path-loop {
                                    type boolean;
                                    description
                                        "This value indicates that the route has D-Path with domain-id that
                                         matches one of the domain-ids configured locally.";
                                }

                            } // container invalid-reason

                        } // list routes

                    } // container local-rib

                    container rib-in-out {
                        description "Enter the rib-in-out context";

                        container rib-in-pre {
                            description "Enter the rib-in-pre context";

                            list routes {
                                key "prefix neighbor router-instance-origin path-id";
                                description "Enter the routes list instance";

                                leaf prefix {
                                    type types-sros:ipv4-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                            } // list routes

                        } // container rib-in-pre

                        container rib-in-post {
                            description "Enter the rib-in-post context";

                            list routes {
                                key "prefix neighbor router-instance-origin path-id";
                                description "Enter the routes list instance";

                                leaf prefix {
                                    type types-sros:ipv4-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf last-modified-date {
                                    type yang:date-and-time;
                                    description "Timestamp of when this path was last changed";
                                }

                                leaf used-route {
                                    type boolean;
                                    description "The value specifies if the route is used by the local BGP speaker.";
                                }

                                leaf valid-route {
                                    type boolean;
                                    description "This value is true when the route is usable";
                                }

                                leaf best-route {
                                    type boolean;
                                    description "This value specifies if the route is best or not";
                                }

                                leaf backup-route {
                                    type boolean;
                                    description "This value specifies if the route is backup route";
                                }

                                leaf group-best {
                                    type boolean;
                                    description
                                        "This value indicates if this route is group best when
                                         deterministic MED is set.";
                                }

                                leaf sticky-ecmp {
                                    type boolean;
                                    description
                                        "This value indicates if route is marked as sticky-ecmp by
                                         import policy.";
                                }

                                leaf stale-route {
                                    type boolean;
                                    description
                                        "This value indicates if route is stale due to BGP graceful
                                         restart.";
                                }

                                leaf unused-weight-only {
                                    type boolean;
                                    description "Indicates true if the route is unused, but being used for weight calculation";
                                }

                                leaf long-live-gr-stale {
                                    type boolean;
                                    description
                                        "This value indicates if route is stale due to BGP long live
                                         graceful restart.";
                                }

                                leaf rtm-install-disabled {
                                    type boolean;
                                    description "This value indicates if the route is not to be installed in routing table.";
                                }

                                leaf tie-break-reason {
                                    type enumeration {
                                        enum unknown                        { value -1; }
                                        enum none                           { value 0; }
                                        enum origin                         { value 1; }
                                        enum as-path-length                 { value 2; }
                                        enum next-hop-cost                  { value 3; }
                                        enum med                            { value 4; }
                                        enum local-pref                     { value 5; }
                                        enum aggregator                     { value 6; }
                                        enum originator-id                  { value 7; }
                                        enum cluster-list                   { value 9; }
                                        enum extended-community             { value 10; }
                                        enum aigp                           { value 11; }
                                        enum missing-attribute              { value 12; }
                                        enum rtm-pref                       { value 13; }
                                        enum owner                          { value 14; }
                                        enum eigp-labeled                   { value 15; }
                                        enum vpn-route                      { value 16; }
                                        enum ebgp-route                     { value 17; }
                                        enum peer-ip                        { value 18; }
                                        enum local-peer                     { value 19; }
                                        enum multi-path                     { value 20; }
                                        enum vpn-rd                         { value 21; }
                                        enum next-hop-type                  { value 22; }
                                        enum invalid-route                  { value 23; }
                                        enum origin-validation              { value 24; }
                                        enum long-live-gr-stale             { value 25; }
                                        enum default-originate              { value 26; }
                                        enum rtm-install-disabled           { value 27; }
                                        enum peer-router-id                 { value 28; }
                                        enum path-identifier                { value 29; }
                                        enum d-path-length                  { value 30; }
                                        enum epe-route                      { value 31; }
                                    }
                                    description "Tie breaker reason for this route.";
                                }

                                leaf multipath-exclusion-reason {
                                    type enumeration {
                                        enum none                           { value 0; }
                                        enum not-nexthop-diverse            { value 1; }
                                        enum not-multipath-eligible         { value 2; }
                                        enum max-paths-exceeded             { value 3; }
                                        enum not-same-exact-as-path         { value 4; }
                                        enum not-same-neighbor-as           { value 5; }
                                        enum longer-as-path                 { value 6; }
                                        enum resolving-type                 { value 7; }
                                        enum label-type                     { value 8; }
                                    }
                                    description "Multipath exclusion reason for this route.";
                                }

                                leaf origin-validation-state {
                                    type enumeration {
                                        enum unknown                        { value -1; }
                                        enum not-applicable                 { value 0; }
                                        enum valid                          { value 1; }
                                        enum not-found                      { value 2; }
                                        enum invalid                        { value 3; }
                                    }
                                    description "Origin validation state of the route.";
                                }

                                leaf route-tag {
                                    type uint32;
                                    description "Router identifier.";
                                }

                                leaf forwarding-class {
                                    type enumeration {
                                        enum be                             { value 0; }
                                        enum l2                             { value 1; }
                                        enum af                             { value 2; }
                                        enum l1                             { value 3; }
                                        enum h2                             { value 4; }
                                        enum ef                             { value 5; }
                                        enum h1                             { value 6; }
                                        enum nc                             { value 7; }
                                    }
                                    description "QoS association of the routes";
                                }

                                leaf priority {
                                    type enumeration {
                                        enum high                           { value 0; }
                                        enum low                            { value 1; }
                                    }
                                    description "Route enqueuing priority.";
                                }

                                leaf rib-priority {
                                    type enumeration {
                                        enum normal                         { value 0; }
                                        enum high                           { value 1; }
                                    }
                                    description "Rib priority.";
                                }

                                leaf source-class {
                                    type uint8;
                                    description "Source class index of the route.";
                                }

                                leaf destination-class {
                                    type uint8;
                                    description "Destination class index of the route.";
                                }

                                leaf add-paths-send-limit {
                                    type union {
                                        type uint8;
                                        type enumeration {
                                            enum multipath {
                                                value -1;
                                                description "Indicates that the ECMP paths available for this routes will be advertised to peers using add-paths";
                                            }
                                        }
                                    }
                                    description "The value indicates max number of add paths allowed by the route.";
                                }

                                leaf leakable-route {
                                    type boolean;
                                    description "This value indicates if route is leak eligible";
                                }

                                leaf leaked-route {
                                    type boolean;
                                    description "This value indicates if route is leaked from another VRF.";
                                }

                                leaf in-rtm {
                                    type boolean;
                                    description "This value indicates if route is installed in rtm.";
                                }

                                container invalid-reason {
                                    description "Enter the invalid-reason context";

                                    leaf rejected-route {
                                        type boolean;
                                        description
                                            "The value indicates if route is temporarily rejected or
                                             rejected by the route policy.";
                                    }

                                    leaf as-loop {
                                        type boolean;
                                        description
                                            "This value indicates that the route has loops but peer doesn't
                                             have loop detection enabled.";
                                    }

                                    leaf next-hop-unresolved {
                                        type boolean;
                                        description
                                            "This value indicates that the route is not BGP route or VPN
                                             route and its next hop is not reachable.";
                                    }

                                    leaf cluster-loop {
                                        type boolean;
                                        description "The value indicate that the route is not valid due to cluster loop.";
                                    }

                                    leaf d-path-loop {
                                        type boolean;
                                        description
                                            "This value indicates that the route has D-Path with domain-id that
                                             matches one of the domain-ids configured locally.";
                                    }

                                } // container invalid-reason

                            } // list routes

                        } // container rib-in-post

                        container rib-out-post {
                            description "Enter the rib-out-post context";

                            list routes {
                                key "prefix neighbor path-id";
                                description "Enter the routes list instance";

                                leaf prefix {
                                    type types-sros:ipv4-prefix;
                                    description "Route prefix";
                                }

                                leaf neighbor {
                                    type types-sros:ip-address-with-zone;
                                    description "IP address of BGP neighbor";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf next-hop {
                                    type types-sros:ip-address;
                                    description "IP address of the destination router.";
                                }

                            } // list routes

                        } // container rib-out-post

                    } // container rib-in-out

                } // container ipv4-unicast

                container ipv6-unicast {
                    description "Enter the ipv6-unicast context";

                    container local-rib {
                        description "Enter the local-rib context";

                        list routes {
                            key "prefix neighbor owner router-instance-origin path-id";
                            description "Enter the routes list instance";

                            leaf prefix {
                                type types-sros:ipv6-prefix;
                                description "Route prefix";
                            }

                            leaf neighbor {
                                type types-sros:ip-address-with-zone;
                                description "IP address of BGP neighbor";
                            }

                            leaf owner {
                                type types-router:protocol-type;
                                description "BGP route owner";
                            }

                            leaf router-instance-origin {
                                type uint32;
                                description "Route instance origin value";
                            }

                            leaf path-id {
                                type uint64;
                                description "Path identifier of this route";
                            }

                            leaf attr-id {
                                type uint64;
                                description
                                    "The value represents attribute id of this route. The attribute
                                     defined by this id represents the attribute information of this
                                     route.";
                            }

                            leaf peer-router-id {
                                type types-sros:ip-address;
                                description "The value indicates peer router identifier for this route.";
                            }

                            leaf last-modified-date {
                                type yang:date-and-time;
                                description "Timestamp of when this path was last changed";
                            }

                            leaf used-route {
                                type boolean;
                                description "The value specifies if the route is used by the local BGP speaker.";
                            }

                            leaf valid-route {
                                type boolean;
                                description "This value is true when the route is usable";
                            }

                            leaf best-route {
                                type boolean;
                                description "This value specifies if the route is best or not";
                            }

                            leaf backup-route {
                                type boolean;
                                description "This value specifies if the route is backup route";
                            }

                            leaf group-best {
                                type boolean;
                                description
                                    "This value indicates if this route is group best when
                                     deterministic MED is set.";
                            }

                            leaf sticky-ecmp {
                                type boolean;
                                description
                                    "This value indicates if route is marked as sticky-ecmp by
                                     import policy.";
                            }

                            leaf stale-route {
                                type boolean;
                                description
                                    "This value indicates if route is stale due to BGP graceful
                                     restart.";
                            }

                            leaf unused-weight-only {
                                type boolean;
                                description "Indicates true if the route is unused, but being used for weight calculation";
                            }

                            leaf long-live-gr-stale {
                                type boolean;
                                description
                                    "This value indicates if route is stale due to BGP long live
                                     graceful restart.";
                            }

                            leaf rtm-install-disabled {
                                type boolean;
                                description "This value indicates if the route is not to be installed in routing table.";
                            }

                            leaf tie-break-reason {
                                type enumeration {
                                    enum unknown                        { value -1; }
                                    enum none                           { value 0; }
                                    enum origin                         { value 1; }
                                    enum as-path-length                 { value 2; }
                                    enum next-hop-cost                  { value 3; }
                                    enum med                            { value 4; }
                                    enum local-pref                     { value 5; }
                                    enum aggregator                     { value 6; }
                                    enum originator-id                  { value 7; }
                                    enum cluster-list                   { value 9; }
                                    enum extended-community             { value 10; }
                                    enum aigp                           { value 11; }
                                    enum missing-attribute              { value 12; }
                                    enum rtm-pref                       { value 13; }
                                    enum owner                          { value 14; }
                                    enum eigp-labeled                   { value 15; }
                                    enum vpn-route                      { value 16; }
                                    enum ebgp-route                     { value 17; }
                                    enum peer-ip                        { value 18; }
                                    enum local-peer                     { value 19; }
                                    enum multi-path                     { value 20; }
                                    enum vpn-rd                         { value 21; }
                                    enum next-hop-type                  { value 22; }
                                    enum invalid-route                  { value 23; }
                                    enum origin-validation              { value 24; }
                                    enum long-live-gr-stale             { value 25; }
                                    enum default-originate              { value 26; }
                                    enum rtm-install-disabled           { value 27; }
                                    enum peer-router-id                 { value 28; }
                                    enum path-identifier                { value 29; }
                                    enum d-path-length                  { value 30; }
                                    enum epe-route                      { value 31; }
                                }
                                description "Tie breaker reason for this route.";
                            }

                            leaf multipath-exclusion-reason {
                                type enumeration {
                                    enum none                           { value 0; }
                                    enum not-nexthop-diverse            { value 1; }
                                    enum not-multipath-eligible         { value 2; }
                                    enum max-paths-exceeded             { value 3; }
                                    enum not-same-exact-as-path         { value 4; }
                                    enum not-same-neighbor-as           { value 5; }
                                    enum longer-as-path                 { value 6; }
                                    enum resolving-type                 { value 7; }
                                    enum label-type                     { value 8; }
                                }
                                description "Multipath exclusion reason for this route.";
                            }

                            leaf origin-validation-state {
                                type enumeration {
                                    enum unknown                        { value -1; }
                                    enum not-applicable                 { value 0; }
                                    enum valid                          { value 1; }
                                    enum not-found                      { value 2; }
                                    enum invalid                        { value 3; }
                                }
                                description "Origin validation state of the route.";
                            }

                            leaf route-tag {
                                type uint32;
                                description "Router identifier.";
                            }

                            leaf forwarding-class {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "QoS association of the routes";
                            }

                            leaf priority {
                                type enumeration {
                                    enum high                           { value 0; }
                                    enum low                            { value 1; }
                                }
                                description "Route enqueuing priority.";
                            }

                            leaf rib-priority {
                                type enumeration {
                                    enum normal                         { value 0; }
                                    enum high                           { value 1; }
                                }
                                description "Rib priority.";
                            }

                            leaf source-class {
                                type uint8;
                                description "Source class index of the route.";
                            }

                            leaf destination-class {
                                type uint8;
                                description "Destination class index of the route.";
                            }

                            leaf add-paths-send-limit {
                                type union {
                                    type uint8;
                                    type enumeration {
                                        enum multipath {
                                            value -1;
                                            description "Indicates that the ECMP paths available for this routes will be advertised to peers using add-paths";
                                        }
                                    }
                                }
                                description "The value indicates max number of add paths allowed by the route.";
                            }

                            leaf leakable-route {
                                type boolean;
                                description "This value indicates if route is leak eligible";
                            }

                            leaf leaked-route {
                                type boolean;
                                description "This value indicates if route is leaked from another VRF.";
                            }

                            leaf label-value {
                                type uint32;
                                description "The MPLS label value.";
                            }

                            leaf in-rtm {
                                type boolean;
                                description "This value indicates if route is installed in rtm.";
                            }

                            container invalid-reason {
                                description "Enter the invalid-reason context";

                                leaf rejected-route {
                                    type boolean;
                                    description
                                        "The value indicates if route is temporarily rejected or
                                         rejected by the route policy.";
                                }

                                leaf as-loop {
                                    type boolean;
                                    description
                                        "This value indicates that the route has loops but peer doesn't
                                         have loop detection enabled.";
                                }

                                leaf next-hop-unresolved {
                                    type boolean;
                                    description
                                        "This value indicates that the route is not BGP route or VPN
                                         route and its next hop is not reachable.";
                                }

                                leaf cluster-loop {
                                    type boolean;
                                    description "The value indicate that the route is not valid due to cluster loop.";
                                }

                                leaf d-path-loop {
                                    type boolean;
                                    description
                                        "This value indicates that the route has D-Path with domain-id that
                                         matches one of the domain-ids configured locally.";
                                }

                            } // container invalid-reason

                        } // list routes

                    } // container local-rib

                    container rib-in-out {
                        description "Enter the rib-in-out context";

                        container rib-in-pre {
                            description "Enter the rib-in-pre context";

                            list routes {
                                key "prefix neighbor router-instance-origin path-id";
                                description "Enter the routes list instance";

                                leaf prefix {
                                    type types-sros:ipv6-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                            } // list routes

                        } // container rib-in-pre

                        container rib-in-post {
                            description "Enter the rib-in-post context";

                            list routes {
                                key "prefix neighbor router-instance-origin path-id";
                                description "Enter the routes list instance";

                                leaf prefix {
                                    type types-sros:ipv6-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf last-modified-date {
                                    type yang:date-and-time;
                                    description "Timestamp of when this path was last changed";
                                }

                                leaf used-route {
                                    type boolean;
                                    description "The value specifies if the route is used by the local BGP speaker.";
                                }

                                leaf valid-route {
                                    type boolean;
                                    description "This value is true when the route is usable";
                                }

                                leaf best-route {
                                    type boolean;
                                    description "This value specifies if the route is best or not";
                                }

                                leaf backup-route {
                                    type boolean;
                                    description "This value specifies if the route is backup route";
                                }

                                leaf group-best {
                                    type boolean;
                                    description
                                        "This value indicates if this route is group best when
                                         deterministic MED is set.";
                                }

                                leaf sticky-ecmp {
                                    type boolean;
                                    description
                                        "This value indicates if route is marked as sticky-ecmp by
                                         import policy.";
                                }

                                leaf stale-route {
                                    type boolean;
                                    description
                                        "This value indicates if route is stale due to BGP graceful
                                         restart.";
                                }

                                leaf unused-weight-only {
                                    type boolean;
                                    description "Indicates true if the route is unused, but being used for weight calculation";
                                }

                                leaf long-live-gr-stale {
                                    type boolean;
                                    description
                                        "This value indicates if route is stale due to BGP long live
                                         graceful restart.";
                                }

                                leaf rtm-install-disabled {
                                    type boolean;
                                    description "This value indicates if the route is not to be installed in routing table.";
                                }

                                leaf tie-break-reason {
                                    type enumeration {
                                        enum unknown                        { value -1; }
                                        enum none                           { value 0; }
                                        enum origin                         { value 1; }
                                        enum as-path-length                 { value 2; }
                                        enum next-hop-cost                  { value 3; }
                                        enum med                            { value 4; }
                                        enum local-pref                     { value 5; }
                                        enum aggregator                     { value 6; }
                                        enum originator-id                  { value 7; }
                                        enum cluster-list                   { value 9; }
                                        enum extended-community             { value 10; }
                                        enum aigp                           { value 11; }
                                        enum missing-attribute              { value 12; }
                                        enum rtm-pref                       { value 13; }
                                        enum owner                          { value 14; }
                                        enum eigp-labeled                   { value 15; }
                                        enum vpn-route                      { value 16; }
                                        enum ebgp-route                     { value 17; }
                                        enum peer-ip                        { value 18; }
                                        enum local-peer                     { value 19; }
                                        enum multi-path                     { value 20; }
                                        enum vpn-rd                         { value 21; }
                                        enum next-hop-type                  { value 22; }
                                        enum invalid-route                  { value 23; }
                                        enum origin-validation              { value 24; }
                                        enum long-live-gr-stale             { value 25; }
                                        enum default-originate              { value 26; }
                                        enum rtm-install-disabled           { value 27; }
                                        enum peer-router-id                 { value 28; }
                                        enum path-identifier                { value 29; }
                                        enum d-path-length                  { value 30; }
                                        enum epe-route                      { value 31; }
                                    }
                                    description "Tie breaker reason for this route.";
                                }

                                leaf multipath-exclusion-reason {
                                    type enumeration {
                                        enum none                           { value 0; }
                                        enum not-nexthop-diverse            { value 1; }
                                        enum not-multipath-eligible         { value 2; }
                                        enum max-paths-exceeded             { value 3; }
                                        enum not-same-exact-as-path         { value 4; }
                                        enum not-same-neighbor-as           { value 5; }
                                        enum longer-as-path                 { value 6; }
                                        enum resolving-type                 { value 7; }
                                        enum label-type                     { value 8; }
                                    }
                                    description "Multipath exclusion reason for this route.";
                                }

                                leaf origin-validation-state {
                                    type enumeration {
                                        enum unknown                        { value -1; }
                                        enum not-applicable                 { value 0; }
                                        enum valid                          { value 1; }
                                        enum not-found                      { value 2; }
                                        enum invalid                        { value 3; }
                                    }
                                    description "Origin validation state of the route.";
                                }

                                leaf route-tag {
                                    type uint32;
                                    description "Router identifier.";
                                }

                                leaf forwarding-class {
                                    type enumeration {
                                        enum be                             { value 0; }
                                        enum l2                             { value 1; }
                                        enum af                             { value 2; }
                                        enum l1                             { value 3; }
                                        enum h2                             { value 4; }
                                        enum ef                             { value 5; }
                                        enum h1                             { value 6; }
                                        enum nc                             { value 7; }
                                    }
                                    description "QoS association of the routes";
                                }

                                leaf priority {
                                    type enumeration {
                                        enum high                           { value 0; }
                                        enum low                            { value 1; }
                                    }
                                    description "Route enqueuing priority.";
                                }

                                leaf rib-priority {
                                    type enumeration {
                                        enum normal                         { value 0; }
                                        enum high                           { value 1; }
                                    }
                                    description "Rib priority.";
                                }

                                leaf source-class {
                                    type uint8;
                                    description "Source class index of the route.";
                                }

                                leaf destination-class {
                                    type uint8;
                                    description "Destination class index of the route.";
                                }

                                leaf add-paths-send-limit {
                                    type union {
                                        type uint8;
                                        type enumeration {
                                            enum multipath {
                                                value -1;
                                                description "Indicates that the ECMP paths available for this routes will be advertised to peers using add-paths";
                                            }
                                        }
                                    }
                                    description "The value indicates max number of add paths allowed by the route.";
                                }

                                leaf leakable-route {
                                    type boolean;
                                    description "This value indicates if route is leak eligible";
                                }

                                leaf leaked-route {
                                    type boolean;
                                    description "This value indicates if route is leaked from another VRF.";
                                }

                                leaf in-rtm {
                                    type boolean;
                                    description "This value indicates if route is installed in rtm.";
                                }

                                container invalid-reason {
                                    description "Enter the invalid-reason context";

                                    leaf rejected-route {
                                        type boolean;
                                        description
                                            "The value indicates if route is temporarily rejected or
                                             rejected by the route policy.";
                                    }

                                    leaf as-loop {
                                        type boolean;
                                        description
                                            "This value indicates that the route has loops but peer doesn't
                                             have loop detection enabled.";
                                    }

                                    leaf next-hop-unresolved {
                                        type boolean;
                                        description
                                            "This value indicates that the route is not BGP route or VPN
                                             route and its next hop is not reachable.";
                                    }

                                    leaf cluster-loop {
                                        type boolean;
                                        description "The value indicate that the route is not valid due to cluster loop.";
                                    }

                                    leaf d-path-loop {
                                        type boolean;
                                        description
                                            "This value indicates that the route has D-Path with domain-id that
                                             matches one of the domain-ids configured locally.";
                                    }

                                } // container invalid-reason

                            } // list routes

                        } // container rib-in-post

                        container rib-out-post {
                            description "Enter the rib-out-post context";

                            list routes {
                                key "prefix neighbor path-id";
                                description "Enter the routes list instance";

                                leaf prefix {
                                    type types-sros:ipv6-prefix;
                                    description "Route prefix";
                                }

                                leaf neighbor {
                                    type types-sros:ip-address-with-zone;
                                    description "IP address of BGP neighbor";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf next-hop {
                                    type types-sros:ip-address;
                                    description "IP address of the destination router.";
                                }

                            } // list routes

                        } // container rib-out-post

                    } // container rib-in-out

                } // container ipv6-unicast

                container label-ipv4 {
                    description "Enter the label-ipv4 context";

                    container local-rib {
                        description "Enter the local-rib context";

                        list routes {
                            key "prefix neighbor owner router-instance-origin path-id";
                            description "Enter the routes list instance";

                            leaf prefix {
                                type types-sros:ipv4-prefix;
                                description "Route prefix";
                            }

                            leaf neighbor {
                                type types-sros:ip-address-with-zone;
                                description "IP address of BGP neighbor";
                            }

                            leaf owner {
                                type types-router:protocol-type;
                                description "BGP route owner";
                            }

                            leaf router-instance-origin {
                                type uint32;
                                description "Route instance origin value";
                            }

                            leaf path-id {
                                type uint64;
                                description "Path identifier of this route";
                            }

                            leaf attr-id {
                                type uint64;
                                description
                                    "The value represents attribute id of this route. The attribute
                                     defined by this id represents the attribute information of this
                                     route.";
                            }

                            leaf peer-router-id {
                                type types-sros:ip-address;
                                description "The value indicates peer router identifier for this route.";
                            }

                            leaf last-modified-date {
                                type yang:date-and-time;
                                description "Timestamp of when this path was last changed";
                            }

                            leaf used-route {
                                type boolean;
                                description "The value specifies if the route is used by the local BGP speaker.";
                            }

                            leaf valid-route {
                                type boolean;
                                description "This value is true when the route is usable";
                            }

                            leaf best-route {
                                type boolean;
                                description "This value specifies if the route is best or not";
                            }

                            leaf backup-route {
                                type boolean;
                                description "This value specifies if the route is backup route";
                            }

                            leaf group-best {
                                type boolean;
                                description
                                    "This value indicates if this route is group best when
                                     deterministic MED is set.";
                            }

                            leaf sticky-ecmp {
                                type boolean;
                                description
                                    "This value indicates if route is marked as sticky-ecmp by
                                     import policy.";
                            }

                            leaf stale-route {
                                type boolean;
                                description
                                    "This value indicates if route is stale due to BGP graceful
                                     restart.";
                            }

                            leaf unused-weight-only {
                                type boolean;
                                description "Indicates true if the route is unused, but being used for weight calculation";
                            }

                            leaf long-live-gr-stale {
                                type boolean;
                                description
                                    "This value indicates if route is stale due to BGP long live
                                     graceful restart.";
                            }

                            leaf rtm-install-disabled {
                                type boolean;
                                description "This value indicates if the route is not to be installed in routing table.";
                            }

                            leaf tie-break-reason {
                                type enumeration {
                                    enum unknown                        { value -1; }
                                    enum none                           { value 0; }
                                    enum origin                         { value 1; }
                                    enum as-path-length                 { value 2; }
                                    enum next-hop-cost                  { value 3; }
                                    enum med                            { value 4; }
                                    enum local-pref                     { value 5; }
                                    enum aggregator                     { value 6; }
                                    enum originator-id                  { value 7; }
                                    enum cluster-list                   { value 9; }
                                    enum extended-community             { value 10; }
                                    enum aigp                           { value 11; }
                                    enum missing-attribute              { value 12; }
                                    enum rtm-pref                       { value 13; }
                                    enum owner                          { value 14; }
                                    enum eigp-labeled                   { value 15; }
                                    enum vpn-route                      { value 16; }
                                    enum ebgp-route                     { value 17; }
                                    enum peer-ip                        { value 18; }
                                    enum local-peer                     { value 19; }
                                    enum multi-path                     { value 20; }
                                    enum vpn-rd                         { value 21; }
                                    enum next-hop-type                  { value 22; }
                                    enum invalid-route                  { value 23; }
                                    enum origin-validation              { value 24; }
                                    enum long-live-gr-stale             { value 25; }
                                    enum default-originate              { value 26; }
                                    enum rtm-install-disabled           { value 27; }
                                    enum peer-router-id                 { value 28; }
                                    enum path-identifier                { value 29; }
                                    enum d-path-length                  { value 30; }
                                    enum epe-route                      { value 31; }
                                }
                                description "Tie breaker reason for this route.";
                            }

                            leaf multipath-exclusion-reason {
                                type enumeration {
                                    enum none                           { value 0; }
                                    enum not-nexthop-diverse            { value 1; }
                                    enum not-multipath-eligible         { value 2; }
                                    enum max-paths-exceeded             { value 3; }
                                    enum not-same-exact-as-path         { value 4; }
                                    enum not-same-neighbor-as           { value 5; }
                                    enum longer-as-path                 { value 6; }
                                    enum resolving-type                 { value 7; }
                                    enum label-type                     { value 8; }
                                }
                                description "Multipath exclusion reason for this route.";
                            }

                            leaf origin-validation-state {
                                type enumeration {
                                    enum unknown                        { value -1; }
                                    enum not-applicable                 { value 0; }
                                    enum valid                          { value 1; }
                                    enum not-found                      { value 2; }
                                    enum invalid                        { value 3; }
                                }
                                description "Origin validation state of the route.";
                            }

                            leaf route-tag {
                                type uint32;
                                description "Router identifier.";
                            }

                            leaf forwarding-class {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "QoS association of the routes";
                            }

                            leaf priority {
                                type enumeration {
                                    enum high                           { value 0; }
                                    enum low                            { value 1; }
                                }
                                description "Route enqueuing priority.";
                            }

                            leaf rib-priority {
                                type enumeration {
                                    enum normal                         { value 0; }
                                    enum high                           { value 1; }
                                }
                                description "Rib priority.";
                            }

                            leaf source-class {
                                type uint8;
                                description "Source class index of the route.";
                            }

                            leaf destination-class {
                                type uint8;
                                description "Destination class index of the route.";
                            }

                            leaf add-paths-send-limit {
                                type union {
                                    type uint8;
                                    type enumeration {
                                        enum multipath {
                                            value -1;
                                            description "Indicates that the ECMP paths available for this routes will be advertised to peers using add-paths";
                                        }
                                    }
                                }
                                description "The value indicates max number of add paths allowed by the route.";
                            }

                            leaf leakable-route {
                                type boolean;
                                description "This value indicates if route is leak eligible";
                            }

                            leaf leaked-route {
                                type boolean;
                                description "This value indicates if route is leaked from another VRF.";
                            }

                            leaf conflict-sid {
                                type boolean;
                                description "This value indicates if route sid is not valid";
                            }

                            leaf label-value {
                                type uint32;
                                description "The MPLS label value.";
                            }

                            leaf in-rtm {
                                type boolean;
                                description "This value indicates if route is installed in rtm.";
                            }

                            leaf in-ttm {
                                type boolean;
                                description "This value indicates if route is installed in ttm.";
                            }

                            container invalid-reason {
                                description "Enter the invalid-reason context";

                                leaf rejected-route {
                                    type boolean;
                                    description
                                        "The value indicates if route is temporarily rejected or
                                         rejected by the route policy.";
                                }

                                leaf as-loop {
                                    type boolean;
                                    description
                                        "This value indicates that the route has loops but peer doesn't
                                         have loop detection enabled.";
                                }

                                leaf next-hop-unresolved {
                                    type boolean;
                                    description
                                        "This value indicates that the route is not BGP route or VPN
                                         route and its next hop is not reachable.";
                                }

                                leaf cluster-loop {
                                    type boolean;
                                    description "The value indicate that the route is not valid due to cluster loop.";
                                }

                                leaf d-path-loop {
                                    type boolean;
                                    description
                                        "This value indicates that the route has D-Path with domain-id that
                                         matches one of the domain-ids configured locally.";
                                }

                            } // container invalid-reason

                        } // list routes

                    } // container local-rib

                    container rib-in-out {
                        description "Enter the rib-in-out context";

                        container rib-in-pre {
                            description "Enter the rib-in-pre context";

                            list routes {
                                key "prefix neighbor router-instance-origin path-id";
                                description "Enter the routes list instance";

                                leaf prefix {
                                    type types-sros:ipv4-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                            } // list routes

                        } // container rib-in-pre

                        container rib-in-post {
                            description "Enter the rib-in-post context";

                            list routes {
                                key "prefix neighbor router-instance-origin path-id";
                                description "Enter the routes list instance";

                                leaf prefix {
                                    type types-sros:ipv4-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                                leaf last-modified-date {
                                    type yang:date-and-time;
                                    description "Timestamp of when this path was last changed";
                                }

                                leaf used-route {
                                    type boolean;
                                    description "The value specifies if the route is used by the local BGP speaker.";
                                }

                                leaf valid-route {
                                    type boolean;
                                    description "This value is true when the route is usable";
                                }

                                leaf best-route {
                                    type boolean;
                                    description "This value specifies if the route is best or not";
                                }

                                leaf backup-route {
                                    type boolean;
                                    description "This value specifies if the route is backup route";
                                }

                                leaf group-best {
                                    type boolean;
                                    description
                                        "This value indicates if this route is group best when
                                         deterministic MED is set.";
                                }

                                leaf sticky-ecmp {
                                    type boolean;
                                    description
                                        "This value indicates if route is marked as sticky-ecmp by
                                         import policy.";
                                }

                                leaf stale-route {
                                    type boolean;
                                    description
                                        "This value indicates if route is stale due to BGP graceful
                                         restart.";
                                }

                                leaf unused-weight-only {
                                    type boolean;
                                    description "Indicates true if the route is unused, but being used for weight calculation";
                                }

                                leaf long-live-gr-stale {
                                    type boolean;
                                    description
                                        "This value indicates if route is stale due to BGP long live
                                         graceful restart.";
                                }

                                leaf rtm-install-disabled {
                                    type boolean;
                                    description "This value indicates if the route is not to be installed in routing table.";
                                }

                                leaf tie-break-reason {
                                    type enumeration {
                                        enum unknown                        { value -1; }
                                        enum none                           { value 0; }
                                        enum origin                         { value 1; }
                                        enum as-path-length                 { value 2; }
                                        enum next-hop-cost                  { value 3; }
                                        enum med                            { value 4; }
                                        enum local-pref                     { value 5; }
                                        enum aggregator                     { value 6; }
                                        enum originator-id                  { value 7; }
                                        enum cluster-list                   { value 9; }
                                        enum extended-community             { value 10; }
                                        enum aigp                           { value 11; }
                                        enum missing-attribute              { value 12; }
                                        enum rtm-pref                       { value 13; }
                                        enum owner                          { value 14; }
                                        enum eigp-labeled                   { value 15; }
                                        enum vpn-route                      { value 16; }
                                        enum ebgp-route                     { value 17; }
                                        enum peer-ip                        { value 18; }
                                        enum local-peer                     { value 19; }
                                        enum multi-path                     { value 20; }
                                        enum vpn-rd                         { value 21; }
                                        enum next-hop-type                  { value 22; }
                                        enum invalid-route                  { value 23; }
                                        enum origin-validation              { value 24; }
                                        enum long-live-gr-stale             { value 25; }
                                        enum default-originate              { value 26; }
                                        enum rtm-install-disabled           { value 27; }
                                        enum peer-router-id                 { value 28; }
                                        enum path-identifier                { value 29; }
                                        enum d-path-length                  { value 30; }
                                        enum epe-route                      { value 31; }
                                    }
                                    description "Tie breaker reason for this route.";
                                }

                                leaf multipath-exclusion-reason {
                                    type enumeration {
                                        enum none                           { value 0; }
                                        enum not-nexthop-diverse            { value 1; }
                                        enum not-multipath-eligible         { value 2; }
                                        enum max-paths-exceeded             { value 3; }
                                        enum not-same-exact-as-path         { value 4; }
                                        enum not-same-neighbor-as           { value 5; }
                                        enum longer-as-path                 { value 6; }
                                        enum resolving-type                 { value 7; }
                                        enum label-type                     { value 8; }
                                    }
                                    description "Multipath exclusion reason for this route.";
                                }

                                leaf origin-validation-state {
                                    type enumeration {
                                        enum unknown                        { value -1; }
                                        enum not-applicable                 { value 0; }
                                        enum valid                          { value 1; }
                                        enum not-found                      { value 2; }
                                        enum invalid                        { value 3; }
                                    }
                                    description "Origin validation state of the route.";
                                }

                                leaf route-tag {
                                    type uint32;
                                    description "Router identifier.";
                                }

                                leaf forwarding-class {
                                    type enumeration {
                                        enum be                             { value 0; }
                                        enum l2                             { value 1; }
                                        enum af                             { value 2; }
                                        enum l1                             { value 3; }
                                        enum h2                             { value 4; }
                                        enum ef                             { value 5; }
                                        enum h1                             { value 6; }
                                        enum nc                             { value 7; }
                                    }
                                    description "QoS association of the routes";
                                }

                                leaf priority {
                                    type enumeration {
                                        enum high                           { value 0; }
                                        enum low                            { value 1; }
                                    }
                                    description "Route enqueuing priority.";
                                }

                                leaf rib-priority {
                                    type enumeration {
                                        enum normal                         { value 0; }
                                        enum high                           { value 1; }
                                    }
                                    description "Rib priority.";
                                }

                                leaf source-class {
                                    type uint8;
                                    description "Source class index of the route.";
                                }

                                leaf destination-class {
                                    type uint8;
                                    description "Destination class index of the route.";
                                }

                                leaf add-paths-send-limit {
                                    type union {
                                        type uint8;
                                        type enumeration {
                                            enum multipath {
                                                value -1;
                                                description "Indicates that the ECMP paths available for this routes will be advertised to peers using add-paths";
                                            }
                                        }
                                    }
                                    description "The value indicates max number of add paths allowed by the route.";
                                }

                                leaf leakable-route {
                                    type boolean;
                                    description "This value indicates if route is leak eligible";
                                }

                                leaf leaked-route {
                                    type boolean;
                                    description "This value indicates if route is leaked from another VRF.";
                                }

                                leaf conflict-sid {
                                    type boolean;
                                    description "This value indicates if route sid is not valid";
                                }

                                leaf in-rtm {
                                    type boolean;
                                    description "This value indicates if route is installed in rtm.";
                                }

                                leaf in-ttm {
                                    type boolean;
                                    description "This value indicates if route is installed in ttm.";
                                }

                                container invalid-reason {
                                    description "Enter the invalid-reason context";

                                    leaf rejected-route {
                                        type boolean;
                                        description
                                            "The value indicates if route is temporarily rejected or
                                             rejected by the route policy.";
                                    }

                                    leaf as-loop {
                                        type boolean;
                                        description
                                            "This value indicates that the route has loops but peer doesn't
                                             have loop detection enabled.";
                                    }

                                    leaf next-hop-unresolved {
                                        type boolean;
                                        description
                                            "This value indicates that the route is not BGP route or VPN
                                             route and its next hop is not reachable.";
                                    }

                                    leaf cluster-loop {
                                        type boolean;
                                        description "The value indicate that the route is not valid due to cluster loop.";
                                    }

                                    leaf d-path-loop {
                                        type boolean;
                                        description
                                            "This value indicates that the route has D-Path with domain-id that
                                             matches one of the domain-ids configured locally.";
                                    }

                                } // container invalid-reason

                            } // list routes

                        } // container rib-in-post

                        container rib-out-post {
                            description "Enter the rib-out-post context";

                            list routes {
                                key "prefix neighbor path-id";
                                description "Enter the routes list instance";

                                leaf prefix {
                                    type types-sros:ipv4-prefix;
                                    description "Route prefix";
                                }

                                leaf neighbor {
                                    type types-sros:ip-address-with-zone;
                                    description "IP address of BGP neighbor";
                                }

                                leaf path-id {
                                    type uint64;
                                    description "Path identifier of this route";
                                }

                                leaf label-type {
                                    type enumeration {
                                        enum unchanged                      { value 1; }
                                        enum pop                            { value 2; }
                                        enum swap                           { value 3; }
                                        enum sr-pop                         { value 4; }
                                        enum sr-swap                        { value 5; }
                                    }
                                }

                                leaf label-mode {
                                    type enumeration {
                                        enum next-hop                       { value 1; }
                                        enum per-prefix                     { value 2; }
                                        enum epe                            { value 3; }
                                        enum explicit-null                  { value 4; }
                                    }
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                                leaf next-hop {
                                    type types-sros:ip-address;
                                    description "IP address of the destination router.";
                                }

                            } // list routes

                        } // container rib-out-post

                    } // container rib-in-out

                    list label-ipv4-statistics {
                        key "prefix";
                        description "Enter the label-ipv4-statistics list instance";

                        leaf prefix {
                            type types-sros:ipv4-prefix;
                            description "Route prefix";
                        }

                        container ingress-statistics {
                            description "Enter the ingress-statistics context";

                            leaf packets {
                                type uint64;
                                description "Number of packets for this route.";
                            }

                            leaf octets {
                                type uint64;
                                description "Number of octets for this route.";
                            }

                            leaf oper-state {
                                type types-sros:oper-state;
                                description "The value indicates the current operational state.";
                            }

                        } // container ingress-statistics

                        container egress-statistics {
                            description "Enter the egress-statistics context";

                            leaf packets {
                                type uint64;
                                description "Number of packets for this route.";
                            }

                            leaf octets {
                                type uint64;
                                description "Number of octets for this route.";
                            }

                            leaf oper-state {
                                type types-sros:oper-state;
                                description "The value indicates the current operational state.";
                            }

                        } // container egress-statistics

                    } // list label-ipv4-statistics

                } // container label-ipv4

                container label-ipv6 {
                    description "Enter the label-ipv6 context";

                    container local-rib {
                        description "Enter the local-rib context";

                        list routes {
                            key "prefix neighbor owner router-instance-origin path-id";
                            description "Enter the routes list instance";

                            leaf prefix {
                                type types-sros:ipv6-prefix;
                                description "Route prefix";
                            }

                            leaf neighbor {
                                type types-sros:ip-address-with-zone;
                                description "IP address of BGP neighbor";
                            }

                            leaf owner {
                                type types-router:protocol-type;
                                description "BGP route owner";
                            }

                            leaf router-instance-origin {
                                type uint32;
                                description "Route instance origin value";
                            }

                            leaf path-id {
                                type uint64;
                                description "Path identifier of this route";
                            }

                            leaf attr-id {
                                type uint64;
                                description
                                    "The value represents attribute id of this route. The attribute
                                     defined by this id represents the attribute information of this
                                     route.";
                            }

                            leaf peer-router-id {
                                type types-sros:ip-address;
                                description "The value indicates peer router identifier for this route.";
                            }

                            leaf last-modified-date {
                                type yang:date-and-time;
                                description "Timestamp of when this path was last changed";
                            }

                            leaf used-route {
                                type boolean;
                                description "The value specifies if the route is used by the local BGP speaker.";
                            }

                            leaf valid-route {
                                type boolean;
                                description "This value is true when the route is usable";
                            }

                            leaf best-route {
                                type boolean;
                                description "This value specifies if the route is best or not";
                            }

                            leaf backup-route {
                                type boolean;
                                description "This value specifies if the route is backup route";
                            }

                            leaf group-best {
                                type boolean;
                                description
                                    "This value indicates if this route is group best when
                                     deterministic MED is set.";
                            }

                            leaf sticky-ecmp {
                                type boolean;
                                description
                                    "This value indicates if route is marked as sticky-ecmp by
                                     import policy.";
                            }

                            leaf stale-route {
                                type boolean;
                                description
                                    "This value indicates if route is stale due to BGP graceful
                                     restart.";
                            }

                            leaf unused-weight-only {
                                type boolean;
                                description "Indicates true if the route is unused, but being used for weight calculation";
                            }

                            leaf long-live-gr-stale {
                                type boolean;
                                description
                                    "This value indicates if route is stale due to BGP long live
                                     graceful restart.";
                            }

                            leaf rtm-install-disabled {
                                type boolean;
                                description "This value indicates if the route is not to be installed in routing table.";
                            }

                            leaf tie-break-reason {
                                type enumeration {
                                    enum unknown                        { value -1; }
                                    enum none                           { value 0; }
                                    enum origin                         { value 1; }
                                    enum as-path-length                 { value 2; }
                                    enum next-hop-cost                  { value 3; }
                                    enum med                            { value 4; }
                                    enum local-pref                     { value 5; }
                                    enum aggregator                     { value 6; }
                                    enum originator-id                  { value 7; }
                                    enum cluster-list                   { value 9; }
                                    enum extended-community             { value 10; }
                                    enum aigp                           { value 11; }
                                    enum missing-attribute              { value 12; }
                                    enum rtm-pref                       { value 13; }
                                    enum owner                          { value 14; }
                                    enum eigp-labeled                   { value 15; }
                                    enum vpn-route                      { value 16; }
                                    enum ebgp-route                     { value 17; }
                                    enum peer-ip                        { value 18; }
                                    enum local-peer                     { value 19; }
                                    enum multi-path                     { value 20; }
                                    enum vpn-rd                         { value 21; }
                                    enum next-hop-type                  { value 22; }
                                    enum invalid-route                  { value 23; }
                                    enum origin-validation              { value 24; }
                                    enum long-live-gr-stale             { value 25; }
                                    enum default-originate              { value 26; }
                                    enum rtm-install-disabled           { value 27; }
                                    enum peer-router-id                 { value 28; }
                                    enum path-identifier                { value 29; }
                                    enum d-path-length                  { value 30; }
                                    enum epe-route                      { value 31; }
                                }
                                description "Tie breaker reason for this route.";
                            }

                            leaf multipath-exclusion-reason {
                                type enumeration {
                                    enum none                           { value 0; }
                                    enum not-nexthop-diverse            { value 1; }
                                    enum not-multipath-eligible         { value 2; }
                                    enum max-paths-exceeded             { value 3; }
                                    enum not-same-exact-as-path         { value 4; }
                                    enum not-same-neighbor-as           { value 5; }
                                    enum longer-as-path                 { value 6; }
                                    enum resolving-type                 { value 7; }
                                    enum label-type                     { value 8; }
                                }
                                description "Multipath exclusion reason for this route.";
                            }

                            leaf origin-validation-state {
                                type enumeration {
                                    enum unknown                        { value -1; }
                                    enum not-applicable                 { value 0; }
                                    enum valid                          { value 1; }
                                    enum not-found                      { value 2; }
                                    enum invalid                        { value 3; }
                                }
                                description "Origin validation state of the route.";
                            }

                            leaf route-tag {
                                type uint32;
                                description "Router identifier.";
                            }

                            leaf forwarding-class {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "QoS association of the routes";
                            }

                            leaf priority {
                                type enumeration {
                                    enum high                           { value 0; }
                                    enum low                            { value 1; }
                                }
                                description "Route enqueuing priority.";
                            }

                            leaf rib-priority {
                                type enumeration {
                                    enum normal                         { value 0; }
                                    enum high                           { value 1; }
                                }
                                description "Rib priority.";
                            }

                            leaf source-class {
                                type uint8;
                                description "Source class index of the route.";
                            }

                            leaf destination-class {
                                type uint8;
                                description "Destination class index of the route.";
                            }

                            leaf add-paths-send-limit {
                                type union {
                                    type uint8;
                                    type enumeration {
                                        enum multipath {
                                            value -1;
                                            description "Indicates that the ECMP paths available for this routes will be advertised to peers using add-paths";
                                        }
                                    }
                                }
                                description "The value indicates max number of add paths allowed by the route.";
                            }

                            leaf label-value {
                                type uint32;
                                description "The MPLS label value.";
                            }

                            leaf in-rtm {
                                type boolean;
                                description "This value indicates if route is installed in rtm.";
                            }

                            leaf in-ttm {
                                type boolean;
                                description "This value indicates if route is installed in ttm.";
                            }

                            container invalid-reason {
                                description "Enter the invalid-reason context";

                                leaf rejected-route {
                                    type boolean;
                                    description
                                        "The value indicates if route is temporarily rejected or
                                         rejected by the route policy.";
                                }

                                leaf as-loop {
                                    type boolean;
                                    description
                                        "This value indicates that the route has loops but peer doesn't
                                         have loop detection enabled.";
                                }

                                leaf next-hop-unresolved {
                                    type boolean;
                                    description
                                        "This value indicates that the route is not BGP route or VPN
                                         route and its next hop is not reachable.";
                                }

                                leaf cluster-loop {
                                    type boolean;
                                    description "The value indicate that the route is not valid due to cluster loop.";
                                }

                                leaf d-path-loop {
                                    type boolean;
                                    description
                                        "This value indicates that the route has D-Path with domain-id that
                                         matches one of the domain-ids configured locally.";
                                }

                            } // container invalid-reason

                        } // list routes

                    } // container local-rib

                    container rib-in-out {
                        description "Enter the rib-in-out context";

                        container rib-in-pre {
                            description "Enter the rib-in-pre context";

                            list routes {
                                key "prefix neighbor router-instance-origin path-id";
                                description "Enter the routes list instance";

                                leaf prefix {
                                    type types-sros:ipv6-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                            } // list routes

                        } // container rib-in-pre

                        container rib-in-post {
                            description "Enter the rib-in-post context";

                            list routes {
                                key "prefix neighbor router-instance-origin path-id";
                                description "Enter the routes list instance";

                                leaf prefix {
                                    type types-sros:ipv6-prefix;
                                    description "Route prefix";
                                }

                                leaf neighbor {
                                    type types-sros:ip-address-with-zone;
                                    description "IP address of BGP neighbor";
                                }

                                leaf router-instance-origin {
                                    type uint32;
                                    description "Route instance origin value";
                                }

                                leaf path-id {
                                    type uint64;
                                    description "Path identifier of this route";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf label-value {
                                    type uint32;
                                    description "The MPLS label value.";
                                }

                                leaf last-modified-date {
                                    type yang:date-and-time;
                                    description "Timestamp of when this path was last changed";
                                }

                                leaf used-route {
                                    type boolean;
                                    description "The value specifies if the route is used by the local BGP speaker.";
                                }

                                leaf valid-route {
                                    type boolean;
                                    description "This value is true when the route is usable";
                                }

                                leaf best-route {
                                    type boolean;
                                    description "This value specifies if the route is best or not";
                                }

                                leaf backup-route {
                                    type boolean;
                                    description "This value specifies if the route is backup route";
                                }

                                leaf group-best {
                                    type boolean;
                                    description
                                        "This value indicates if this route is group best when
                                         deterministic MED is set.";
                                }

                                leaf sticky-ecmp {
                                    type boolean;
                                    description
                                        "This value indicates if route is marked as sticky-ecmp by
                                         import policy.";
                                }

                                leaf stale-route {
                                    type boolean;
                                    description
                                        "This value indicates if route is stale due to BGP graceful
                                         restart.";
                                }

                                leaf unused-weight-only {
                                    type boolean;
                                    description "Indicates true if the route is unused, but being used for weight calculation";
                                }

                                leaf long-live-gr-stale {
                                    type boolean;
                                    description
                                        "This value indicates if route is stale due to BGP long live
                                         graceful restart.";
                                }

                                leaf rtm-install-disabled {
                                    type boolean;
                                    description "This value indicates if the route is not to be installed in routing table.";
                                }

                                leaf tie-break-reason {
                                    type enumeration {
                                        enum unknown                        { value -1; }
                                        enum none                           { value 0; }
                                        enum origin                         { value 1; }
                                        enum as-path-length                 { value 2; }
                                        enum next-hop-cost                  { value 3; }
                                        enum med                            { value 4; }
                                        enum local-pref                     { value 5; }
                                        enum aggregator                     { value 6; }
                                        enum originator-id                  { value 7; }
                                        enum cluster-list                   { value 9; }
                                        enum extended-community             { value 10; }
                                        enum aigp                           { value 11; }
                                        enum missing-attribute              { value 12; }
                                        enum rtm-pref                       { value 13; }
                                        enum owner                          { value 14; }
                                        enum eigp-labeled                   { value 15; }
                                        enum vpn-route                      { value 16; }
                                        enum ebgp-route                     { value 17; }
                                        enum peer-ip                        { value 18; }
                                        enum local-peer                     { value 19; }
                                        enum multi-path                     { value 20; }
                                        enum vpn-rd                         { value 21; }
                                        enum next-hop-type                  { value 22; }
                                        enum invalid-route                  { value 23; }
                                        enum origin-validation              { value 24; }
                                        enum long-live-gr-stale             { value 25; }
                                        enum default-originate              { value 26; }
                                        enum rtm-install-disabled           { value 27; }
                                        enum peer-router-id                 { value 28; }
                                        enum path-identifier                { value 29; }
                                        enum d-path-length                  { value 30; }
                                        enum epe-route                      { value 31; }
                                    }
                                    description "Tie breaker reason for this route.";
                                }

                                leaf multipath-exclusion-reason {
                                    type enumeration {
                                        enum none                           { value 0; }
                                        enum not-nexthop-diverse            { value 1; }
                                        enum not-multipath-eligible         { value 2; }
                                        enum max-paths-exceeded             { value 3; }
                                        enum not-same-exact-as-path         { value 4; }
                                        enum not-same-neighbor-as           { value 5; }
                                        enum longer-as-path                 { value 6; }
                                        enum resolving-type                 { value 7; }
                                        enum label-type                     { value 8; }
                                    }
                                    description "Multipath exclusion reason for this route.";
                                }

                                leaf origin-validation-state {
                                    type enumeration {
                                        enum unknown                        { value -1; }
                                        enum not-applicable                 { value 0; }
                                        enum valid                          { value 1; }
                                        enum not-found                      { value 2; }
                                        enum invalid                        { value 3; }
                                    }
                                    description "Origin validation state of the route.";
                                }

                                leaf route-tag {
                                    type uint32;
                                    description "Router identifier.";
                                }

                                leaf forwarding-class {
                                    type enumeration {
                                        enum be                             { value 0; }
                                        enum l2                             { value 1; }
                                        enum af                             { value 2; }
                                        enum l1                             { value 3; }
                                        enum h2                             { value 4; }
                                        enum ef                             { value 5; }
                                        enum h1                             { value 6; }
                                        enum nc                             { value 7; }
                                    }
                                    description "QoS association of the routes";
                                }

                                leaf priority {
                                    type enumeration {
                                        enum high                           { value 0; }
                                        enum low                            { value 1; }
                                    }
                                    description "Route enqueuing priority.";
                                }

                                leaf rib-priority {
                                    type enumeration {
                                        enum normal                         { value 0; }
                                        enum high                           { value 1; }
                                    }
                                    description "Rib priority.";
                                }

                                leaf source-class {
                                    type uint8;
                                    description "Source class index of the route.";
                                }

                                leaf destination-class {
                                    type uint8;
                                    description "Destination class index of the route.";
                                }

                                leaf add-paths-send-limit {
                                    type union {
                                        type uint8;
                                        type enumeration {
                                            enum multipath {
                                                value -1;
                                                description "Indicates that the ECMP paths available for this routes will be advertised to peers using add-paths";
                                            }
                                        }
                                    }
                                    description "The value indicates max number of add paths allowed by the route.";
                                }

                                leaf in-rtm {
                                    type boolean;
                                    description "This value indicates if route is installed in rtm.";
                                }

                                leaf in-ttm {
                                    type boolean;
                                    description "This value indicates if route is installed in ttm.";
                                }

                                container invalid-reason {
                                    description "Enter the invalid-reason context";

                                    leaf rejected-route {
                                        type boolean;
                                        description
                                            "The value indicates if route is temporarily rejected or
                                             rejected by the route policy.";
                                    }

                                    leaf as-loop {
                                        type boolean;
                                        description
                                            "This value indicates that the route has loops but peer doesn't
                                             have loop detection enabled.";
                                    }

                                    leaf next-hop-unresolved {
                                        type boolean;
                                        description
                                            "This value indicates that the route is not BGP route or VPN
                                             route and its next hop is not reachable.";
                                    }

                                    leaf cluster-loop {
                                        type boolean;
                                        description "The value indicate that the route is not valid due to cluster loop.";
                                    }

                                    leaf d-path-loop {
                                        type boolean;
                                        description
                                            "This value indicates that the route has D-Path with domain-id that
                                             matches one of the domain-ids configured locally.";
                                    }

                                } // container invalid-reason

                            } // list routes

                        } // container rib-in-post

                        container rib-out-post {
                            description "Enter the rib-out-post context";

                            list routes {
                                key "prefix neighbor path-id";
                                description "Enter the routes list instance";

                                leaf prefix {
                                    type types-sros:ipv6-prefix;
                                    description "Route prefix";
                                }

                                leaf neighbor {
                                    type types-sros:ip-address-with-zone;
                                    description "IP address of BGP neighbor";
                                }

                                leaf path-id {
                                    type uint64;
                                    description "Path identifier of this route";
                                }

                                leaf label-type {
                                    type enumeration {
                                        enum unchanged                      { value 1; }
                                        enum pop                            { value 2; }
                                        enum swap                           { value 3; }
                                        enum sr-pop                         { value 4; }
                                        enum sr-swap                        { value 5; }
                                    }
                                }

                                leaf label-mode {
                                    type enumeration {
                                        enum next-hop                       { value 1; }
                                        enum per-prefix                     { value 2; }
                                        enum epe                            { value 3; }
                                        enum explicit-null                  { value 4; }
                                    }
                                }

                                leaf label-value {
                                    type uint32;
                                    description "The MPLS label value.";
                                }

                                leaf attr-id {
                                    type uint64;
                                    description
                                        "The value represents attribute id of this route. The attribute
                                         defined by this id represents the attribute information of this
                                         route.";
                                }

                                leaf peer-router-id {
                                    type types-sros:ip-address;
                                    description "The value indicates peer router identifier for this route.";
                                }

                                leaf next-hop {
                                    type types-sros:ip-address;
                                    description "IP address of the destination router.";
                                }

                            } // list routes

                        } // container rib-out-post

                    } // container rib-in-out

                    list label-ipv6-statistics {
                        key "prefix";
                        description "Enter the label-ipv6-statistics list instance";

                        leaf prefix {
                            type types-sros:ipv6-prefix;
                            description "Route prefix";
                        }

                        container ingress-statistics {
                            description "Enter the ingress-statistics context";

                            leaf packets {
                                type uint64;
                                description "Number of packets for this route.";
                            }

                            leaf octets {
                                type uint64;
                                description "Number of octets for this route.";
                            }

                            leaf oper-state {
                                type types-sros:oper-state;
                                description "The value indicates the current operational state.";
                            }

                        } // container ingress-statistics

                        container egress-statistics {
                            description "Enter the egress-statistics context";

                            leaf packets {
                                type uint64;
                                description "Number of packets for this route.";
                            }

                            leaf octets {
                                type uint64;
                                description "Number of octets for this route.";
                            }

                            leaf oper-state {
                                type types-sros:oper-state;
                                description "The value indicates the current operational state.";
                            }

                        } // container egress-statistics

                    } // list label-ipv6-statistics

                } // container label-ipv6









                container attr-sets {
                    description "Enter the attr-sets context";

                    list attr-set {
                        key "route-type index";
                        description "Enter the attr-set list instance";

                        leaf route-type {
                            type enumeration {
                                enum rib-in                         { value 1; }
                                enum rib-out                        { value 2; }
                            }
                            description "RIB type";
                        }

                        leaf index {
                            type uint64;
                            description "RIB attribute index";
                        }

                        leaf origin {
                            type enumeration {
                                enum igp                            { value 0; }
                                enum egp                            { value 1; }
                                enum incomplete                     { value 2; }
                            }
                            description
                                "This the mandatory attribute which defines the path originator

                                 'igp' means Network Layer Reachability Information interior to
                                 the originating AS.

                                 'egp' means Network Layer Reachability Information is learned
                                 via EGP protocol.

                                 'incomplete' means Network Layer Reachability Information is
                                 learned by some other means.";
                        }

                        leaf atomic-aggregate {
                            type boolean;
                            description
                                "This value will be true when as-path does not include
                                 all the AS numbers used to aggregate several routes.";
                        }

                        leaf next-hop {
                            type types-sros:ip-address;
                            description "IP address of the destination router.";
                        }

                        leaf med {
                            type uint32;
                            description
                                "This is used when external (inter-AS) links have multiple exit
                                 or entry points to same neighboring AS";
                        }

                        leaf local-pref {
                            type uint32;
                            description
                                "This value represents degree of preference for an advertised
                                 route to other internal peers.";
                        }

                        leaf originator-id {
                            type types-sros:ipv4-address;
                            description
                                "This value represents BGP Id of the route originator
                                 in local AS";
                        }

                        leaf aigp {
                            type uint64;
                            description "This value represents accumulated IGP metric";
                        }

                        container as-path {
                            description "Enter the as-path context";

                            list segment {
                                key "segment-index";
                                description "Enter the segment list instance";

                                leaf segment-index {
                                    type uint32;
                                    description "RIB attribute AS Path segment index";
                                }

                                leaf type {
                                    type enumeration {
                                        enum as-set                         { value 1; }
                                        enum as-sequence                    { value 2; }
                                        enum as-confed-sequence             { value 3; }
                                        enum as-confed-set                  { value 4; }
                                    }
                                    description
                                        "AS Path segment type.
                                         'as-set' means unordered set of autonomous systems that this
                                         route has traversed.
                                         'as-sequence' means ordered set of autonomous systems that this
                                         route has traversed.
                                         'as-confed-sequence' means ordered set of Member Autonomous
                                         Systems that this route has traversed.
                                         'as-confed-set' means ordered set of Member Autonomous Systems
                                         this route has traversed.";
                                }

                                list as-numbers {
                                    key "as-number-index";
                                    description "Enter the as-numbers list instance";

                                    leaf as-number-index {
                                        type uint32;
                                        description "RIB attribute AS Path AS-number index";
                                    }

                                    leaf as-number {
                                        type inet:as-number;
                                        description "Autonomous System number";
                                    }

                                } // list as-numbers

                            } // list segment

                        } // container as-path

                        container clusters {
                            description "Enter the clusters context";

                            list cluster-list {
                                key "cluster-index";
                                description "Enter the cluster-list list instance";

                                leaf cluster-index {
                                    type uint32;
                                    description "RIB attribute cluster index";
                                }

                                leaf cluster-id {
                                    type types-sros:ipv4-address;
                                    description
                                        "The value represents a reflection path that this route has
                                         passed.";
                                }

                            } // list cluster-list

                        } // container clusters

                        container aggregator {
                            description "Enter the aggregator context";

                            leaf as-number {
                                type inet:as-number;
                                description
                                    "This value represents last AS number that formed the
                                     aggregate route";
                            }

                            leaf address {
                                type types-sros:ipv4-address;
                                description
                                    "This value represents the IP address of the BGP
                                     speaker that formed the aggregate route.";
                            }

                        } // container aggregator

                        container communities {
                            description "Enter the communities context";

                            list community {
                                key "community-index";
                                description "Enter the community list instance";

                                leaf community-index {
                                    type uint32;
                                    description "RIB attribute community index";
                                }

                                leaf community-value {
                                    type string {
                                        length "1..72";
                                    }
                                    description "Community value";
                                }

                            } // list community

                        } // container communities

                        container extended-communities {
                            description "Enter the extended-communities context";

                            list extended-community {
                                key "community-index";
                                description "Enter the extended-community list instance";

                                leaf community-index {
                                    type uint32;
                                    description "RIB attribute community index";
                                }

                                leaf community-value {
                                    type string {
                                        length "1..72";
                                    }
                                    description "Community value";
                                }

                            } // list extended-community

                        } // container extended-communities

                        container large-communities {
                            description "Enter the large-communities context";

                            list large-community {
                                key "community-index";
                                description "Enter the large-community list instance";

                                leaf community-index {
                                    type uint32;
                                    description "RIB attribute community index";
                                }

                                leaf community-value {
                                    type string {
                                        length "1..72";
                                    }
                                    description "Community value";
                                }

                            } // list large-community

                        } // container large-communities

                        container ipv6-extended-communities {
                            description "Enter the ipv6-extended-communities context";

                            list ipv6-extended-community {
                                key "community-index";
                                description "Enter the ipv6-extended-community list instance";

                                leaf community-index {
                                    type uint32;
                                    description "RIB attribute community index";
                                }

                                leaf community-value {
                                    type string {
                                        length "1..72";
                                    }
                                    description "Community value";
                                }

                            } // list ipv6-extended-community

                        } // container ipv6-extended-communities


                        container unknown-attributes {
                            description "Enter the unknown-attributes context";

                            list unknown-attribute {
                                key "unknown-attr-index";
                                description "Enter the unknown-attribute list instance";

                                leaf unknown-attr-index {
                                    type uint32;
                                    description "RIB attribute unknown attribute index";
                                }

                                leaf attr-type {
                                    type uint32;
                                    description "RIB attribute unknown attribute type";
                                }

                                leaf attr-len {
                                    type uint32;
                                    description "RIB attribute unknown attribute length";
                                }

                                leaf optional {
                                    type boolean;
                                    description "This value indicates if the TLV is optional.";
                                }

                                leaf transitive {
                                    type boolean;
                                    description "This value indicates if the TLV is transitive.";
                                }

                                leaf partial {
                                    type boolean;
                                    description "This value indicates if the TLV has partial information.";
                                }

                                leaf extended {
                                    type boolean;
                                    description "If set to true, length is 2 octets; otherwise, length is 1 octet.";
                                }

                            } // list unknown-attribute

                        } // container unknown-attributes

                        container prefix-sid {
                            description "Enter the prefix-sid context";

                            leaf label-index {
                                type uint32;
                                description "Label index value in Segment Routing Global Block space";
                            }

                            leaf originator-start-label {
                                type uint32;
                                description "Start label in Segment Routing Global Block range";
                            }

                            leaf originator-number-of-labels {
                                type uint32;
                                description "Number of labels in Segment Routing Global Block range";
                            }

                        } // container prefix-sid

                        container d-path {
                            description "Enter the d-path context";

                            list domain-segment {
                                key "domain-segment-index";
                                description "Enter the domain-segment list instance";

                                leaf domain-segment-index {
                                    type uint32;
                                    description "RIB attribute D-Path segment index";
                                }

                                leaf domain-segment-length {
                                    type uint8;
                                    description "Number of domains in a segment.";
                                }

                                list domain {
                                    key "domain-index";
                                    description "Enter the domain list instance";

                                    leaf domain-index {
                                        type uint32;
                                        description "RIB attribute D-Path Domain index";
                                    }

                                    leaf domain-id {
                                        type types-services:domain-id;
                                        description "Domain-Id encoded in the D-Path attribute";
                                    }

                                    leaf isf-safi-type {
                                        type uint16;
                                        description
                                            "MP-BGP Sub-Address Family that advertises reachability
                                             for IP prefixes and can be used for inter-subnet
                                             forwarding within a given tenant network.";
                                    }

                                } // list domain

                            } // list domain-segment

                        } // container d-path


                    } // list attr-set

                } // container attr-sets

            } // container rib

            list bmp-session {
                key "station-name";
                description "Enter the bmp-session list instance";

                leaf station-name {
                    type types-sros:named-item;
                    description "BMP station used for the BMP session.";
                }

                leaf connection-state {
                    type enumeration {
                        enum inactive {
                            value 0;
                            description "The BMP station is configured, but other constraints prevent BMP from starting a session.";
                        }
                        enum shutdown {
                            value 1;
                            description "The connection to the BMP-station is administratively disabled.";
                        }
                        enum idle {
                            value 2;
                            description "BMP is in between attempts to open a new session to the BMP-station.";
                        }
                        enum connecting {
                            value 3;
                            description "BMP is actively trying to set up a TCP connection to the BMP-station.";
                        }
                        enum welcoming {
                            value 4;
                            description "BMP has succesfully set up a TCP connection, but hasn't started sending BMP messages yet.";
                        }
                        enum established {
                            value 5;
                            description "BMP has a fully functional BMP-session to the BMP-station.";
                        }
                    }
                    description "Operational state of the BMP session with the BMP station.";
                }

                leaf local-address {
                    type types-sros:ip-address;
                    description "Local IP address of the BMP session with the BMP station.";
                }

                leaf local-port {
                    type types-sros:tcp-udp-port;
                    description "Local TCP port of the BMP session with the BMP station.";
                }

                leaf connection-state-changed {
                    type yang:date-and-time;
                    description "Last time the connection-state of the BMP session with the BMP station was changed.";
                }

                leaf last-message-sent {
                    type yang:date-and-time;
                    description "Last time a message was sent in the BMP session with the BMP station.";
                }

                leaf bytes-sent {
                    type uint64;
                    description "Total number of bytes that were sent in the BMP session with the BMP station.";
                }

                leaf route-monitoring-messages {
                    type uint64;
                    description "Total number of route monitoring messages that were sent in the BMP session with the BMP station.";
                }

                leaf statistics-messages {
                    type uint64;
                    description "Total number of statistics messages that were sent in the BMP session with the BMP station.";
                }

                leaf peer-up-notifications {
                    type uint64;
                    description "Total number of peer-up notifications that were sent in the BMP session with the BMP station.";
                }

                leaf peer-down-notifications {
                    type uint64;
                    description "Total number of peer-down notification that were sent in the BMP session with the BMP station.";
                }

                leaf initiation-messages {
                    type uint64;
                    description "Total number of initiation messages that were sent in the BMP session with the BMP station.";
                }

                leaf termination-messages {
                    type uint64;
                    description "Total number of termination messages that were sent in the BMP session with the BMP station.";
                }

                leaf route-mirroring-messages {
                    type uint64;
                    description "Total number of route monitoring messages that were sent in the BMP session with the BMP station.";
                }

            } // list bmp-session

            container next-hops {
                description "Enter the next-hops context";

                list next-hop {
                    key "index";
                    description "Enter the next-hop list instance";

                    leaf index {
                        type uint64;
                        description "The value indicates the key for next-hops.";
                    }

                    leaf ip-address {
                        type types-sros:ip-address;
                        description "specifies the next-hop ip address.";
                    }

                    leaf admin-tag-policy {
                        type string {
                            length "0..64";
                        }
                        description "Attribute policy-name for route-admin-tag-policy.";
                    }

                    leaf flex-algo {
                        type uint32;
                        description "specifies the flex-algo for this next-hop";
                    }

                    leaf locator {
                        type types-sros:ip-prefix;
                        description "specifies the locator prefix for the next-hop";
                    }

                    leaf-list color-ext-community-value {
                        type uint32;
                        description "specifies the color community value.";
                    }

                    leaf resolving-prefix {
                        type types-sros:ip-prefix-with-host-bits;
                        description "specifies the route prefix";
                    }

                    leaf resolving-protocol {
                        type types-router:protocol-type;
                        description "specifies the resolving protocol";
                    }

                    leaf resolving-metric {
                        type uint32;
                        description "specifies the resolving metric";
                    }

                    leaf resolving-preference {
                        type uint32;
                        description "specifies the resolving preference";
                    }

                    leaf installed {
                        type boolean;
                        description "specifies the fib programmed";
                    }

                    leaf reason {
                        type types-bgp:next-hop-reason;
                        description "specifies the reason why the next-hop is unreachable";
                    }

                    leaf reference-count {
                        type uint32;
                        description "specifies the number of references to this next-hop";
                    }

                    leaf created {
                        type types-sros:time-interval;
                        units "seconds";
                        description "Indicates the time elapsed since this next-hop was created";
                    }

                    leaf last-modified {
                        type types-sros:time-interval;
                        units "seconds";
                        description "Indicates the time elapsed since this next-hop was updated";
                    }

                    leaf bfd-strict-mode {
                        type boolean;
                        description "specifies the bfd-strict-mode nh-reachability setting";
                    }

                    leaf enforce-untagged-route {
                        type types-sros:untagged-route-type;
                        description "Indicates enforcement of untagged routes";
                    }

                    leaf explicit-null {
                        type boolean;
                        description "specifies if the next-hop is linked to label-ipv6 routes with explicit-null label";
                    }

                    leaf used-for-family {
                        type enumeration {
                            enum ipv4                           { value 1; }
                            enum ipv6                           { value 3; }
                            enum mcast-ipv4                     { value 4; }
                            enum mcast-ipv6                     { value 16; }
                            enum label-ipv4                     { value 17; }
                            enum label-ipv6                     { value 18; }
                        }
                        description
                            "Specifies the address family for which
                             next-hop is supported.";
                    }

                    leaf bgp-bgp-final-protocol {
                        type types-router:protocol-type;
                        description "specifies the final protocol for bgp-over-bgp.";
                    }

                    container upa-trigger {
                        description "Enter the upa-trigger context";

                        leaf next-hop {
                            type types-bgp:upa-trigger-next-hop;
                            description "Action to be taken when an UPA is received for a next-hop.";
                        }

                    } // container upa-trigger

                    list resolved-next-hop {
                        key "index";
                        description "Enter the resolved-next-hop list instance";

                        leaf index {
                            type uint64;
                            description "The value indicates the key for resolved next-hops.";
                        }

                        leaf resolved-ip-address {
                            type types-sros:ip-address;
                            description "specifies the resolved next-hop ip address.";
                        }

                        leaf tunnel-id {
                            type uint32;
                            description "specifies tunnel";
                        }

                        leaf weight {
                            type uint32;
                            description "specifies the next-hop weight";
                        }

                        leaf backup {
                            type boolean;
                            description "specifies if backup nexthop";
                        }

                        leaf interface {
                            type leafref {
                                path "../../../../../interface/interface-name";
                            }
                            description "specifies the interface";
                        }

                    } // list resolved-next-hop

                } // list next-hop

            } // container next-hops

            container vpn-next-hops {
                description "Enter the vpn-next-hops context";

                list next-hop {
                    key "index";
                    description "Enter the next-hop list instance";

                    leaf index {
                        type uint64;
                        description "The value indicates the key for next-hops.";
                    }

                    leaf ip-address {
                        type types-sros:ip-address;
                        description "specifies the next-hop ip address.";
                    }

                    leaf admin-tag-policy {
                        type string {
                            length "0..64";
                        }
                        description "Attribute policy-name for route-admin-tag-policy.";
                    }

                    leaf flex-algo {
                        type uint32;
                        description "specifies the flex-algo for this next-hop";
                    }

                    leaf locator {
                        type types-sros:ip-prefix;
                        description "specifies the locator prefix for the next-hop";
                    }

                    leaf-list color-ext-community-value {
                        type uint32;
                        description "specifies the color community value.";
                    }

                    leaf resolving-prefix {
                        type types-sros:ip-prefix-with-host-bits;
                        description "specifies the route prefix";
                    }

                    leaf resolving-protocol {
                        type types-router:protocol-type;
                        description "specifies the resolving protocol";
                    }

                    leaf resolving-metric {
                        type uint32;
                        description "specifies the resolving metric";
                    }

                    leaf resolving-preference {
                        type uint32;
                        description "specifies the resolving preference";
                    }

                    leaf installed {
                        type boolean;
                        description "specifies the fib programmed";
                    }

                    leaf reason {
                        type types-bgp:next-hop-reason;
                        description "specifies the reason why the next-hop is unreachable";
                    }

                    leaf reference-count {
                        type uint32;
                        description "specifies the number of references to this next-hop";
                    }

                    leaf created {
                        type types-sros:time-interval;
                        units "seconds";
                        description "Indicates the time elapsed since this next-hop was created";
                    }

                    leaf last-modified {
                        type types-sros:time-interval;
                        units "seconds";
                        description "Indicates the time elapsed since this next-hop was updated";
                    }

                    leaf bfd-strict-mode {
                        type boolean;
                        description "specifies the bfd-strict-mode nh-reachability setting";
                    }

                    leaf enforce-untagged-route {
                        type types-sros:untagged-route-type;
                        description "Indicates enforcement of untagged routes";
                    }

                    leaf evpn {
                        type boolean;
                        description "next-hop is linked to an EVPN service";
                    }

                    leaf ip-vpn {
                        type boolean;
                        description "next-hop is linked to a VPRN service.";
                    }

                    leaf auto-bind-ecmp {
                        type uint32;
                        description "specifies the ecmp for this vpn next-hop.";
                    }

                    leaf auto-bind-weighted-ecmp {
                        type boolean;
                        description "specifies whether weighted-ecmp is enabled for this vpn next-hop.";
                    }

                    leaf auto-bind-strict-tunnel-tagging {
                        type boolean;
                        description "specifies whether strict-tunnel-tagging is enabled for this vpn next-hop.";
                    }

                    leaf auto-bind-strict-tunnel-untagged {
                        type boolean;
                        description "specifies whether strict-tunnel-untagged is enabled for this vpn next-hop.";
                    }

                    leaf auto-bind-allow-flex-algo-fallback {
                        type boolean;
                        description "specifies whether allow-flex-algo-fallback is enabled for this vpn next-hop.";
                    }

                    leaf auto-bind-ldp {
                        type boolean;
                        description "specifies auto-bind-ldp for vpn next-hop.";
                    }

                    leaf auto-bind-rsvp {
                        type boolean;
                        description "specifies auto-bind-rsvp for vpn next-hop.";
                    }

                    leaf auto-bind-sr-isis {
                        type boolean;
                        description "specifies auto-bind-sr-isis for vpn next-hop.";
                    }

                    leaf auto-bind-sr-ospf {
                        type boolean;
                        description "specifies auto-bind-sr-ospf for vpn next-hop.";
                    }

                    leaf auto-bind-sr-ospf3 {
                        type boolean;
                        description "specifies auto-bind-sr-ospf3 for vpn next-hop.";
                    }

                    leaf auto-bind-udp {
                        type boolean;
                        description "specifies auto-bind-udp for vpn next-hop.";
                    }

                    leaf auto-bind-gre {
                        type boolean;
                        description "specifies auto-bind-gre for vpn next-hop.";
                    }

                    leaf auto-bind-bgp {
                        type boolean;
                        description "specifies auto-bind-bgp for vpn next-hop.";
                    }

                    leaf auto-bind-sr-te {
                        type boolean;
                        description "specifies auto-bind-sr-te for vpn next-hop.";
                    }

                    leaf auto-bind-sr-policy {
                        type boolean;
                        description "specifies auto-bind-sr-policy for vpn next-hop.";
                    }

                    leaf auto-bind-rib-api {
                        type boolean;
                        description "specifies auto-bind-rib-api for vpn next-hop.";
                    }

                    leaf auto-bind-mpls-fwd-policy {
                        type boolean;
                        description "specifies auto-bind-mpls-fwd-policy for vpn next-hop.";
                    }

                    leaf spoke-sdp {
                        type boolean;
                        description "specifies the spoke-sdp for this vpn next-hop.";
                    }

                    leaf spoke-sdp-id {
                        type uint32;
                        description "specifies the spoke-sdp-id for this vpn next-hop.";
                    }

                    leaf vxlan {
                        type boolean;
                        description "specifies the vxlan for this vpn next-hop.";
                    }

                    leaf entropy-label {
                        type boolean;
                        description "specifies the entropy-label for this vpn next-hop.";
                    }

                    leaf class-based-forwarding {
                        type boolean;
                        description "specifies the class-based-forwarding for this vpn next-hop.";
                    }

                    leaf r-vpls {
                        type boolean;
                        description "specifies the r-vpls for this vpn next-hop.";
                    }

                    leaf b-vpls {
                        type boolean;
                        description "specifies the b-vpls for this vpn next-hop.";
                    }

                    leaf user-labels {
                        type uint8;
                        description "specifies the number of labels required by the user service";
                    }

                    container upa-trigger {
                        description "Enter the upa-trigger context";

                        leaf next-hop {
                            type types-bgp:upa-trigger-next-hop;
                            description "Action to be taken when an UPA is received for a next-hop.";
                        }

                    } // container upa-trigger

                    list resolved-next-hop {
                        key "index";
                        description "Enter the resolved-next-hop list instance";

                        leaf index {
                            type uint64;
                            description "The value indicates the key for resolved next-hops.";
                        }

                        leaf resolved-ip-address {
                            type types-sros:ip-address;
                            description "specifies the resolved next-hop ip address.";
                        }

                        leaf tunnel-id {
                            type uint32;
                            description "specifies tunnel";
                        }

                        leaf weight {
                            type uint32;
                            description "specifies the next-hop weight";
                        }

                        leaf backup {
                            type boolean;
                            description "specifies if backup nexthop";
                        }

                    } // list resolved-next-hop

                } // list next-hop

            } // container vpn-next-hops

        } // container bgp

    } // grouping state-router-bgp

}
