submodule nokia-conf-oam-pm {

    yang-version "1.1";

    belongs-to nokia-conf { prefix "conf"; }

    import nokia-sros-yang-extensions     { prefix "sros-ext"; }
    import nokia-types-eth-cfm            { prefix "types-eth-cfm"; }
    import nokia-types-oam                { prefix "types-oam"; }
    import nokia-types-qos                { prefix "types-qos"; }
    import nokia-types-router             { prefix "types-router"; }
    import nokia-types-sros               { prefix "types-sros"; }

    include nokia-conf-groups;
    include nokia-conf-log;

    sros-ext:sros-major-release "rel25";
    organization "Nokia";
    contact
        "Nokia SR OS Support
         Web: <http://www.nokia.com>";
    description
        "Nokia YANG Data model to configure OAM-PM configuration on SR OS based routers.

         Copyright 2016 Nokia. All rights reserved. Reproduction of this document
         is authorized on the condition that the foregoing copyright notice is included.

         This nokia-conf-oam-pm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-02-11";

    grouping conf-oam-pm {
        container oam-pm {
            description "Enter the oam-pm context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list bin-group {
                key "bin-group-id";
                description "Enter the bin-group list instance";

                leaf bin-group-id {
                    type uint32 {
                        range "1..255";
                    }
                    description "Bin group ID";
                }

                leaf admin-state {
                    type types-sros:admin-state;
                    description "Administrative state of the bin group";
                }

                leaf description {
                    type types-sros:description;
                    description "Text description";
                }

                leaf-list apply-groups {
                    type leafref {
                        path "../../../groups/group/name";
                    }
                    max-elements 8;
                    ordered-by user;
                    sros-ext:auto-restart-to-modify;
                    description "Apply a configuration group at this level";
                }

                leaf-list apply-groups-exclude {
                    type leafref {
                        path "../../../groups/group/name";
                    }
                    max-elements 8;
                    ordered-by user;
                    sros-ext:auto-restart-to-modify;
                    description "Exclude a configuration group at this level";
                }

                list bin-type {
                    key "bin-metric";
                    description "Enter the bin-type list instance";

                    leaf bin-metric {
                        type enumeration {
                            enum fd {
                                value 1;
                                description "Frame Delay";
                            }
                            enum fdr {
                                value 2;
                                description "Frame Delay Range";
                            }
                            enum ifdv {
                                value 3;
                                description "Inter-Frame Delay Variation";
                            }
                        }
                        description "Delay metric bin structure";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list delay-event {
                        key "direction";
                        description "Enter the delay-event list instance";

                        leaf direction {
                            type types-oam:direction;
                            description "Traffic flow direction of the OAM-PM test or metric";
                        }

                        leaf lowest-bin {
                            type uint32 {
                                range "0..9";
                            }
                            mandatory true;
                            description "Lowest delay bin used when applying a delay threshold";
                        }

                        leaf raise-threshold {
                            type int32 {
                                range "1..864000";
                            }
                            mandatory true;
                            description "Raise threshold for excessive delay";
                        }

                        leaf clear-threshold {
                            type int32 {
                                range "0..863999";
                            }
                            description "OAM-PM clear threshold for an excessive delay";
                        }

                        leaf exclude-lowest-bin {
                            type int32 {
                                range "1..9";
                            }
                            description "Lowest bin excluded from the TCA count";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list delay-event

                    list exclude-from-avg {
                        key "direction";
                        description "Enter the exclude-from-avg list instance";

                        leaf direction {
                            type types-oam:direction;
                            description "Traffic flow direction of the OAM-PM test or metric";
                        }

                        leaf bins {
                            type string {
                                length "1..39";
                                pattern "(all|(([0-9]|([0-9]-[0-9]))(,([0-9]|([0-9]-[0-9])))*))";
                            }
                            mandatory true;
                            description "Bin numbers excluded from the average calculation";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list exclude-from-avg

                    list bin {
                        key "bin-number";
                        description "Enter the bin list instance";

                        leaf bin-number {
                            type uint32 {
                                range "0..9";
                            }
                            description "Bin number";
                        }

                        leaf lower-bound {
                            type int64 {
                                range "0|1..4294967295";
                            }
                            units "microseconds";
                            description "Lower bound for the bin";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list bin

                } // list bin-type

            } // list bin-group

            list session {
                key "session-name";
                description "Enter the session list instance";

                leaf session-name {
                    type types-sros:named-item;
                    description "OAM-PM session name";
                }

                leaf session-type {
                    type enumeration {
                        enum proactive                      { value 1; }
                        enum on-demand                      { value 2; }
                    }
                    sros-ext:immutable;
                    default "proactive";
                    description "Session type";
                }

                leaf bin-group {
                    type leafref {
                        path "../../bin-group/bin-group-id";
                    }
                    description "Bin group for the session";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice test-family-choice {
                    mandatory true;
                    case ethernet-case {

                        container ethernet {
                            presence "Enable the ethernet context";
                            description "Enable the ethernet context";

                            leaf dest-mac {
                                type types-sros:mac-unicast-address;
                                description "Destination MAC address for the session";
                            }

                            leaf remote-mep {
                                type uint32 {
                                    range "1..8191";
                                }
                                description "Remote MEP for the session";
                            }

                            leaf priority {
                                type uint32 {
                                    range "0..7";
                                }
                                default "0";
                                description "Priority and forwarding class for the session";
                            }

                            container source {
                                presence "Enable the source context";
                                description "Enable the source context";

                                leaf mep {
                                    type uint32 {
                                        range "1..8191";
                                    }
                                    mandatory true;
                                    description "Source Ethernet MEP ID";
                                }

                                leaf md-admin-name {
                                    type union {
                                        type types-sros:named-item-64;
                                        type types-eth-cfm:admin-name;
                                    }
                                    mandatory true;
                                    description "Source Ethernet MD name";
                                }

                                leaf ma-admin-name {
                                    type union {
                                        type types-sros:named-item-64;
                                        type types-eth-cfm:admin-name;
                                    }
                                    mandatory true;
                                    description "Source Ethernet MA name";
                                }

                            } // container source

                            container dmm {
                                presence "Enable the dmm context";
                                description "Enable the dmm context";

                                leaf admin-state {
                                    type types-sros:admin-state;
                                    default "disable";
                                    description "Administrative state of the test";
                                }

                                leaf test-id {
                                    type union {
                                        type uint32 {
                                            range "0..2147483647";
                                        }
                                        type enumeration {
                                            enum auto {
                                                value -1;
                                                description "Automatically assign a test ID";
                                            }
                                        }
                                    }
                                    sros-ext:auto-restart-to-modify;
                                    mandatory true;
                                    description "Test ID";
                                }

                                leaf test-duration {
                                    type uint32 {
                                        range "1..86400";
                                    }
                                    units "seconds";
                                    sros-ext:auto-restart-to-modify;
                                    description "Duration of an on-demand test";
                                }

                                leaf interval {
                                    type uint32 {
                                        range "50|100|200|300|400|500|600|700|800|900|1000|10000";
                                    }
                                    units "milliseconds";
                                    sros-ext:auto-restart-to-modify;
                                    description "Time between transmission PDUs for the session test";
                                }

                                leaf data-tlv-size {
                                    type uint32 {
                                        range "0|3..2000";
                                    }
                                    units "octets";
                                    sros-ext:auto-restart-to-modify;
                                    default "0";
                                    description "Data TLV size in the frames sent for the test";
                                }

                                leaf delay-template {
                                    type types-sros:named-item-64;
                                    sros-ext:auto-restart-to-modify;
                                    description "Reference to a streaming delay template for the test";
                                }

                                leaf-list apply-groups {
                                    type leafref {
                                        path "../../../../../groups/group/name";
                                    }
                                    max-elements 8;
                                    ordered-by user;
                                    sros-ext:auto-restart-to-modify;
                                    description "Apply a configuration group at this level";
                                }

                                leaf-list apply-groups-exclude {
                                    type leafref {
                                        path "../../../../../groups/group/name";
                                    }
                                    max-elements 8;
                                    ordered-by user;
                                    sros-ext:auto-restart-to-modify;
                                    description "Exclude a configuration group at this level";
                                }

                            } // container dmm

                            container lmm {
                                presence "Enable the lmm context";
                                description "Enable the lmm context";

                                leaf admin-state {
                                    type types-sros:admin-state;
                                    default "disable";
                                    description "Administrative state of the test";
                                }

                                leaf test-id {
                                    type union {
                                        type uint32 {
                                            range "0..2147483647";
                                        }
                                        type enumeration {
                                            enum auto {
                                                value -1;
                                                description "Automatically assign a test ID";
                                            }
                                        }
                                    }
                                    sros-ext:auto-restart-to-modify;
                                    mandatory true;
                                    description "Test ID";
                                }

                                leaf test-duration {
                                    type uint32 {
                                        range "1..86400";
                                    }
                                    units "seconds";
                                    sros-ext:auto-restart-to-modify;
                                    description "Duration of an on-demand test";
                                }

                                leaf interval {
                                    type uint32 {
                                        range "100|1000|10000";
                                    }
                                    units "milliseconds";
                                    sros-ext:auto-restart-to-modify;
                                    description "Time between transmission PDUs for the session test";
                                }

                                leaf fc-collection {
                                    type boolean;
                                    sros-ext:auto-restart-to-modify;
                                    default "false";
                                    description "Enable collection of per-forwarding class counters";
                                }

                                leaf-list apply-groups {
                                    type leafref {
                                        path "../../../../../groups/group/name";
                                    }
                                    max-elements 8;
                                    ordered-by user;
                                    sros-ext:auto-restart-to-modify;
                                    description "Apply a configuration group at this level";
                                }

                                leaf-list apply-groups-exclude {
                                    type leafref {
                                        path "../../../../../groups/group/name";
                                    }
                                    max-elements 8;
                                    ordered-by user;
                                    sros-ext:auto-restart-to-modify;
                                    description "Exclude a configuration group at this level";
                                }

                                container availability {
                                    sros-ext:auto-restart-to-modify;
                                    description "Enter the availability context";

                                    leaf admin-state {
                                        type types-sros:admin-state;
                                        sros-ext:auto-restart-to-modify;
                                        default "disable";
                                        description "Administrative state of availability statistics";
                                    }

                                    leaf flr-threshold {
                                        type types-sros:percent;
                                        sros-ext:auto-restart-to-modify;
                                        default "50";
                                        description "FLR threshold for the test";
                                    }

                                    leaf hli-force-count {
                                        type boolean;
                                        sros-ext:auto-restart-to-modify;
                                        default "false";
                                        description "Increment HLI and CHLI counters despite availability";
                                    }

                                    container timing {
                                        sros-ext:auto-restart-to-modify;
                                        description "Enter the timing context";

                                        leaf frames-per-delta-t {
                                            type uint32 {
                                                range "1..50";
                                            }
                                            units "frames";
                                            sros-ext:auto-restart-to-modify;
                                            description "Number of frames sent in one delta-t";
                                        }

                                        leaf consec-delta-t {
                                            type uint32 {
                                                range "2..10";
                                            }
                                            sros-ext:auto-restart-to-modify;
                                            default "10";
                                            description "Number of consecutive delta-t intervals";
                                        }

                                        leaf chli-threshold {
                                            type uint32 {
                                                range "1..9";
                                            }
                                            sros-ext:auto-restart-to-modify;
                                            default "5";
                                            description "CHLI threshold";
                                        }

                                    } // container timing

                                } // container availability

                                container loss-events {
                                    sros-ext:auto-restart-to-modify;
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf raise-threshold {
                                            type decimal64 {
                                                range "0.000..100.000";
                                                fraction-digits 3;
                                            }
                                            units "percent";
                                            mandatory true;
                                            description "Rising threshold for the average FLR";
                                        }

                                        leaf clear-threshold {
                                            type decimal64 {
                                                range "0.000..99.999";
                                                fraction-digits 3;
                                            }
                                            units "percent";
                                            description "Clear threshold for the average FLR";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container lmm

                            container slm {
                                presence "Enable the slm context";
                                description "Enable the slm context";

                                leaf admin-state {
                                    type types-sros:admin-state;
                                    default "disable";
                                    description "Administrative state of the test";
                                }

                                leaf test-id {
                                    type union {
                                        type uint32 {
                                            range "0..2147483647";
                                        }
                                        type enumeration {
                                            enum auto {
                                                value -1;
                                                description "Automatically assign a test ID";
                                            }
                                        }
                                    }
                                    sros-ext:auto-restart-to-modify;
                                    mandatory true;
                                    description "Test ID";
                                }

                                leaf test-duration {
                                    type uint32 {
                                        range "1..86400";
                                    }
                                    units "seconds";
                                    sros-ext:auto-restart-to-modify;
                                    description "Duration of an on-demand test";
                                }

                                leaf interval {
                                    type uint32 {
                                        range "50|100|200|300|400|500|600|700|800|900|1000";
                                    }
                                    units "milliseconds";
                                    sros-ext:auto-restart-to-modify;
                                    description "Time between transmission PDUs for the session test";
                                }

                                leaf data-tlv-size {
                                    type uint32 {
                                        range "0|3..2000";
                                    }
                                    units "octets";
                                    sros-ext:auto-restart-to-modify;
                                    default "0";
                                    description "Data TLV size in the frames sent for the test";
                                }

                                leaf flr-threshold {
                                    type types-sros:percent;
                                    sros-ext:auto-restart-to-modify;
                                    default "50";
                                    description "FLR threshold for the test";
                                }

                                leaf hli-force-count {
                                    type boolean;
                                    sros-ext:auto-restart-to-modify;
                                    default "false";
                                    description "Increment HLI and CHLI counters despite availability";
                                }

                                leaf-list apply-groups {
                                    type leafref {
                                        path "../../../../../groups/group/name";
                                    }
                                    max-elements 8;
                                    ordered-by user;
                                    sros-ext:auto-restart-to-modify;
                                    description "Apply a configuration group at this level";
                                }

                                leaf-list apply-groups-exclude {
                                    type leafref {
                                        path "../../../../../groups/group/name";
                                    }
                                    max-elements 8;
                                    ordered-by user;
                                    sros-ext:auto-restart-to-modify;
                                    description "Exclude a configuration group at this level";
                                }

                                container timing {
                                    sros-ext:auto-restart-to-modify;
                                    description "Enter the timing context";

                                    leaf frames-per-delta-t {
                                        type uint32 {
                                            range "1..50";
                                        }
                                        units "frames";
                                        sros-ext:auto-restart-to-modify;
                                        description "Frames sent in one Delta-T";
                                    }

                                    leaf consec-delta-t {
                                        type uint32 {
                                            range "2..10";
                                        }
                                        sros-ext:auto-restart-to-modify;
                                        default "10";
                                        description "Consecutive Delta-t intervals";
                                    }

                                    leaf chli-threshold {
                                        type uint32 {
                                            range "1..9";
                                        }
                                        sros-ext:auto-restart-to-modify;
                                        default "5";
                                        description "CHLI threshold";
                                    }

                                } // container timing

                                container loss-events {
                                    sros-ext:auto-restart-to-modify;
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf raise-threshold {
                                            type decimal64 {
                                                range "0.000..100.000";
                                                fraction-digits 3;
                                            }
                                            units "percent";
                                            mandatory true;
                                            description "Rising threshold for the average FLR";
                                        }

                                        leaf clear-threshold {
                                            type decimal64 {
                                                range "0.000..99.999";
                                                fraction-digits 3;
                                            }
                                            units "percent";
                                            description "Clear threshold for the average FLR";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container slm

                        } // container ethernet

                    }
                    case ip-case {

                        container ip {
                            presence "Enable the ip context";
                            description "Enable the ip context";

                            leaf allow-egress-remark-dscp {
                                type boolean;
                                default "false";
                                description "Allow DSCP modification by the egress QoS policy";
                            }

                            leaf destination {
                                type types-sros:ip-unicast-address;
                                description "Destination IP address for the session";
                            }

                            leaf destination-udp-port {
                                type types-sros:tcp-udp-port-non-zero;
                                description "Destination UDP port for the session";
                            }

                            leaf do-not-fragment {
                                type boolean;
                                default "false";
                                description "Do not allow packet fragmentation in the IPv4 header";
                            }

                            leaf dscp {
                                type union {
                                    type types-qos:dscp-name;
                                    type types-oam:dscp-resolve;
                                }
                                default "resolve";
                                description "DSCP value configured to the DSCP name";
                            }

                            leaf fc {
                                type types-oam:forwarding-class;
                                default "be";
                                description "Forwarding class for the session";
                            }

                            leaf pattern {
                                type types-oam:padding-pattern;
                                default "0";
                                description "Pattern used to fill the packet padding field";
                            }

                            leaf profile {
                                type enumeration {
                                    enum in                             { value 1; }
                                    enum out                            { value 2; }
                                }
                                default "out";
                                description "Profile type for the session";
                            }

                            leaf router-instance {
                                type string;
                                default "Base";
                                description "Router instance for the session";
                            }

                            leaf source {
                                type types-sros:ip-unicast-address;
                                description "Source IP address for the session";
                            }

                            leaf source-udp-port {
                                type types-sros:tcp-udp-port-non-zero {
                                    range "64374..64383";
                                }
                                description "Source UDP port for the session";
                            }

                            leaf ttl {
                                type uint32 {
                                    range "1..255";
                                }
                                default "255";
                                description "TTL value for the session";
                            }

                            container forwarding {
                                presence "Enable the forwarding context";
                                description "Enable the forwarding context";

                                choice forwarding-choice {
                                    mandatory true;
                                    case next-hop-case {

                                        leaf next-hop {
                                            type types-sros:ip-unicast-address;
                                            description "IP address for forwarding";
                                        }

                                    }
                                    case interface-case {

                                        leaf interface {
                                            type types-sros:interface-name;
                                            description "Interface name";
                                        }

                                    }
                                    case bypass-routing-case {

                                        leaf bypass-routing {
                                            type empty;
                                            description "Bypass the routing table when sending test packets";
                                        }

                                    }
                                }
                            } // container forwarding

                            container tunnel {
                                description "Enter the tunnel context";

                                choice tunnel-types {
                                    case tunnel-type-mpls {

                                        container mpls {
                                            presence "Enable the mpls context";
                                            description "Enable the mpls context";

                                            choice mpls-tunnel-types {
                                                case mpls-rsvp-te {

                                                    container rsvp-te {
                                                        presence "Enable the rsvp-te context";
                                                        description "Enable the rsvp-te context";

                                                        leaf lsp {
                                                            type types-sros:named-item-64;
                                                            description "Name of LSP that carries the test packets";
                                                        }

                                                    } // container rsvp-te

                                                }
                                                case mpls-rsvp-te-auto {

                                                    container rsvp-te-auto {
                                                        presence "Enable the rsvp-te-auto context";
                                                        description "Enable the rsvp-te-auto context";

                                                        leaf lsp-template {
                                                            type types-sros:named-item;
                                                            description "LSP template used to identify the LSP to be tested";
                                                        }

                                                        leaf from {
                                                            type types-sros:ipv4-unicast-address;
                                                            description "IPv4 address used to identify the LSP to be tested";
                                                        }

                                                        leaf to {
                                                            type types-sros:ipv4-unicast-address;
                                                            description "IPv4 unicast address to identify the LSP to be tested";
                                                        }

                                                    } // container rsvp-te-auto

                                                }
                                                case mpls-sr-isis {

                                                    container sr-isis {
                                                        presence "Enable the sr-isis context";
                                                        description "Enable the sr-isis context";

                                                        leaf flex-algo {
                                                            type types-router:flex-algo-id;
                                                            description "Flex-algorithm to tunnel IP packets for session tests";
                                                        }

                                                        leaf prefix {
                                                            type types-sros:ip-unicast-prefix;
                                                            description "IP prefix to tunnel IP packets for the session tests";
                                                        }

                                                        leaf igp-instance {
                                                            type uint32 {
                                                                range "0..127";
                                                            }
                                                            default "0";
                                                            description "IGP instance used to tunnel IP packets";
                                                        }

                                                    } // container sr-isis

                                                }
                                                case mpls-sr-ospf {

                                                    container sr-ospf {
                                                        presence "Enable the sr-ospf context";
                                                        description "Enable the sr-ospf context";

                                                        leaf flex-algo {
                                                            type types-router:flex-algo-id;
                                                            description "Flex-algorithm to tunnel IP packets for session tests";
                                                        }

                                                        leaf prefix {
                                                            type types-sros:ipv4-unicast-prefix;
                                                            description "IP prefix to tunnel IP packets for the session tests";
                                                        }

                                                        leaf igp-instance {
                                                            type uint32 {
                                                                range "0..31";
                                                            }
                                                            default "0";
                                                            description "IGP instance used to tunnel IP packets";
                                                        }

                                                    } // container sr-ospf

                                                }
                                                case mpls-sr-ospf3 {

                                                    container sr-ospf3 {
                                                        presence "Enable the sr-ospf3 context";
                                                        description "Enable the sr-ospf3 context";

                                                        leaf prefix {
                                                            type types-sros:ip-unicast-prefix;
                                                            description "IP prefix to tunnel IP packets for the session tests";
                                                        }

                                                        leaf igp-instance {
                                                            type uint32 {
                                                                range "0..31 | 64..95";
                                                            }
                                                            default "0";
                                                            description "IGP instance used to tunnel IP packets";
                                                        }

                                                    } // container sr-ospf3

                                                }
                                                case mpls-sr-policy {

                                                    container sr-policy {
                                                        presence "Enable the sr-policy context";
                                                        description "Enable the sr-policy context";

                                                        leaf color {
                                                            type uint32;
                                                            default "0";
                                                            description "Color for associating the SR policy with an objective";
                                                        }

                                                        leaf endpoint {
                                                            type types-sros:ip-address;
                                                            description "Segment Routing endpoint for the session";
                                                        }

                                                        leaf segment-list {
                                                            type uint32 {
                                                                range "1..32";
                                                            }
                                                            description "Segment Routing segment list for the session";
                                                        }

                                                    } // container sr-policy

                                                }
                                                case mpls-sr-te {

                                                    container sr-te {
                                                        presence "Enable the sr-te context";
                                                        description "Enable the sr-te context";

                                                        leaf lsp {
                                                            type types-sros:named-item-64;
                                                            description "Name of LSP that carries the test packets";
                                                        }

                                                    } // container sr-te

                                                }
                                            }
                                        } // container mpls

                                    }
                                }
                            } // container tunnel

                            container twamp-light {
                                presence "Enable the twamp-light context";
                                description "Enable the twamp-light context";

                                leaf admin-state {
                                    type types-sros:admin-state;
                                    default "disable";
                                    description "Administrative state of the test";
                                }

                                leaf test-id {
                                    type union {
                                        type uint32 {
                                            range "0..2147483647";
                                        }
                                        type enumeration {
                                            enum auto {
                                                value -1;
                                                description "Automatically assign a test ID";
                                            }
                                        }
                                    }
                                    sros-ext:auto-restart-to-modify;
                                    mandatory true;
                                    description "Test ID";
                                }

                                leaf test-duration {
                                    type uint32 {
                                        range "1..86400";
                                    }
                                    units "seconds";
                                    sros-ext:auto-restart-to-modify;
                                    description "Duration of an on-demand test";
                                }

                                leaf interval {
                                    type uint32 {
                                        range "50|100|200|300|400|500|600|700|800|900|1000|10000";
                                    }
                                    units "milliseconds";
                                    sros-ext:auto-restart-to-modify;
                                    description "Time between transmission PDUs for the session test";
                                }

                                leaf allow-ipv6-udp-checksum-zero {
                                    type boolean;
                                    sros-ext:auto-restart-to-modify;
                                    default "false";
                                    description "Process IPv6 packets with a zero UDP checksum";
                                }

                                leaf pad-size {
                                    type uint32 {
                                        range "0..2000";
                                    }
                                    units "octets";
                                    sros-ext:auto-restart-to-modify;
                                    default "0";
                                    description "Amount of packet padding sent for the TWAMP-Light test";
                                }

                                leaf pad-tlv-size {
                                    type uint32 {
                                        range "4..2000";
                                    }
                                    units "octets";
                                    sros-ext:auto-restart-to-modify;
                                    description "Pad TLV size in each sent STAMP packet";
                                }

                                leaf record-stats {
                                    type enumeration {
                                        enum delay                          { value 1; }
                                        enum loss                           { value 2; }
                                        enum delay-and-loss                 { value 3; }
                                    }
                                    sros-ext:auto-restart-to-modify;
                                    default "delay";
                                    description "Type of statistics recorded for the TWAMP-Light test";
                                }

                                leaf session-sender-type {
                                    type enumeration {
                                        enum twamp-light {
                                            value 1;
                                            description "Two-Way Active Measurement Protocol, Light";
                                        }
                                        enum stamp {
                                            value 2;
                                            description "Simple Two-Way Active Measurement Protocol";
                                        }
                                    }
                                    sros-ext:auto-restart-to-modify;
                                    default "twamp-light";
                                    description "Packet type sent by the test";
                                }

                                leaf timestamp-format {
                                    type enumeration {
                                        enum ntp {
                                            value 0;
                                            description "Network Time Protocol";
                                        }
                                        enum ptp {
                                            value 1;
                                            description "Precision Time Protocol";
                                        }
                                    }
                                    sros-ext:auto-restart-to-modify;
                                    default "ntp";
                                    description "TWAMP Light or STAMP test packet timestamp format";
                                }

                                leaf delay-template {
                                    type types-sros:named-item-64;
                                    sros-ext:auto-restart-to-modify;
                                    description "Reference to a streaming delay template for the test";
                                }

                                leaf-list apply-groups {
                                    type leafref {
                                        path "../../../../../groups/group/name";
                                    }
                                    max-elements 8;
                                    ordered-by user;
                                    sros-ext:auto-restart-to-modify;
                                    description "Apply a configuration group at this level";
                                }

                                leaf-list apply-groups-exclude {
                                    type leafref {
                                        path "../../../../../groups/group/name";
                                    }
                                    max-elements 8;
                                    ordered-by user;
                                    sros-ext:auto-restart-to-modify;
                                    description "Exclude a configuration group at this level";
                                }

                                container loss {
                                    sros-ext:auto-restart-to-modify;
                                    description "Enter the loss context";

                                    leaf flr-threshold {
                                        type types-sros:percent;
                                        sros-ext:auto-restart-to-modify;
                                        default "50";
                                        description "FLR threshold for the test";
                                    }

                                    leaf hli-force-count {
                                        type boolean;
                                        sros-ext:auto-restart-to-modify;
                                        default "false";
                                        description "Increment HLI and CHLI counters despite availability";
                                    }

                                    container timing {
                                        sros-ext:auto-restart-to-modify;
                                        description "Enter the timing context";

                                        leaf frames-per-delta-t {
                                            type uint32 {
                                                range "1..50";
                                            }
                                            units "frames";
                                            sros-ext:auto-restart-to-modify;
                                            description "Number of frames sent in one delta-t";
                                        }

                                        leaf consec-delta-t {
                                            type uint32 {
                                                range "2..10";
                                            }
                                            sros-ext:auto-restart-to-modify;
                                            default "10";
                                            description "Number of consecutive delta-t intervals";
                                        }

                                        leaf chli-threshold {
                                            type uint32 {
                                                range "1..9";
                                            }
                                            sros-ext:auto-restart-to-modify;
                                            default "5";
                                            description "CHLI threshold";
                                        }

                                    } // container timing

                                } // container loss

                                container loss-events {
                                    sros-ext:auto-restart-to-modify;
                                    description "Enter the loss-events context";

                                    list avg-flr-event {
                                        key "direction";
                                        description "Enter the avg-flr-event list instance";

                                        leaf direction {
                                            type enumeration {
                                                enum forward                        { value 1; }
                                                enum backward                       { value 2; }
                                            }
                                            description "Traffic flow direction";
                                        }

                                        leaf raise-threshold {
                                            type decimal64 {
                                                range "0.000..100.000";
                                                fraction-digits 3;
                                            }
                                            units "percent";
                                            mandatory true;
                                            description "Rising threshold for the average FLR";
                                        }

                                        leaf clear-threshold {
                                            type decimal64 {
                                                range "0.000..99.999";
                                                fraction-digits 3;
                                            }
                                            units "percent";
                                            description "Clear threshold for the average FLR";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum forward                        { value 1; }
                                                enum backward                       { value 2; }
                                                enum aggregate                      { value 3; }
                                            }
                                            description "Traffic flow direction";
                                        }

                                        leaf raise-threshold {
                                            type int32 {
                                                range "1..864000";
                                            }
                                            mandatory true;
                                            description "Rising threshold that determines when to generate event";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container twamp-light

                        } // container ip

                    }
                    case mpls-case {

                        container mpls {
                            presence "Enable the mpls context";
                            description "Enable the mpls context";

                            leaf dscp {
                                type types-qos:dscp-name;
                                default "be";
                                description "DSCP value for the session";
                            }

                            leaf fc {
                                type types-oam:forwarding-class;
                                default "be";
                                description "Forwarding class for the session";
                            }

                            leaf pattern {
                                type types-oam:padding-pattern;
                                default "0";
                                description "Pattern value repeated to fill padding field of packet";
                            }

                            leaf profile {
                                type enumeration {
                                    enum in                             { value 1; }
                                    enum out                            { value 2; }
                                }
                                default "out";
                                description "QoS profile for the session";
                            }

                            leaf ttl {
                                type uint32 {
                                    range "1..255";
                                }
                                default "255";
                                description "MPLS TTL value for the session";
                            }

                            container lsp {
                                description "Enter the lsp context";

                                choice lsp-choice {
                                    case mpls-tp-static-case {

                                        container mpls-tp-static {
                                            presence "Enable the mpls-tp-static context";
                                            description "Enable the mpls-tp-static context";

                                            leaf lsp {
                                                type types-sros:named-item-64;
                                                description "LSP to be tested";
                                            }

                                        } // container mpls-tp-static

                                    }
                                    case rsvp-case {

                                        container rsvp {
                                            presence "Enable the rsvp context";
                                            description "Enable the rsvp context";

                                            leaf lsp {
                                                type types-sros:named-item-64;
                                                description "LSP to be tested";
                                            }

                                            leaf udp-return-object {
                                                type types-sros:ip-unicast-address;
                                                description "IP address used by far end of the test to send response";
                                            }

                                        } // container rsvp

                                    }
                                    case rsvp-auto-case {

                                        container rsvp-auto {
                                            presence "Enable the rsvp-auto context";
                                            description "Enable the rsvp-auto context";

                                            leaf lsp-template {
                                                type types-sros:named-item;
                                                description "LSP template used to identify the LSP to be tested";
                                            }

                                            leaf from {
                                                type types-sros:ipv4-unicast-address;
                                                description "IPv4 address used to identify the LSP to be tested";
                                            }

                                            leaf to {
                                                type types-sros:ipv4-unicast-address;
                                                description "IPv4 address used to identify the LSP to be tested";
                                            }

                                            leaf udp-return-object {
                                                type types-sros:ip-unicast-address;
                                                description "IP address used by far end of the test to send response";
                                            }

                                        } // container rsvp-auto

                                    }
                                }
                            } // container lsp

                            container dm {
                                presence "Enable the dm context";
                                description "Enable the dm context";

                                leaf admin-state {
                                    type types-sros:admin-state;
                                    default "disable";
                                    description "Administrative state of the MPLS DM test";
                                }

                                leaf test-id {
                                    type uint32 {
                                        range "0..67108863";
                                    }
                                    sros-ext:auto-restart-to-modify;
                                    mandatory true;
                                    description "Test ID for query and response messages";
                                }

                                leaf interval {
                                    type uint32 {
                                        range "1000|2000|3000|4000|5000|6000|7000|8000|9000|10000";
                                    }
                                    units "milliseconds";
                                    sros-ext:auto-restart-to-modify;
                                    default "1000";
                                    description "Elapsed time between query messages sent for the test";
                                }

                                leaf pad-tlv-size {
                                    type uint32 {
                                        range "0|2..257";
                                    }
                                    units "octets";
                                    sros-ext:auto-restart-to-modify;
                                    default "0";
                                    description "Size of the pad TLV in query messages sent for the test";
                                }

                                leaf reflect-pad {
                                    type boolean;
                                    sros-ext:auto-restart-to-modify;
                                    default "false";
                                    description "Copy the pad TLV in each query to the response";
                                }

                                leaf test-duration {
                                    type uint32 {
                                        range "1..86400";
                                    }
                                    units "seconds";
                                    sros-ext:auto-restart-to-modify;
                                    description "Duration of an on-demand test";
                                }

                                leaf delay-template {
                                    type types-sros:named-item-64;
                                    sros-ext:auto-restart-to-modify;
                                    description "Reference to a streaming delay template for the test";
                                }

                                leaf-list apply-groups {
                                    type leafref {
                                        path "../../../../../groups/group/name";
                                    }
                                    max-elements 8;
                                    ordered-by user;
                                    sros-ext:auto-restart-to-modify;
                                    description "Apply a configuration group at this level";
                                }

                                leaf-list apply-groups-exclude {
                                    type leafref {
                                        path "../../../../../groups/group/name";
                                    }
                                    max-elements 8;
                                    ordered-by user;
                                    sros-ext:auto-restart-to-modify;
                                    description "Exclude a configuration group at this level";
                                }

                            } // container dm

                        } // container mpls

                    }
                }
                list measurement-interval {
                    key "duration";
                    description "Enter the measurement-interval list instance";

                    leaf duration {
                        type types-oam:measurement-interval-duration;
                        description "Duration of the measurement interval";
                    }

                    leaf accounting-policy {
                        type leafref {
                            path "../../../../log/accounting-policy/policy-id";
                        }
                        description "Accounting policy for the measurement interval";
                    }

                    leaf boundary-type {
                        type enumeration {
                            enum clock-aligned                  { value 1; }
                            enum test-relative                  { value 2; }
                        }
                        default "clock-aligned";
                        description "Alignment of the start of the measurement interval";
                    }

                    leaf clock-offset {
                        type uint32 {
                            range "0..86399";
                        }
                        units "seconds";
                        default "0";
                        description "Offset for a clock-aligned measurement interval";
                    }

                    leaf intervals-stored {
                        type uint32 {
                            range "1..96";
                        }
                        description "Maximum number of measurement intervals stored";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container threshold-cross-alerts {
                        description "Enter the threshold-cross-alerts context";

                        leaf admin-state {
                            type types-sros:admin-state;
                            default "disable";
                            description "Administrative state of TCAs for measurement interval";
                        }

                        leaf delay-events {
                            type boolean;
                            default "false";
                            description "Enable delay TCAs for the measurement interval";
                        }

                        leaf loss-events {
                            type boolean;
                            default "false";
                            description "Enable loss TCAs for the measurement interval";
                        }

                    } // container threshold-cross-alerts

                } // list measurement-interval

            } // list session

            container streaming {
                description "Enter the streaming context";

                list delay-template {
                    key "delay-template-name";
                    description "Enter the delay-template list instance";

                    leaf delay-template-name {
                        type types-sros:named-item-64;
                        description "Streaming delay template name";
                    }

                    leaf admin-state {
                        type types-sros:admin-state;
                        default "disable";
                        description "Administrative state of the delay template";
                    }

                    leaf description {
                        type types-sros:description;
                        description "Text description";
                    }

                    leaf sample-window {
                        type uint32 {
                            range "10..60";
                        }
                        units "seconds";
                        sros-ext:auto-restart-to-modify;
                        default "60";
                        description "Sample window duration for the template";
                    }

                    leaf window-integrity {
                        type uint32 {
                            range "1..100";
                        }
                        units "percent";
                        sros-ext:auto-restart-to-modify;
                        default "50";
                        description "Measurements for the sample window validity";
                    }

                    leaf-list apply-groups {
                        type leafref {
                            path "../../../../groups/group/name";
                        }
                        max-elements 8;
                        ordered-by user;
                        sros-ext:auto-restart-to-modify;
                        description "Apply a configuration group at this level";
                    }

                    leaf-list apply-groups-exclude {
                        type leafref {
                            path "../../../../groups/group/name";
                        }
                        max-elements 8;
                        ordered-by user;
                        sros-ext:auto-restart-to-modify;
                        description "Exclude a configuration group at this level";
                    }

                    list fd-avg {
                        key "direction";
                        description "Add a list entry for fd-avg";

                        leaf direction {
                            type types-oam:direction;
                            description "Traffic flow direction of the OAM-PM test or metric";
                        }

                    } // list fd-avg

                    list ifdv-avg {
                        key "direction";
                        description "Add a list entry for ifdv-avg";

                        leaf direction {
                            type types-oam:direction;
                            description "Traffic flow direction of the OAM-PM test or metric";
                        }

                    } // list ifdv-avg

                } // list delay-template

            } // container streaming

        } // container oam-pm

    } // grouping conf-oam-pm

}
