module nokia-oper-perform {

    yang-version "1.1";

    namespace "urn:nokia.com:sros:ns:yang:sr:oper-perform";

    prefix "oper-perform";

    import ietf-yang-types                { prefix "yang"; }
    import nokia-sros-yang-extensions     { prefix "sros-ext"; }
    import nokia-state                    { prefix "state"; }
    import nokia-types-card               { prefix "types-card"; }
    import nokia-types-operation          { prefix "types-operation"; }
    import nokia-types-security           { prefix "types-security"; }
    import nokia-types-services           { prefix "types-services"; }
    import nokia-types-sros               { prefix "types-sros"; }

    sros-ext:sros-major-release "rel25";
    organization "Nokia";
    contact
        "Nokia SR OS Support
         Web: <http://www.nokia.com>";
    description
        "Nokia YANG Data model for perform on SR OS based routers.

         Copyright 2016 Nokia. All rights reserved. Reproduction of this document
         is authorized on the condition that the foregoing copyright notice is included.

         This nokia-oper-perform YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-08";

    container perform {
        config false;
        description "Perform troubleshooting and debugging";

        container application-assurance {
            description "Enter the application-assurance context";

            list aarp {
                key "aarp-id";
                description "Enter the aarp list instance";

                leaf aarp-id {
                    type leafref {
                        path "/state:state/state:application-assurance/state:aarp/state:aarp-id";
                    }
                    description "AARP ID";
                }

                action force-evaluate {
                    description "Force an evaluation of the specific AARP instance";

                    input {

                        leaf force-evaluate {
                            type empty;
                            description "Perform an AARP force-evaluate operation";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action force-evaluate

            } // list aarp

            list group {
                key "aa-group-id";
                description "Enter the group list instance";

                leaf aa-group-id {
                    type leafref {
                        path "/state:state/state:application-assurance/state:group/state:aa-group-id";
                    }
                    description "AA group ID";
                }

                list partition {
                    key "aa-partition-id";
                    description "Enter the partition list instance";

                    leaf aa-partition-id {
                        type leafref {
                            path "/state:state/state:application-assurance/state:group[state:aa-group-id=current()/../../aa-group-id]/state:partition/state:aa-partition-id";
                        }
                        description "AA partition ID";
                    }

                    container aa-sub {
                        description "Enter the aa-sub context";

                        action esm {
                            description "Perform AA operations on an ESM subscriber";

                            input {

                                leaf sub-ident-string {
                                    type types-sros:named-item;
                                    mandatory true;
                                    description "Subscriber ID";
                                }

                                choice option {
                                    case a {

                                        leaf quarantine {
                                            type empty;
                                            description "Quarantine a subscriber";
                                        }

                                    }
                                    case b {

                                        leaf clear-quarantine {
                                            type empty;
                                            description "Remove a subscriber from quarantine";
                                        }

                                    }
                                }
                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action esm

                        action esm-mac {
                            description "Perform AA actions on an ESM-MAC subscriber";

                            input {

                                leaf esm-mac-name {
                                    type types-sros:named-item;
                                    mandatory true;
                                    description "ESM-MAC name";
                                }

                                choice option {
                                    case a {

                                        leaf quarantine {
                                            type empty;
                                            description "Quarantine a subscriber";
                                        }

                                    }
                                    case b {

                                        leaf clear-quarantine {
                                            type empty;
                                            description "Remove a subscriber from quarantine";
                                        }

                                    }
                                }
                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action esm-mac

                        action sap {
                            description "Perform AA actions on a SAP";

                            input {

                                leaf sap-id {
                                    type types-sros:sap;
                                    mandatory true;
                                    description "SAP ID";
                                }

                                choice option {
                                    case a {

                                        leaf quarantine {
                                            type empty;
                                            description "Quarantine a subscriber";
                                        }

                                    }
                                    case b {

                                        leaf clear-quarantine {
                                            type empty;
                                            description "Remove a subscriber from quarantine";
                                        }

                                    }
                                }
                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action sap

                        action spoke-sdp {
                            description "Perform AA actions on a spoke SDP";

                            input {

                                leaf sdp-bind-id {
                                    type types-services:sdp-bind-id;
                                    mandatory true;
                                    description "Spoke-SDP and VC ID";
                                }

                                choice option {
                                    case a {

                                        leaf quarantine {
                                            type empty;
                                            description "Quarantine a subscriber";
                                        }

                                    }
                                    case b {

                                        leaf clear-quarantine {
                                            type empty;
                                            description "Remove a subscriber from quarantine";
                                        }

                                    }
                                }
                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action spoke-sdp

                        action transit {
                            description "Perform AA actions on a transit subscriber";

                            input {

                                leaf transit-aasub-name {
                                    type types-sros:named-item;
                                    mandatory true;
                                    description "Transit subscriber name";
                                }

                                choice option {
                                    case a {

                                        leaf quarantine {
                                            type empty;
                                            description "Quarantine a subscriber";
                                        }

                                    }
                                    case b {

                                        leaf clear-quarantine {
                                            type empty;
                                            description "Remove a subscriber from quarantine";
                                        }

                                    }
                                }
                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action transit

                    } // container aa-sub

                    action tethering {
                        description "Perform AA actions on tethering statistics";

                        input {

                            leaf clear-counters {
                                type empty;
                                mandatory true;
                                description "Clear counters";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action tethering

                } // list partition

                action load-balance {
                    description "Load balance subscribers across ISAs in the group";

                    input {

                        leaf service-id {
                            type types-services:service-id;
                            description "Service ID";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action load-balance

            } // list group

        } // container application-assurance

        list card {
            key "slot-number";
            description "Enter the card list instance";

            leaf slot-number {
                type uint32;
                description "Card slot number";
            }

            action power-cycle {
                description "Force a power cycle of a card";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action power-cycle

        } // list card

        list chassis {
            key "chassis-class chassis-number";
            description "Enter the chassis list instance";

            leaf chassis-class {
                type leafref {
                    path "/state:state/state:chassis/state:chassis-class";
                }
                description "Physical chassis";
            }

            leaf chassis-number {
                type leafref {
                    path "/state:state/state:chassis/state:chassis-number";
                }
                description "Unique index ID for the physical chassis";
            }

            action check-backplane-eprom {
                description "Check chassis backplane EPROM";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    container results {
                        description "Enter the results context";

                        leaf eprom1-status {
                            type types-sros:up-down-status;
                            description "Status of BP EPROM 1";
                        }

                        leaf eprom2-status {
                            type types-sros:up-down-status;
                            description "Status of BP EPROM 2";
                        }

                    } // container results

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action check-backplane-eprom

            action link-check {
                description "Check chassis links";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    container results {
                        description "Enter the results context";

                        list link {
                            key "slot-number instance-id";
                            description "Chassis link";

                            leaf slot-number {
                                type types-card:iom-card-slot;
                                description "The slot number";
                            }

                            leaf instance-id {
                                type string;
                                description "The pluggable instance identifier";
                            }

                            leaf status {
                                type types-sros:up-down-status;
                                description "The status of the chassis link";
                            }

                        } // list link

                    } // container results

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action link-check

        } // list chassis

        list esa {
            key "esa-id";
            description "Enter the esa list instance";

            leaf esa-id {
                type leafref {
                    path "/state:state/state:esa/state:esa-id";
                }
                description "ESA ID";
            }

            action fetch-ahs-log {
                description "Fetch AHS log";

                input {

                    leaf period {
                        type union {
                            type int32 {
                                range "1..31";
                            }
                            type enumeration {
                                enum all                            { value -1; }
                            }
                        }
                        mandatory true;
                        description "Number of days to fetch";
                    }

                    leaf file-url {
                        type types-sros:cflash-and-url;
                        mandatory true;
                        description "File URL";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action fetch-ahs-log

            action reset-management-engine {
                description "Perform management reset operation";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action reset-management-engine

            action fetch-hardware-data {
                description "Fetch hardware data";

                input {

                    leaf file-url {
                        type types-sros:cflash-and-url;
                        mandatory true;
                        description "URL for the system-generated retrievable file";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action fetch-hardware-data

            container show {
                description "Perform ESA maintenance show operations";

                action firmware-versions {
                    description "Display ESA firmware versions";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action firmware-versions

            } // container show

        } // list esa

        container defender-mitigation-system {
            description "Enter the defender-mitigation-system context";

            action dynamic-block-clear {
                description "Clear the dynamic-block state for a tracked source IP";

                input {

                    leaf protected-object {
                        type leafref {
                            path "/state:state/state:defender-mitigation-system/state:protected-object/state:id";
                        }
                        mandatory true;
                        description "PO within which to clear the dynamic-block state";
                    }

                    leaf src-ip-address {
                        type types-sros:ip-address;
                        mandatory true;
                        description "Tracked-source IP address to clear dynamic-block state";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action dynamic-block-clear

            container user-list-import {
                description "Enter the user-list-import context";

                action force-import {
                    description "Force system to attempt to import a new user-list file";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action force-import

            } // container user-list-import

            container show {
                description "Enter the show context";

                container user-list-import {
                    description "Enter the user-list-import context";

                    action dns-list-summary {
                        description "Display a summary of DNS lists imported in user-lists";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            list dns-list {
                                description "Enter the dns-list list instance";

                                leaf list-name {
                                    type types-sros:named-item;
                                }

                                leaf strings {
                                    type uint32;
                                }

                            } // list dns-list

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action dns-list-summary

                    action dns-list {
                        description "Display information for a specific DNS list";

                        input {

                            leaf list-name {
                                type types-sros:named-item;
                                mandatory true;
                                description "DNS list name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            list dns-list-strings {
                                description "Enter the dns-list-strings list instance";

                                leaf query-name {
                                    type string {
                                        length "1..127";
                                    }
                                }

                            } // list dns-list-strings

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action dns-list

                    action tls-fingerprint-list-summary {
                        description "Display a summary of imported TLS fingerprint lists";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action tls-fingerprint-list-summary

                    action tls-fingerprint-list {
                        description "Display information for a specific TLS fingerprint list";

                        input {

                            leaf list-name {
                                type types-sros:named-item;
                                mandatory true;
                                description "TLS fingerprint list name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action tls-fingerprint-list

                } // container user-list-import

                action resources {
                    description "Display Defender Mitigation System resources";

                    input {

                        leaf protected-object {
                            type leafref {
                                path "/state:state/state:defender-mitigation-system/state:protected-object/state:id";
                            }
                            description "PO to check for resources consumed";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action resources

                action tls-fingerprints {
                    description "Display recorded TLS fingerprints for POs";

                    input {

                        leaf protected-object {
                            type leafref {
                                path "/state:state/state:defender-mitigation-system/state:protected-object/state:id";
                            }
                            mandatory true;
                            description "PO to display recorded fingerprints";
                        }

                        leaf tls-client-filter {
                            type leafref {
                                path "/state:state/state:defender-mitigation-system/state:protected-object[state:id=current()/../protected-object]/state:protocol-handlers/state:tls-client-filter/state:tls-client-filter-name";
                            }
                            mandatory true;
                            description "TLS client filter name to display recorded fingerprints";
                        }

                        leaf output-type {
                            type enumeration {
                                enum standard {
                                    value 0;
                                    description "Display the standard output of recorded fingerprints";
                                }
                                enum summary {
                                    value 1;
                                    description "Display a summary of recorded data";
                                }
                            }
                            default "standard";
                            description "Output type to display";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action tls-fingerprints



                list esa {
                    key "esa-id";
                    description "Enter the esa list instance";

                    leaf esa-id {
                        type leafref {
                            path "/state:state/state:esa/state:esa-id";
                        }
                        description "ESA ID";
                    }

                    list vm {
                        key "vm-id";
                        description "Enter the vm list instance";

                        leaf vm-id {
                            type leafref {
                                path "/state:state/state:esa[state:esa-id=current()/../../esa-id]/state:vm/state:vm-id";
                            }
                            description "VM ID within the ESA";
                        }

                        action flow-search {
                            description "Display Defender Mitigation System flow records";

                            input {

                                leaf protected-object {
                                    type leafref {
                                        path "/state:state/state:defender-mitigation-system/state:protected-object/state:id";
                                    }
                                    description "PO within which to search for flows";
                                }

                                leaf src-ip-prefix {
                                    type types-sros:ip-prefix;
                                    description "IP prefix to match to the source-side flow IP address";
                                }

                                leaf dst-port {
                                    type uint32;
                                    description "Destination port of the flow";
                                }

                                leaf flow-state {
                                    type enumeration {
                                        enum any {
                                            value 0;
                                            description "Include all flows";
                                        }
                                        enum active {
                                            value 1;
                                            description "Include only active flows";
                                        }
                                        enum closed {
                                            value 2;
                                            description "Include only closed flows";
                                        }
                                    }
                                    default "any";
                                    description "Status of the flow";
                                }

                                leaf duration {
                                    type uint32 {
                                        range "1..86400";
                                    }
                                    description "Minimum duration of the flow";
                                }

                                leaf total-volume {
                                    type uint32;
                                    units "kilobytes";
                                    description "Minimum amount of total traffic for the flow";
                                }

                                leaf dropped-volume {
                                    type uint32;
                                    units "kilobytes";
                                    description "Minimum amount of dropped traffic for the flow search";
                                }

                                leaf search-type {
                                    type enumeration {
                                        enum standard {
                                            value 0;
                                            description "Display the standard output";
                                        }
                                        enum count {
                                            value 1;
                                            description "Display the total count only";
                                        }
                                    }
                                    default "standard";
                                    description "Type of search to perform";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action flow-search

                        action tracked-source-search {
                            description "Display DMS tracked-source records";

                            input {

                                leaf protected-object {
                                    type leafref {
                                        path "/state:state/state:defender-mitigation-system/state:protected-object/state:id";
                                    }
                                    description "PO within which to search for tracked sources";
                                }

                                leaf source-state {
                                    type enumeration {
                                        enum any {
                                            value 0;
                                            description "Include all sources";
                                        }
                                        enum active {
                                            value 1;
                                            description "Include only active tracked sources";
                                        }
                                        enum closed {
                                            value 2;
                                            description "Include only closed tracked sources";
                                        }
                                        enum dynamic-block {
                                            value 3;
                                            description "Include only temporarily blocked tracked sources";
                                        }
                                    }
                                    default "any";
                                    description "Status of the tracked source";
                                }

                                leaf ip-prefix {
                                    type types-sros:ip-prefix;
                                    description "IP prefix to match to the tracked source";
                                }

                                leaf duration {
                                    type uint32 {
                                        range "1..86400";
                                    }
                                    description "Minimum duration of the tracked source";
                                }

                                leaf total-volume {
                                    type uint32;
                                    units "kilobytes";
                                    description "Minimum amount of total traffic for the tracked source";
                                }

                                leaf dropped-volume {
                                    type uint32;
                                    units "kilobytes";
                                    description "Minimum amount of dropped traffic for tracked source";
                                }

                                leaf dynamic-block-count {
                                    type uint32;
                                    default "0";
                                    description "Minimum dynamic-block occurrences for tracked sources";
                                }

                                leaf search-type {
                                    type enumeration {
                                        enum standard {
                                            value 0;
                                            description "Display the standard output";
                                        }
                                        enum count {
                                            value 1;
                                            description "Display the total count only";
                                        }
                                    }
                                    default "standard";
                                    description "Type of search to perform";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                list tracked-source {
                                    description "Enter the tracked-source list instance";

                                    leaf source-id {
                                        type uint32;
                                        description "The tracked source identifier.";
                                    }

                                    leaf protected-object-id {
                                        type uint32;
                                        description "The identifier for the protected-object which the tracked source was created for.";
                                    }

                                    leaf location {
                                        type enumeration {
                                            enum external {
                                                value 0;
                                                description "The tracked source is external.";
                                            }
                                            enum internal {
                                                value 1;
                                                description "The tracked source is internal (PO).";
                                            }
                                        }
                                        description "The location of the tracked source";
                                    }

                                    leaf source-state {
                                        type enumeration {
                                            enum active {
                                                value 0;
                                                description "The tracked source is active.";
                                            }
                                            enum closed {
                                                value 1;
                                                description "The tracked source is closed (inactive).";
                                            }
                                            enum dynamic-block {
                                                value 2;
                                                description "The tracked source is under dynamic block.";
                                            }
                                        }
                                        description "The current status of the tracked source.";
                                    }

                                    leaf authentication {
                                        type string;
                                        description "The authentication method(s) used on the tracked source.";
                                    }

                                    leaf ip-address {
                                        type types-sros:ip-address;
                                        description "The tracked source IP address.";
                                    }

                                    leaf admitted-packets {
                                        type yang:counter64;
                                        units "packets";
                                        description "The number of admitted packets recorded for the tracked source.";
                                    }

                                    leaf admitted-bytes {
                                        type yang:counter64;
                                        units "bytes";
                                        description "The number of admitted bytes recorded for the tracked source.";
                                    }

                                    leaf discarded-packets {
                                        type yang:counter64;
                                        units "packets";
                                        description "The number of discarded packets recorded for the tracked source.";
                                    }

                                    leaf discarded-bytes {
                                        type yang:counter64;
                                        units "bytes";
                                        description "The number of discarded bytes recorded for the tracked source.";
                                    }

                                    leaf active-flows {
                                        type yang:counter64;
                                        units "flows";
                                        description "The number of active flow records for the tracked source.";
                                    }

                                    leaf closed-flows {
                                        type yang:counter64;
                                        units "flows";
                                        description "The number of closed flow records for the tracked source.";
                                    }

                                    leaf first-packet-time {
                                        type yang:date-and-time;
                                        description "Date and time of the first packet recorded for the tracked source.";
                                    }

                                    leaf last-packet-time {
                                        type yang:date-and-time;
                                        description "Date and time of the last packet recorded for the tracked source.";
                                    }

                                    leaf dynamic-block-count {
                                        type yang:counter64;
                                        description "The number of times the tracked source has transitioned to the dynamic-block state.";
                                    }

                                    leaf last-dynamic-block-time {
                                        type yang:date-and-time;
                                        description
                                            "Expiration date and time for the last dynamic-block penalty applied to the tracked source.
                                             Only available if dynamic-block-count is greater than 0.";
                                    }

                                } // list tracked-source

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action tracked-source-search

                    } // list vm

                } // list esa

            } // container show

        } // container defender-mitigation-system

        container log {
            description "Enter the log context";

            action test-event {
                description "Send a test log event";

                input {

                    leaf custom-text {
                        type string {
                            length "0..800";
                        }
                        default "";
                        description "Custom text of the test event message field";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action test-event

            action custom-event {
                description "Send a custom generic log event";

                input {

                    leaf event-number {
                        type uint32 {
                            range "1..6";
                        }
                        mandatory true;
                        description "Custom event to send";
                    }

                    leaf subject {
                        type string {
                            length "1..32";
                        }
                        mandatory true;
                        description "Subject of the log event";
                    }

                    leaf message-string {
                        type string {
                            length "1..2000";
                        }
                        mandatory true;
                        description "Message for the log event";
                    }

                    leaf parameter1 {
                        type string {
                            length "0..2000";
                        }
                        default "";
                        description "Custom text of the parameter";
                    }

                    leaf parameter2 {
                        type string {
                            length "0..2000";
                        }
                        default "";
                        description "Custom text of the parameter";
                    }

                    leaf parameter3 {
                        type string {
                            length "0..2000";
                        }
                        default "";
                        description "Custom text of the parameter";
                    }

                    leaf parameter4 {
                        type string {
                            length "0..2000";
                        }
                        default "";
                        description "Custom text of the parameter";
                    }

                    leaf parameter5 {
                        type string {
                            length "0..2000";
                        }
                        default "";
                        description "Custom text of the parameter";
                    }

                    leaf parameter6 {
                        type string {
                            length "0..2000";
                        }
                        default "";
                        description "Custom text of the parameter";
                    }

                    leaf parameter7 {
                        type string {
                            length "0..2000";
                        }
                        default "";
                        description "Custom text of the parameter";
                    }

                    leaf parameter8 {
                        type string {
                            length "0..2000";
                        }
                        default "";
                        description "Custom text of the parameter";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action custom-event

        } // container log

        container lag {
            description "Perform LAG operations";

            container force-active {
                description "Perform LAG force-active operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container force-active

            container force-standby {
                description "Perform LAG force-standby operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container force-standby

            container clear-force {
                description "Perform LAG clear-force operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container clear-force

            action load-balance {
                description "Perform LAG load-balance operation";

                input {

                    leaf lag-name {
                        type leafref {
                            path "/state:state/state:lag/state:lag-name";
                        }
                        mandatory true;
                        description "LAG name";
                    }

                    leaf class {
                        type uint32 {
                            range "1..3";
                        }
                        default "1";
                        description "Class used for load balancing";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action load-balance

        } // container lag

        list pcap {
            key "session-name";
            description "Enter the pcap list instance";

            leaf session-name {
                type leafref {
                    path "/state:state/state:mirror/state:mirror-dest/state:pcap/state:session-name";
                }
                description "PCAP session name for the packet capture";
            }

            container capture {
                description "Enter the capture context";

                action start {
                    description "Start PCAP capture";

                    input {

                        leaf url-suffix {
                            type string {
                                length "1..19";
                            }
                            description "pcap capture file-url suffix string.";
                        }

                        leaf timestamp {
                            type boolean;
                            default "false";
                            description "Add a timestamp to the PCAP capture filename";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action start

                action stop {
                    description "Stop PCAP capture";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action stop

            } // container capture

        } // list pcap

        container python {
            description "Enter the python context";

            container python-script {
                description "Enter the python-script context";

                action protect {
                    description "Convert a Python file into a protected SRPY format";

                    input {

                        leaf input-file {
                            type string {
                                length "1..180";
                            }
                            mandatory true;
                            description "URL of the input unprotected script file";
                        }

                        leaf hmac-sha256-key {
                            type string {
                                length "1..128";
                            }
                            mandatory true;
                            description "Key used to compute the hash";
                        }

                        leaf output-file {
                            type string {
                                length "1..180";
                            }
                            mandatory true;
                            description "URL of the output protected script file";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action protect

                container reload {
                    description "Enter the reload context";

                    action script {
                        description "Reload and recompile the specified script";

                        input {

                            leaf name {
                                type leafref {
                                    path "/state:state/state:python/state:python-script/state:name";
                                }
                                mandatory true;
                                description "Name of the python script to reload";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action script

                } // container reload

            } // container python-script

            container python-policy {
                description "Enter the python-policy context";

                container cache {
                    description "Enter the cache context";

                    action policy {
                        description "Set the lifetime of a specified python cache entry";

                        input {

                            leaf name {
                                type leafref {
                                    path "/state:state/state:python/state:python-policy/state:name";
                                }
                                mandatory true;
                                description "Name of the Python policy";
                            }

                            choice hex-or-string {
                                mandatory true;
                                case hex-key {

                                    leaf hex-key {
                                        type types-sros:hex-string {
                                            length "3..1026";
                                        }
                                        description "Policy key in hexadecimal format";
                                    }

                                }
                                case string-key {

                                    leaf string-key {
                                        type string {
                                            length "1..512";
                                        }
                                        description "Policy key in ASCII format";
                                    }

                                }
                            }
                            leaf set-lifetime {
                                type uint32 {
                                    range "1..604800";
                                }
                                units "seconds";
                                mandatory true;
                                description "Lifetime to set for a Python cache entry";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action policy

                } // container cache

            } // container python-policy

        } // container python

        container system {
            description "Enter the system context";

            container power-management {
                description "Enter the power-management context";

                container power-save {
                    description "Enter the power-save context";

                    action low-power-fabric {
                        description "Perform low-power switch fabric operations";

                        input {

                            leaf capacity {
                                type decimal64 {
                                    range "12.50..100.00";
                                    fraction-digits 2;
                                }
                                units "percent";
                                mandatory true;
                                description "Low-power switch fabric mode percentage";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action low-power-fabric


                } // container power-save

            } // container power-management

            container script-control {
                description "Enter the script-control context";

                container script-policy {
                    description "Enter the script-policy context";

                    action stop {
                        description "Stop the execution of scripts";

                        input {

                            choice all-or-policy {
                                mandatory true;
                                case case-all {

                                    leaf all {
                                        type empty;
                                        description "Stop script execution for all script policies";
                                    }

                                }
                                case case-policy {

                                    leaf policy-name {
                                        type leafref {
                                            path "/state:state/state:system/state:script-control/state:script-policy[state:owner=current()/../owner]/state:policy-name";
                                        }
                                        description "Stop script execution for a specific policy";
                                    }

                                    leaf owner {
                                        type leafref {
                                            path "/state:state/state:system/state:script-control/state:script-policy[state:policy-name=current()/../policy-name]/state:owner";
                                        }
                                        default "TiMOS CLI";
                                        description "Stop script execution for a specific owner";
                                    }

                                }
                            }
                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stop

                } // container script-policy

            } // container script-control

            container security {
                description "Enter the security context";

                container secure-boot {
                    description "Enter the secure-boot context";

                    container show {
                        description "Enter the show context";

                        action uefi-variables {
                            description "Display secure-boot UEFI variables";

                            input {

                                leaf card {
                                    type leafref {
                                        path "/state:state/state:cpm/state:cpm-slot";
                                    }
                                    mandatory true;
                                    description "CPM slot where UEFI variables are returned";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf enabled {
                                    type boolean;
                                    description "Whether or not secure-boot is enabled on the CPM.";
                                }

                                container pk {
                                    description "Details of the system-wide pk certificate";

                                    leaf subject {
                                        type types-sros:very-long-description;
                                        description "The subject of the certificate";
                                    }

                                    leaf serial-number {
                                        type types-sros:description;
                                        description "The serial-number of the certificate";
                                    }

                                    leaf raw {
                                        type types-sros:very-long-description;
                                        description "The contents of the certificate";
                                    }

                                } // container pk

                                list kek {
                                    description "Details of a single kek certificate";

                                    leaf subject {
                                        type types-sros:very-long-description;
                                        description "The subject of the certificate";
                                    }

                                    leaf serial-number {
                                        type types-sros:description;
                                        description "The serial-number of the certificate";
                                    }

                                    leaf raw {
                                        type types-sros:very-long-description;
                                        description "The contents of the certificate";
                                    }

                                } // list kek

                                list db {
                                    description "Details of a single db certificate";

                                    container x509 {
                                        description "The x509 signature of the db certificate";

                                        leaf subject {
                                            type types-sros:very-long-description;
                                            description "The subject of the certificate";
                                        }

                                        leaf serial-number {
                                            type types-sros:description;
                                            description "The serial-number of the certificate";
                                        }

                                        leaf raw {
                                            type types-sros:very-long-description;
                                            description "The contents of the certificate";
                                        }

                                    } // container x509

                                } // list db

                                list dbx {
                                    description "Details of a single dbx certficate";

                                    choice signature {
                                        case sha256 {
                                            description "A sha256 signature of a dbx certificate";

                                            leaf value {
                                                type types-sros:very-long-description;
                                                description "The sha256 value for the certificate";
                                            }

                                        }
                                        case x509 {
                                            description "The x509 signature of the dbx certificate";

                                            leaf subject {
                                                type types-sros:very-long-description;
                                                description "The subject of the certificate";
                                            }

                                            leaf serial-number {
                                                type types-sros:description;
                                                description "The serial-number of the certificate";
                                            }

                                            leaf raw {
                                                type types-sros:very-long-description;
                                                description "The contents of the certificate";
                                            }

                                        }
                                    }
                                } // list dbx

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action uefi-variables

                    } // container show

                } // container secure-boot


            } // container security

            container ssh {
                description "Perform SSH operations";

                action generate-keypair {
                    description "Generate SSH authentication key pair";

                    input {

                        leaf save-path {
                            type types-sros:cflash-url;
                            mandatory true;
                            description "Path to save the result key file";
                        }

                        choice key-type {
                            mandatory true;
                            case rsa {

                                leaf rsa-key-size {
                                    type uint32 {
                                        range "2048..4096";
                                    }
                                    default "3072";
                                    description "Length in bits of the RSA key to be generated";
                                }

                            }
                            case ecdsa {

                                leaf ecdsa-curve {
                                    type types-security:ecdsa-curve;
                                    default "secp256r1";
                                    description "Elliptic curve of the ECDSA key to be generated";
                                }

                            }
                            case ed25519 {

                                leaf ed25519 {
                                    type empty;
                                    description "Generate an ed25519 key";
                                }

                            }
                        }
                        leaf passphrase {
                            type string {
                                length "8..256";
                            }
                            description "Passphrase used to protect the generated SSH key";
                        }

                        leaf force {
                            type empty;
                            description "Force the SSH key file overwrite";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action generate-keypair

            } // container ssh

        } // container system

        container filter {
            description "Enter the filter context";

            list ip-filter {
                key "filter-name";
                description "Enter the ip-filter list instance";

                leaf filter-name {
                    type leafref {
                        path "/state:state/state:filter/state:ip-filter/state:filter-name";
                    }
                    description "Name to associate with the IP filter";
                }

                list entry {
                    key "entry-id";
                    description "Enter the entry list instance";

                    leaf entry-id {
                        type leafref {
                            path "/state:state/state:filter/state:ip-filter[state:filter-name=current()/../../filter-name]/state:entry/state:entry-id";
                        }
                        description "ID for the IP filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list ip-filter

            list ipv6-filter {
                key "filter-name";
                description "Enter the ipv6-filter list instance";

                leaf filter-name {
                    type leafref {
                        path "/state:state/state:filter/state:ipv6-filter/state:filter-name";
                    }
                    description "Name to associate with the IPv6 filter";
                }

                list entry {
                    key "entry-id";
                    description "Enter the entry list instance";

                    leaf entry-id {
                        type leafref {
                            path "/state:state/state:filter/state:ipv6-filter[state:filter-name=current()/../../filter-name]/state:entry/state:entry-id";
                        }
                        description "ID for the IPv6 filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list ipv6-filter

            list mac-filter {
                key "filter-name";
                description "Enter the mac-filter list instance";

                leaf filter-name {
                    type leafref {
                        path "/state:state/state:filter/state:mac-filter/state:filter-name";
                    }
                    description "Name to associate with the MAC filter";
                }

                list entry {
                    key "entry-id";
                    description "Enter the entry list instance";

                    leaf entry-id {
                        type leafref {
                            path "/state:state/state:filter/state:mac-filter[state:filter-name=current()/../../filter-name]/state:entry/state:entry-id";
                        }
                        description "ID for the MAC filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list mac-filter

            list redirect-policy {
                key "redirect-policy-name";
                description "Enter the redirect-policy list instance";

                leaf redirect-policy-name {
                    type leafref {
                        path "/state:state/state:filter/state:redirect-policy/state:redirect-policy-name";
                    }
                    description "Name of the redirect policy";
                }

                action activate-best-dest {
                    description "Activate the current best destination";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action activate-best-dest

            } // list redirect-policy

        } // container filter

        list router {
            key "router-instance";
            description "Enter the router list instance";

            leaf router-instance {
                type string;
                description "Router name or VPRN service name";
            }

            list isis {
                key "isis-instance";
                description "Enter the isis list instance";

                leaf isis-instance {
                    type leafref {
                        path "/state:state/state:router[state:router-name=current()/../../router-instance]/state:isis/state:isis-instance";
                    }
                    description "IS-IS instance";
                }

                action ldp-sync-exit {
                    description "Terminate LDP synchronization and restore actual cost";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action ldp-sync-exit

                action overload {
                    description "Perform IS-IS overload";

                    input {

                        leaf seconds {
                            type uint32 {
                                range "60..1800";
                            }
                            mandatory true;
                            description "Overload duration";
                        }

                        leaf max-metric {
                            type boolean;
                            default "false";
                            description "Enable advertising max-metric values";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action overload

                action run-manual-spf {
                    description "Run SPF algorithm";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action run-manual-spf

            } // list isis

            container pim {
                description "Enter the pim context";

                action mc-ecmp-rebalance {
                    description "Perform multicast ECMP rebalance";

                    input {

                        leaf threshold {
                            type uint32 {
                                range "1..7";
                            }
                            description "ECMP preference level threshold";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action mc-ecmp-rebalance

                container show {
                    description "Enter the show context";

                    action iom-failures {
                        description "Display IOM failures";

                        input {

                            leaf detail {
                                type boolean;
                                description "Display IOM failure details";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action iom-failures

                } // container show

            } // container pim

            container mcast-umh-red {
                description "Display Upstream Multi-Homing info";

                container show {
                    description "Enter the show context";

                    action pair {
                        description "Enter the pair context";

                        input {

                            choice filter {
                                case summary {

                                    leaf summary {
                                        type empty;
                                        description "Summary";
                                    }

                                }
                                case card {

                                    leaf card {
                                        type uint32;
                                        description "Slot number";
                                    }

                                }
                                case pair {

                                    leaf pair-id {
                                        type uint32 {
                                            range "1..1000";
                                        }
                                        description "Pair ID";
                                    }

                                }
                            }
                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action pair

                } // container show

            } // container mcast-umh-red

        } // list router

        container gnss {
            description "Enter the gnss context";

            container restart-position-survey {
                description "Enter the restart-position-survey context";

                action all {
                    description "Restart the GNSS position survey on all GNSS ports";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action port {
                    description "Restart the position survey on the specified GNSS port";

                    input {

                        leaf port {
                            type leafref {
                                path "/state:state/state:port/state:port-id";
                            }
                            mandatory true;
                            description "GNSS port for the GNSS position survey";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action port

            } // container restart-position-survey

        } // container gnss

        container mda {
            description "Enter the mda context";

            list card-slot {
                key "slot-number";
                description "Enter the card-slot list instance";

                leaf slot-number {
                    type leafref {
                        path "/state:state/state:card/state:slot-number";
                    }
                    description "Card slot number";
                }

                list mda-slot {
                    key "mda";
                    description "Enter the mda-slot list instance";

                    leaf mda {
                        type leafref {
                            path "/state:state/state:card[state:slot-number=current()/../../slot-number]/state:mda/state:mda-slot";
                        }
                        description "Card MDA slot";
                    }

                    action ptp-reset {
                        description "Reset the PTP timing on the specified MDA";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ptp-reset

                } // list mda-slot

                list xiom-slot {
                    key "xiom";
                    description "Enter the xiom-slot list instance";

                    leaf xiom {
                        type leafref {
                            path "/state:state/state:card[state:slot-number=current()/../../slot-number]/state:xiom/state:xiom-slot";
                        }
                        description "XIOM slot";
                    }

                    list mda-slot {
                        key "mda";
                        description "Enter the mda-slot list instance";

                        leaf mda {
                            type leafref {
                                path "/state:state/state:card[state:slot-number=current()/../../../slot-number]/state:xiom[state:xiom-slot=current()/../../xiom]/state:mda/state:mda-slot";
                            }
                            description "XIOM MDA slot";
                        }

                        action ptp-reset {
                            description "Reset the PTP timing on the specified XIOM MDA";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action ptp-reset

                    } // list mda-slot

                } // list xiom-slot

            } // list card-slot

        } // container mda


        container service {
            description "Service level operations";

            list vprn {
                key "service-name";
                description "Enter the VPRN context";

                leaf service-name {
                    type leafref {
                        path "/state:state/state:service/state:vprn/state:service-name";
                    }
                    description "VPRN service to perform actions on";
                }


                container mvpn {
                    description "MVPN action";

                    action revert-to-primary {
                        description "Initiate revert to primary.";

                        input {

                            leaf umh-pair-id {
                                type uint32 {
                                    range "1..max";
                                }
                                description "UMH pair identification";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action revert-to-primary

                } // container mvpn

            } // list vprn

            list ies {
                key "service-name";
                description "Enter the IES context";

                leaf service-name {
                    type leafref {
                        path "/state:state/state:service/state:ies/state:service-name";
                    }
                    description "IES service to perform actions on";
                }


            } // list ies

            list cpipe {
                key "service-name";
                description "Enter the CPIPE context";

                leaf service-name {
                    type leafref {
                        path "/state:state/state:service/state:cpipe/state:service-name";
                    }
                    description "Name of Cpipe service to perform actions on";
                }

                list sap {
                    key "sap-id";
                    description "Enter CPIPE sap context";

                    leaf sap-id {
                        type leafref {
                            path "/state:state/state:service/state:cpipe/state:sap/state:sap-id";
                        }
                        description "SAP ID";
                    }

                    container cem {
                        description "Enter CPIPE sap CEM context";


                    } // container cem

                } // list sap

            } // list cpipe

        } // container service

    } // container perform

}
