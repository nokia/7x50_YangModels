module nokia-types-lldp {

    yang-version "1.1";

    namespace "urn:nokia.com:sros:ns:yang:sr:types-lldp";

    prefix "types-lldp";

    import nokia-sros-yang-extensions     { prefix "sros-ext"; }

    sros-ext:sros-major-release "rel25";
    organization "Nokia";
    contact
        "Nokia SR OS Support
         Web: <http://www.nokia.com>";
    description
        "Common lldp data types used in the SR OS management system.

         Copyright 2016 Nokia. All rights reserved. Reproduction of this document
         is authorized on the condition that the foregoing copyright notice is included.

         This nokia-types-lldp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    typedef port-id-subtype {
        type enumeration {
            enum interface-alias                { value 1; }
            enum port-component                 { value 2; }
            enum mac-address                    { value 3; }
            enum network-address                { value 4; }
            enum interface-name                 { value 5; }
            enum agent-circuit-id               { value 6; }
            enum local                          { value 7; }
        }
        description "The port identifier subtype.";
    }

    typedef chassis-id-subtype {
        type enumeration {
            enum chassis-component              { value 1; }
            enum interface-alias                { value 2; }
            enum port-component                 { value 3; }
            enum mac-address                    { value 4; }
            enum network-address                { value 5; }
            enum interface-name                 { value 6; }
            enum local                          { value 7; }
        }
        description "The chassis identifier subtype.";
    }

    typedef address-family-numbers {
        type enumeration {
            enum other                          { value 0; }
            enum ipv4                           { value 1; }
            enum ipv6                           { value 2; }
            enum nsap                           { value 3; }
            enum hdlc                           { value 4; }
            enum bbn-1822                       { value 5; }
            enum all-802                        { value 6; }
            enum e163                           { value 7; }
            enum e164                           { value 8; }
            enum f69                            { value 9; }
            enum x121                           { value 10; }
            enum ipx                            { value 11; }
            enum apple-talk                     { value 12; }
            enum dec-net-phase-iv               { value 13; }
            enum banyan-vines                   { value 14; }
            enum e164-with-nsap                 { value 15; }
            enum dns                            { value 16; }
            enum distinguished-name             { value 17; }
            enum as-number                      { value 18; }
            enum xtp-over-ipv4                  { value 19; }
            enum xtp-over-ipv6                  { value 20; }
            enum xtp-native-mode-xtp            { value 21; }
            enum fibre-channel-world-wide-port-name { value 22; }
            enum fibre-channel-world-wide-node-name { value 23; }
            enum gateway-identifier             { value 24; }
            enum reserved                       { value 65535; }
        }
        description
            "Specifies the address numbers family which are derived in the
             Assigned Numbers RFC.";
    }

    typedef chassis-id {
        type string {
            length "1..1023";
        }
        description
            "Specifies the format of a chassis identifier string. Objects
             of this type are always used with an associated chassis-id-subtype
             typedef, which identifies the format.";
    }

    typedef mac-addr-type {
        type enumeration {
            enum nearest-bridge {
                value 1;
                description "Use the nearest bridge";
            }
            enum nearest-non-tpmr {
                value 2;
                description "Use nearest non-Two-Port MAC Relay (TPMR)";
            }
            enum nearest-customer {
                value 3;
                description "Use the nearest customer";
            }
        }
        description "Specifies the MAC address type.";
    }

    typedef management-address {
        type string {
            length "1..128";
        }
        description
            "Specifies the value of a management address associated with
             the LLDP agent that may be used to reach higher layer entities to
             assist discovery by network management.";
    }

    typedef lldp-port-id {
        type string {
            length "1..1023";
        }
        description
            "Specifies the format of a port identifier string. Objects of
             this type are always used with an associated lldp-port-id-subtype
             which identifies the format.";
    }

    typedef lldp-port-id-subtype {
        type enumeration {
            enum interface-alias                { value 1; }
            enum port-component                 { value 2; }
            enum mac-address                    { value 3; }
            enum network-address                { value 4; }
            enum interface-name                 { value 5; }
            enum agent-circuit-id               { value 6; }
            enum local                          { value 7; }
        }
        description "Specifies the source of a particular type of lldp-port-id.";
    }

    typedef system-capabilities {
        type bits {
            bit other                          { position 0; }
            bit repeater                       { position 1; }
            bit bridge                         { position 2; }
            bit wlan-access-point              { position 3; }
            bit router                         { position 4; }
            bit telephone                      { position 5; }
            bit docsis-cable-device            { position 6; }
            bit station-only                   { position 7; }
            bit c-vlan                         { position 8; }
            bit s-vlan                         { position 9; }
            bit two-port-mac-relay             { position 10; }
        }
        description "Specifies the system capabilities.";
    }

}
