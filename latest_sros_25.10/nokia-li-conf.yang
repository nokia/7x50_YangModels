module nokia-li-conf {

    yang-version "1.1";

    namespace "urn:nokia.com:sros:ns:yang:sr:li-conf";

    prefix "li-conf";

    import ietf-inet-types                { prefix "inet"; }
    import ietf-yang-types                { prefix "yang"; }
    import nokia-sros-yang-extensions     { prefix "sros-ext"; }
    import nokia-types-filter             { prefix "types-filter"; }
    import nokia-types-log                { prefix "types-log"; }
    import nokia-types-services           { prefix "types-services"; }
    import nokia-types-sros               { prefix "types-sros"; }
    import nokia-types-subscriber-mgmt    { prefix "types-submgt"; }

    sros-ext:sros-major-release "rel25";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-li-conf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-12-17";

    container li {
        description "Configure lawful intercept";


        container li-filter {
            description "Enter the li-filter context";

            leaf lock-filter {
                type enumeration {
                    enum lock                           { value 0; }
                    enum unlock                         { value 2; }
                }
                default "lock";
                description "Lock state of LI filters";
            }

            list li-ip-filter {
                key "li-filter-name";
                description "Enter the li-ip-filter list instance";

                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                leaf description {
                    type types-sros:description;
                    description "Text description";
                }

                list entry {
                    key "li-entry-id";
                    description "Enter the entry list instance";

                    leaf li-entry-id {
                        type types-filter:limited-entry-id;
                        description "LI filter entry ID";
                    }

                    leaf description {
                        type types-sros:description;
                        description "Text description";
                    }

                    container match {
                        description "Enter the match context";

                        leaf protocol {
                            type types-sros:match-ip-protocol;
                            description "IP protocol to match";
                        }

                        leaf fragment {
                            type enumeration {
                                enum false                          { value 2; }
                                enum true                           { value 3; }
                            }
                            description "Fragmentation state as the match criterion";
                        }

                        container dst-port {
                            description "Enter the dst-port context";

                            choice port {
                                case eq {

                                    leaf eq {
                                        type uint16 {
                                            range "0..65535";
                                        }
                                        description "Condition on equality to specified value";
                                    }

                                }
                                case lt {

                                    leaf lt {
                                        type uint16 {
                                            range "1..65535";
                                        }
                                        description "Condition on being less than the specified value";
                                    }

                                }
                                case gt {

                                    leaf gt {
                                        type uint16 {
                                            range "0..65534";
                                        }
                                        description "Condition on being greater than the specified value";
                                    }

                                }
                                case range {

                                    container range {
                                        presence "Enable the range context";
                                        description "Enable the range context";

                                        leaf start {
                                            type uint16 {
                                                range "0..65534";
                                            }
                                            mandatory true;
                                            description "Lower bound port to match";
                                        }

                                        leaf end {
                                            type uint16 {
                                                range "1..65535";
                                            }
                                            mandatory true;
                                            description "Upper bound port to match";
                                        }

                                    } // container range

                                }
                            }
                        } // container dst-port

                        container src-port {
                            description "Enter the src-port context";

                            choice port {
                                case eq {

                                    leaf eq {
                                        type uint16 {
                                            range "0..65535";
                                        }
                                        description "Condition on equality to specified value";
                                    }

                                }
                                case lt {

                                    leaf lt {
                                        type uint16 {
                                            range "1..65535";
                                        }
                                        description "Condition on being less than the specified value";
                                    }

                                }
                                case gt {

                                    leaf gt {
                                        type uint16 {
                                            range "0..65534";
                                        }
                                        description "Condition on being greater than the specified value";
                                    }

                                }
                                case range {

                                    container range {
                                        presence "Enable the range context";
                                        description "Enable the range context";

                                        leaf start {
                                            type uint16 {
                                                range "0..65534";
                                            }
                                            mandatory true;
                                            description "Lower bound port to match";
                                        }

                                        leaf end {
                                            type uint16 {
                                                range "1..65535";
                                            }
                                            mandatory true;
                                            description "Upper bound port to match";
                                        }

                                    } // container range

                                }
                            }
                        } // container src-port

                        container dst-ip {
                            description "Enter the dst-ip context";

                            leaf address {
                                type union {
                                    type types-sros:ipv4-prefix-with-host-bits;
                                    type types-sros:ipv4-address;
                                }
                                description "IP address to match";
                            }

                            leaf mask {
                                type types-sros:ipv4-address;
                                description "Mask that is applied as an AND to the IP address";
                            }

                        } // container dst-ip

                        container src-ip {
                            description "Enter the src-ip context";

                            leaf address {
                                type union {
                                    type types-sros:ipv4-prefix-with-host-bits;
                                    type types-sros:ipv4-address;
                                }
                                description "IP address to match";
                            }

                            leaf mask {
                                type types-sros:ipv4-address;
                                description "Mask that is applied as an AND to the IP address";
                            }

                        } // container src-ip

                    } // container match

                } // list entry

            } // list li-ip-filter

            list li-ipv6-filter {
                key "li-filter-name";
                description "Enter the li-ipv6-filter list instance";

                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                leaf description {
                    type types-sros:description;
                    description "Text description";
                }

                list entry {
                    key "li-entry-id";
                    description "Enter the entry list instance";

                    leaf li-entry-id {
                        type types-filter:limited-entry-id;
                        description "LI filter entry ID";
                    }

                    leaf description {
                        type types-sros:description;
                        description "Text description";
                    }

                    container match {
                        description "Enter the match context";

                        leaf next-header {
                            type types-sros:match-ip-protocol;
                            description "IP protocol to match";
                        }

                        container dst-port {
                            description "Enter the dst-port context";

                            choice port {
                                case eq {

                                    leaf eq {
                                        type uint16 {
                                            range "0..65535";
                                        }
                                        description "Condition on equality to specified value";
                                    }

                                }
                                case lt {

                                    leaf lt {
                                        type uint16 {
                                            range "1..65535";
                                        }
                                        description "Condition on being less than the specified value";
                                    }

                                }
                                case gt {

                                    leaf gt {
                                        type uint16 {
                                            range "0..65534";
                                        }
                                        description "Condition on being greater than the specified value";
                                    }

                                }
                                case range {

                                    container range {
                                        presence "Enable the range context";
                                        description "Enable the range context";

                                        leaf start {
                                            type uint16 {
                                                range "0..65534";
                                            }
                                            mandatory true;
                                            description "Lower bound port to match";
                                        }

                                        leaf end {
                                            type uint16 {
                                                range "1..65535";
                                            }
                                            mandatory true;
                                            description "Upper bound port to match";
                                        }

                                    } // container range

                                }
                            }
                        } // container dst-port

                        container src-port {
                            description "Enter the src-port context";

                            choice port {
                                case eq {

                                    leaf eq {
                                        type uint16 {
                                            range "0..65535";
                                        }
                                        description "Condition on equality to specified value";
                                    }

                                }
                                case lt {

                                    leaf lt {
                                        type uint16 {
                                            range "1..65535";
                                        }
                                        description "Condition on being less than the specified value";
                                    }

                                }
                                case gt {

                                    leaf gt {
                                        type uint16 {
                                            range "0..65534";
                                        }
                                        description "Condition on being greater than the specified value";
                                    }

                                }
                                case range {

                                    container range {
                                        presence "Enable the range context";
                                        description "Enable the range context";

                                        leaf start {
                                            type uint16 {
                                                range "0..65534";
                                            }
                                            mandatory true;
                                            description "Lower bound port to match";
                                        }

                                        leaf end {
                                            type uint16 {
                                                range "1..65535";
                                            }
                                            mandatory true;
                                            description "Upper bound port to match";
                                        }

                                    } // container range

                                }
                            }
                        } // container src-port

                        container dst-ip {
                            description "Enter the dst-ip context";

                            leaf address {
                                type union {
                                    type types-sros:ipv6-prefix-with-host-bits;
                                    type types-sros:ipv6-address;
                                }
                                description "IP address to match";
                            }

                            leaf mask {
                                type types-sros:ipv6-address;
                                description "Mask that is applied as an AND to the IPv6 address";
                            }

                        } // container dst-ip

                        container src-ip {
                            description "Enter the src-ip context";

                            leaf address {
                                type union {
                                    type types-sros:ipv6-prefix-with-host-bits;
                                    type types-sros:ipv6-address;
                                }
                                description "IP address to match";
                            }

                            leaf mask {
                                type types-sros:ipv6-address;
                                description "Mask that is applied as an AND to the IPv6 address";
                            }

                        } // container src-ip

                    } // container match

                } // list entry

            } // list li-ipv6-filter

            list li-mac-filter {
                key "li-filter-name";
                description "Enter the li-mac-filter list instance";

                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                leaf description {
                    type types-sros:description;
                    description "Text description";
                }

                list entry {
                    key "li-entry-id";
                    description "Enter the entry list instance";

                    leaf li-entry-id {
                        type types-filter:limited-entry-id;
                        description "LI filter entry ID";
                    }

                    leaf description {
                        type types-sros:description;
                        description "Text description";
                    }

                    container match {
                        description "Enter the match context";

                        leaf frame-type {
                            type types-filter:mac-frame-type;
                            default "802dot3";
                            description "Frame type for MAC filter match";
                        }

                        leaf sap {
                            type types-sros:sap;
                            description "QinQ SAP for filter match";
                        }

                        leaf outer-tag {
                            type int32 {
                                range "1..4094";
                            }
                            description "Outer tag for the QinQ SAP for filter match";
                        }

                        container dst-mac {
                            presence "Enable the dst-mac context";
                            description "Enable the dst-mac context";

                            leaf address {
                                type yang:mac-address;
                                mandatory true;
                                description "MAC address for filter match";
                            }

                            leaf mask {
                                type yang:mac-address;
                                default "ff:ff:ff:ff:ff:ff";
                                description "MAC address mask for filter match";
                            }

                        } // container dst-mac

                        container src-mac {
                            presence "Enable the src-mac context";
                            description "Enable the src-mac context";

                            leaf address {
                                type yang:mac-address;
                                mandatory true;
                                description "MAC address for filter match";
                            }

                            leaf mask {
                                type yang:mac-address;
                                default "ff:ff:ff:ff:ff:ff";
                                description "MAC address mask for filter match";
                            }

                        } // container src-mac

                    } // container match

                } // list entry

            } // list li-mac-filter

            container associations {
                description "Enter the associations context";

                list li-ip-filter {
                    key "li-filter-name";
                    description "Enter the li-ip-filter list instance";

                    leaf li-filter-name {
                        type leafref {
                            path "../../../li-ip-filter/li-filter-name";
                        }
                        description "Name of an existing LI IP filter";
                    }

                    list ip-filter {
                        key "filter-name";
                        min-elements 1;
                        max-elements 1;
                        description "Add a list entry for ip-filter";

                        leaf filter-name {
                            type types-filter:filter-name;
                            description "IP filter to be associated with specified LI IP filter";
                        }

                    } // list ip-filter

                } // list li-ip-filter

                list li-ipv6-filter {
                    key "li-filter-name";
                    description "Enter the li-ipv6-filter list instance";

                    leaf li-filter-name {
                        type leafref {
                            path "../../../li-ipv6-filter/li-filter-name";
                        }
                        description "LI IPv6 filter name";
                    }

                    list ipv6-filter {
                        key "filter-name";
                        min-elements 1;
                        max-elements 1;
                        description "Add a list entry for ipv6-filter";

                        leaf filter-name {
                            type types-filter:filter-name;
                            description "IP filter to be associated with specified LI IP filter";
                        }

                    } // list ipv6-filter

                } // list li-ipv6-filter

                list li-mac-filter {
                    key "li-filter-name";
                    description "Enter the li-mac-filter list instance";

                    leaf li-filter-name {
                        type leafref {
                            path "../../../li-mac-filter/li-filter-name";
                        }
                        description "LI MAC filter name";
                    }

                    list mac-filter {
                        key "filter-name";
                        min-elements 1;
                        max-elements 1;
                        description "Add a list entry for mac-filter";

                        leaf filter-name {
                            type types-filter:filter-name;
                            description "IP filter to be associated with specified LI IP filter";
                        }

                    } // list mac-filter

                } // list li-mac-filter

            } // container associations

            list reserved-block {
                key "block-name";
                max-elements 8;
                description "Enter the reserved-block list instance";

                leaf block-name {
                    type types-sros:named-item {
                        pattern "((([^d_ ]|d($|[^e]|e($|[^f]|f($|[^a]|a($|[^u]|u($|[^l]|l($|[^t]|t\\P{C})))))))\\P{C}*))";
                    }
                    description "Object uniquely identifying an LI reserved block";
                }

                leaf description {
                    type types-sros:description;
                    description "Text description";
                }

                list ip-filter {
                    key "filter-name";
                    description "Add a list entry for ip-filter";

                    leaf filter-name {
                        type types-filter:filter-name;
                        description "IP filter ID for LI filter reserved block";
                    }

                } // list ip-filter

                list ipv6-filter {
                    key "filter-name";
                    description "Add a list entry for ipv6-filter";

                    leaf filter-name {
                        type types-filter:filter-name;
                        description "IP filter ID for LI filter reserved block";
                    }

                } // list ipv6-filter

                list mac-filter {
                    key "filter-name";
                    description "Add a list entry for mac-filter";

                    leaf filter-name {
                        type types-filter:filter-name;
                        description "IP filter ID for LI filter reserved block";
                    }

                } // list mac-filter

                container entry-range {
                    presence "Enable the entry-range context";
                    description "Enable the entry-range context";

                    leaf start {
                        type types-filter:entry-id;
                        mandatory true;
                        description "Lower bound of the range";
                    }

                    leaf end {
                        type types-filter:entry-id;
                        mandatory true;
                        description "Upper bound of the range";
                    }

                } // container entry-range

            } // list reserved-block

        } // container li-filter

        list li-source {
            key "service-name";
            description "Enter the li-source list instance";

            leaf service-name {
                type types-services:service-name;
                description "Administrative service name";
            }

            leaf admin-state {
                type types-sros:admin-state;
                default "enable";
                description "Administrative state of mirror service";
            }

            list port {
                key "port-id";
                description "Enter the port list instance";

                leaf port-id {
                    type types-services:mirror-source-port-lag-key;
                    description "Port ID";
                }

                leaf ingress {
                    type boolean;
                    default "false";
                    description "Perform lawful intercept on ingress traffic";
                }

                leaf egress {
                    type boolean;
                    default "false";
                    description "Perform lawful intercept on egress traffic";
                }

            } // list port

            list sap {
                key "sap-id";
                description "Enter the sap list instance";

                leaf intercept-id {
                    type types-services:li-interception-identifier;
                    description "Intercept ID of the traffic flow";
                }

                leaf session-id {
                    type types-services:li-session-identifier;
                    description "Session ID of the traffic flow";
                }

                leaf sap-id {
                    type types-sros:sap;
                    description "SAP ID";
                }

                leaf ingress {
                    type boolean;
                    default "false";
                    description "Perform lawful intercept on ingress traffic";
                }

                leaf egress {
                    type boolean;
                    default "false";
                    description "Perform lawful intercept on egress traffic";
                }

            } // list sap

            list li-ip-filter {
                key "li-filter-name";
                description "Enter the li-ip-filter list instance";

                leaf li-filter-name {
                    type leafref {
                        path "../../../li-filter/li-ip-filter/li-filter-name";
                    }
                    description "A unique ID for an li-ip-filter";
                }

                list entry {
                    key "li-entry-id";
                    min-elements 1;
                    description "Enter the entry list instance";

                    leaf li-entry-id {
                        type leafref {
                            path "../../../../li-filter/li-ip-filter[li-filter-name=current()/../../li-filter-name]/entry/li-entry-id";
                        }
                        description "A unique ID for an li-ip-filter entry";
                    }

                    leaf intercept-id {
                        type types-services:li-interception-identifier;
                        description "Intercept ID of the traffic flow";
                    }

                    leaf session-id {
                        type types-services:li-session-identifier;
                        description "Session ID of the traffic flow";
                    }

                } // list entry

            } // list li-ip-filter

            list li-ipv6-filter {
                key "li-filter-name";
                description "Enter the li-ipv6-filter list instance";

                leaf li-filter-name {
                    type leafref {
                        path "../../../li-filter/li-ipv6-filter/li-filter-name";
                    }
                    description "A unique ID for an li-ipv6-filter";
                }

                list entry {
                    key "li-entry-id";
                    min-elements 1;
                    description "Enter the entry list instance";

                    leaf li-entry-id {
                        type leafref {
                            path "../../../../li-filter/li-ipv6-filter[li-filter-name=current()/../../li-filter-name]/entry/li-entry-id";
                        }
                        description "A unique ID for an li-ipv6-filter entry";
                    }

                    leaf intercept-id {
                        type types-services:li-interception-identifier;
                        description "Intercept ID of the traffic flow";
                    }

                    leaf session-id {
                        type types-services:li-session-identifier;
                        description "Session ID of the traffic flow";
                    }

                } // list entry

            } // list li-ipv6-filter

            list li-mac-filter {
                key "li-filter-name";
                description "Enter the li-mac-filter list instance";

                leaf li-filter-name {
                    type leafref {
                        path "../../../li-filter/li-mac-filter/li-filter-name";
                    }
                    description "A unique ID for an li-mac-filter";
                }

                list entry {
                    key "li-entry-id";
                    min-elements 1;
                    description "Enter the entry list instance";

                    leaf li-entry-id {
                        type leafref {
                            path "../../../../li-filter/li-mac-filter[li-filter-name=current()/../../li-filter-name]/entry/li-entry-id";
                        }
                        description "A unique ID for an li-mac-filter entry";
                    }

                    leaf intercept-id {
                        type types-services:li-interception-identifier;
                        description "Intercept ID of the traffic flow";
                    }

                    leaf session-id {
                        type types-services:li-session-identifier;
                        description "Session ID of the traffic flow";
                    }

                } // list entry

            } // list li-mac-filter

            container nat {
                description "Enter the nat context";

                container ethernet-header {
                    description "Enter the ethernet-header context";

                    leaf source-address {
                        type types-sros:mac-address;
                        description "Source MAC address field of the Ethernet encapsulation";
                    }

                    leaf destination-address {
                        type types-sros:mac-address;
                        description "Destination MAC address field of Ethernet encapsulation";
                    }

                    leaf type {
                        type uint16 {
                            range "1536..65535";
                        }
                        default "1792";
                        description "Ethertype of the ethernet encapsulation";
                    }

                } // container ethernet-header

                list nat44 {
                    key "router-instance ip";
                    description "Enter the nat44 list instance";

                    leaf router-instance {
                        type types-services:service-name;
                        description "Name of the service";
                    }

                    leaf ip {
                        type types-sros:ipv4-address;
                        description "IP address of the subscriber";
                    }

                    leaf intercept-id {
                        type types-services:li-interception-identifier-wide;
                        description "The intercept id of the traffic flow";
                    }

                    leaf session-id {
                        type types-services:li-session-identifier;
                        description "The session id of the traffic flow";
                    }

                } // list nat44

                list dslite {
                    key "router-instance b4";
                    description "Enter the dslite list instance";

                    leaf router-instance {
                        type types-services:service-name;
                        description "Name of the service";
                    }

                    leaf b4 {
                        type types-sros:ipv6-prefix;
                        description "B4 prefix of the subscriber";
                    }

                    leaf intercept-id {
                        type types-services:li-interception-identifier-wide;
                        description "The intercept id of the traffic flow";
                    }

                    leaf session-id {
                        type types-services:li-session-identifier;
                        description "The session id of the traffic flow";
                    }

                } // list dslite

                list nat64 {
                    key "router-instance ip";
                    description "Enter the nat64 list instance";

                    leaf router-instance {
                        type types-services:service-name;
                        description "Name of the service";
                    }

                    leaf ip {
                        type types-sros:ipv6-prefix;
                        description "IP prefix of the subscriber";
                    }

                    leaf intercept-id {
                        type types-services:li-interception-identifier-wide;
                        description "The intercept id of the traffic flow";
                    }

                    leaf session-id {
                        type types-services:li-session-identifier;
                        description "The session id of the traffic flow";
                    }

                } // list nat64

                list l2-aware {
                    key "subscriber-id";
                    description "Enter the l2-aware list instance";

                    leaf subscriber-id {
                        type types-submgt:subscriber-id;
                        description "The string identifying the subscribe";
                    }

                    leaf intercept-id {
                        type types-services:li-interception-identifier-wide;
                        description "The intercept id of the traffic flow";
                    }

                    leaf session-id {
                        type types-services:li-session-identifier;
                        description "The session id of the traffic flow";
                    }

                } // list l2-aware

            } // container nat

            list wlan-gw-dsm-ue {
                key "mac";
                description "Enter the wlan-gw-dsm-ue list instance";

                leaf mac {
                    type yang:mac-address;
                    description "MAC address of the DSM UE";
                }

                leaf intercept-id {
                    type types-services:li-interception-identifier-wide;
                    description "Intercept identifier";
                }

                leaf session-id {
                    type types-services:li-session-identifier;
                    description "Session identifier";
                }

            } // list wlan-gw-dsm-ue

            list subscriber {
                key "subscriber-id";
                description "Enter the subscriber list instance";

                leaf subscriber-id {
                    type types-submgt:subscriber-id;
                    description "Subscriber ID";
                }

                leaf ingress {
                    type boolean;
                    default "false";
                    description "Perform lawful intercept on ingress traffic";
                }

                leaf egress {
                    type boolean;
                    default "false";
                    description "Perform lawful intercept on egress traffic";
                }

                leaf-list fc {
                    type enumeration {
                        enum be                             { value 0; }
                        enum l2                             { value 1; }
                        enum af                             { value 2; }
                        enum l1                             { value 3; }
                        enum h2                             { value 4; }
                        enum ef                             { value 5; }
                        enum h1                             { value 6; }
                        enum nc                             { value 7; }
                    }
                    max-elements 8;
                    description "Forwarding classes to be mirrored";
                }

                leaf host-type {
                    type enumeration {
                        enum ipoe                           { value 2; }
                        enum ppp                            { value 3; }
                    }
                    description "Subscriber host type to be monitored";
                }

                leaf ip-family {
                    type enumeration {
                        enum ipv4                           { value 2; }
                        enum ipv6                           { value 3; }
                    }
                    description "IP family for LI";
                }

                leaf intercept-id {
                    type types-services:li-interception-identifier;
                    description "Intercept ID of the traffic flow";
                }

                leaf session-id {
                    type types-services:li-session-identifier;
                    description "Session ID of the traffic flow";
                }

                choice host-identification {
                    case sap-id {

                        leaf sap-id {
                            type types-sros:sap;
                            description "SAP ID";
                        }

                        leaf mac-address {
                            type yang:mac-address;
                            description "The source MAC address";
                        }

                        leaf ip-address {
                            type types-sros:ipv4-address;
                            description "IP address of the subscriber";
                        }

                    }
                    case sla-profile {

                        leaf sla-profile {
                            type types-sros:external-named-item;
                            description "SLA profile";
                        }

                    }
                }
            } // list subscriber

        } // list li-source

        container log {
            description "Enter the log context";

            list log-id {
                key "name";
                max-elements 30;
                description "Enter the log-id list instance";

                leaf name {
                    type types-log:li-log-name;
                    description "Log ID";
                }

                leaf admin-state {
                    type types-sros:admin-state;
                    default "enable";
                    description "The administrative state of the log";
                }

                leaf description {
                    type types-sros:description;
                    description "Text description";
                }

                leaf netconf-stream {
                    type types-sros:named-item;
                    description "Destination NETCONF stream name";
                }

                leaf time-format {
                    type enumeration {
                        enum utc                            { value 1; }
                        enum local                          { value 2; }
                    }
                    default "utc";
                    description "Time zone to display date and time";
                }

                leaf filter {
                    type types-log:log-filter-name;
                    description "Event filter ID to associate with log ID configuration";
                }

                container source {
                    description "Enter the source context";

                    leaf li {
                        type boolean;
                        default "false";
                        description "Event stream for events configured for LI activities";
                    }

                } // container source

                container destination {
                    description "Enter the destination context";

                    choice log-id-destination {
                        case memory {

                            container memory {
                                presence "Enable the memory context";
                                description "Enable the memory context";

                                leaf max-entries {
                                    type uint32 {
                                        range "50..1024";
                                    }
                                    sros-ext:immutable;
                                    default "100";
                                    description "Number of events stored in this memory log";
                                }

                            } // container memory

                        }
                        case snmp {

                            container snmp {
                                presence "Enable the snmp context";
                                description "Enable the snmp context";

                                leaf max-entries {
                                    type uint32 {
                                        range "50..1024";
                                    }
                                    sros-ext:immutable;
                                    default "100";
                                    description "Number of events stored in this snmp log";
                                }

                                leaf send-using-vprn {
                                    type types-services:service-name;
                                    sros-ext:immutable;
                                    description "VPRN to use to send SNMP notifications";
                                }

                            } // container snmp

                        }
                        case netconf {

                            container netconf {
                                presence "Enable the netconf context";
                                description "Enable the netconf context";

                                leaf max-entries {
                                    type uint32 {
                                        range "50..1024";
                                    }
                                    sros-ext:immutable;
                                    default "100";
                                    description "Maximum number of events stored in the NETCONF log";
                                }

                            } // container netconf

                        }
                    }
                } // container destination

            } // list log-id

        } // container log

        container management {
            description "Enter the management context";

            leaf tech-support-li-info {
                type enumeration {
                    enum include                        { value 0; }
                    enum exclude                        { value 1; }
                }
                default "include";
                description "Specifies whether lawful interception is included or excluded in tech support output.";
            }

        } // container management

        container mirror-dest-reservation {
            description "Enter the mirror-dest-reservation context";

            leaf start {
                type uint32 {
                    range "1..2147483647";
                }
                description "Lower bound of the mirror destination ID";
            }

            leaf end {
                type uint32 {
                    range "1..2147483647";
                }
                description "Upper bound of the mirror destination ID";
            }

        } // container mirror-dest-reservation

        list mirror-dest-template {
            key "name";
            max-elements 8;
            description "Enter the mirror-dest-template list instance";

            leaf name {
                type types-sros:named-item;
                description "Mirror destination template name";
            }

            leaf type {
                type types-services:mirror-type;
                sros-ext:immutable;
                default "ether";
                description "Encapsulation type supported by the mirror service";
            }

            container layer-3-encap {
                description "Enter the layer-3-encap context";

                leaf router-instance {
                    type types-sros:router-instance;
                    default "Base";
                    description "Virtual router instance to inject mirrored packets";
                }

                leaf encap-type {
                    type enumeration {
                        enum ip-udp-shim                    { value 1; }
                        enum ip-gre                         { value 2; }
                    }
                    sros-ext:immutable;
                    default "ip-udp-shim";
                    description "Header type of the layer 3 encapsulation";
                }

                leaf direction-bit {
                    type boolean;
                    default "false";
                    description "Use highest bit in interception ID for flow direction";
                }

                leaf ip-source {
                    type types-sros:ipv4-unicast-address;
                    description "Source IPv4 address for Layer 3 encapsulation";
                }

                container udp {
                    description "Enter the udp context";

                    leaf source {
                        when "../../encap-type = 'ip-udp-shim'" {
                            description "header type must be ip-udp-shim";
                        }
                        type types-sros:tcp-udp-port-non-zero;
                        description "Source UDP port";
                    }

                    leaf destination {
                        when "../../encap-type = 'ip-udp-shim'" {
                            description "header type must be ip-udp-shim";
                        }
                        type types-sros:tcp-udp-port-non-zero;
                        description "Destination UDP port";
                    }

                } // container udp

            } // container layer-3-encap

        } // list mirror-dest-template

        container nat {
            description "Enter the nat context";

            leaf use-outside-ip-address {
                type boolean;
                default "false";
                description "Report outside IP address for L2-Aware NAT subscribers";
            }

        } // container nat

        container radius {
            description "Enter the radius context";

            leaf mirror-dest-template {
                type leafref {
                    path "../../mirror-dest-template/name";
                }
                description "RADIUS triggered mirror destination template";
            }

        } // container radius

        container sci {
            description "Enter the sci context";

            leaf pfcp-li-shared-key {
                type types-sros:encrypted-leaf {
                    length "1..199";
                }
                description "Key used to encrypt and decrypt exchanged LI PFCP IEs";
            }

        } // container sci


        container x-interfaces {
            description "Enter the x-interfaces context";

            leaf admin-state {
                type types-sros:admin-state;
                default "disable";
                description "Administrative state of the x-interfaces";
            }

            leaf ine-identifier {
                type types-sros:named-item;
                description "Intercepting Network Element (INE) ID";
            }

            leaf user-db {
                type types-sros:named-item;
                description "Location of the data-trigger host for the LIC";
            }

            container correlation-id {
                description "Enter the correlation-id context";

                leaf ipoe {
                    type enumeration {
                        enum radius-host-acct-id            { value 1; }
                        enum radius-queue-acct-id           { value 2; }
                        enum radius-session-acct-id         { value 3; }
                    }
                    default "radius-host-acct-id";
                    description "RADIUS accounting ID type for subscriber correlation";
                }

                leaf pppoe {
                    type enumeration {
                        enum radius-host-acct-id            { value 1; }
                        enum radius-queue-acct-id           { value 2; }
                        enum radius-session-acct-id         { value 3; }
                    }
                    default "radius-host-acct-id";
                    description "RADIUS accounting ID type for subscriber correlation";
                }

            } // container correlation-id

            list lic {
                key "name";
                max-elements 18;
                description "Enter the lic list instance";

                leaf name {
                    type types-sros:named-item;
                    description "LIC name";
                }

                leaf description {
                    type types-sros:description;
                    description "Text description";
                }

                leaf identifier {
                    type types-sros:named-item;
                    description "LIC ID";
                }

                leaf port {
                    type inet:port-number;
                    description "TCP port associated with the LIC";
                }

                leaf router-instance {
                    type types-sros:named-item-64-or-empty;
                    default "";
                    description "Virtual router instance used by the X-interfaces";
                }

                container ipv4 {
                    description "Enter the ipv4 context";

                    leaf ip-address {
                        type types-sros:ip-address;
                        description "IP address of the LIC";
                    }

                } // container ipv4

                container authentication {
                    description "Enter the authentication context";

                    leaf password {
                        type types-sros:li-static-encrypted-leaf-hex {
                            length "1..50";
                        }
                        description "Password for the X1 and X2 interfaces";
                    }

                    leaf private-ki {
                        type types-sros:li-static-encrypted-leaf {
                            length "1..50";
                        }
                        description "Private Ki string for the X1 and X2 interfaces";
                    }

                    leaf sequence-group {
                        type types-sros:li-static-encrypted-leaf {
                            length "1..42";
                        }
                        description "Sequence group for the X1 and X2 interfaces";
                    }

                } // container authentication

            } // list lic

            container x1 {
                description "Enter the x1 context";

                leaf lic-peer {
                    type leafref {
                        path "../../lic/name";
                    }
                    description "Peer LIC for the X1 interface";
                }

                leaf local-tcp-port {
                    type types-sros:tcp-udp-port-non-zero {
                        range "1..65535";
                    }
                    description "Local TCP port used for the X1 interface";
                }

                container ipv4 {
                    description "Enter the ipv4 context";

                    leaf local-address {
                        type types-sros:ip-address;
                        description "X1 interface IP address";
                    }

                } // container ipv4

                container timeouts {
                    description "Enter the timeouts context";

                    leaf message-timeout {
                        type uint32 {
                            range "180..300";
                        }
                        units "seconds";
                        default "180";
                        description "Maximum time for the LIC to reply to an X1 message";
                    }

                } // container timeouts

            } // container x1

            container x2 {
                description "Enter the x2 context";

                leaf lic-peer {
                    type leafref {
                        path "../../lic/name";
                    }
                    description "Peer LIC for the X2 interface";
                }

                container ipv4 {
                    description "Enter the ipv4 context";

                    leaf local-address {
                        type types-sros:ip-address;
                        description "X2 interface IP address";
                    }

                } // container ipv4

                container timeouts {
                    description "Enter the timeouts context";

                    leaf keep-alive {
                        type uint32 {
                            range "300..600";
                        }
                        units "seconds";
                        default "300";
                        description "Keep-alive timeout";
                    }

                    leaf request {
                        type uint32 {
                            range "5..30";
                        }
                        units "seconds";
                        default "5";
                        description "Tx2-normal timeout";
                    }

                } // container timeouts

            } // container x2

            container x3 {
                description "Enter the x3 context";

                leaf li-group {
                    type uint32 {
                        range "1..4";
                    }
                    description "ISA group of the X3 interface";
                }

                leaf session-limit {
                    type uint32 {
                        range "1..32";
                    }
                    default "32";
                    description "Maximum number of X3 sessions initiated to the LIC";
                }

                container ipv4 {
                    description "Enter the ipv4 context";

                    container local-address-range {
                        description "Enter the local-address-range context";

                        leaf start {
                            type types-sros:ipv4-unicast-address;
                            description "Lower bound of the range";
                        }

                        leaf end {
                            type types-sros:ipv4-unicast-address;
                            description "Upper bound of the range";
                        }

                    } // container local-address-range

                } // container ipv4

                container alarms {
                    description "Enter the alarms context";

                    container cpu-alarm {
                        description "Enter the cpu-alarm context";

                        leaf low-threshold {
                            type uint32 {
                                range "0..99";
                            }
                            units "percent";
                            default "0";
                            description "Low threshold value of the CPU usage alarm";
                        }

                        leaf high-threshold {
                            type uint32 {
                                range "1..100";
                            }
                            units "percent";
                            description "High threshold value of the CPU usage alarm";
                        }

                    } // container cpu-alarm

                    container memory-alarm {
                        description "Enter the memory-alarm context";

                        leaf low-threshold {
                            type uint32 {
                                range "0..99";
                            }
                            units "percent";
                            default "0";
                            description "Low threshold of the packet buffer memory usage alarm";
                        }

                        leaf high-threshold {
                            type uint32 {
                                range "1..100";
                            }
                            units "percent";
                            description "High threshold of the packet buffer memory usage alarm";
                        }

                    } // container memory-alarm

                    container throughput-alarm {
                        description "Enter the throughput-alarm context";

                        leaf low-threshold {
                            type uint32 {
                                range "1..4294967295";
                            }
                            units "megabps";
                            description "Low threshold value of the throughput alarm";
                        }

                        leaf high-threshold {
                            type uint32 {
                                range "1..4294967295";
                            }
                            units "megabps";
                            description "High threshold value of the throughput alarm";
                        }

                    } // container throughput-alarm

                } // container alarms

                list lic-peers {
                    key "name";
                    max-elements 16;
                    description "Add a list entry for lic-peers";

                    leaf name {
                        type leafref {
                            path "../../../lic/name";
                        }
                        description "Peer LIC for the X3 interface";
                    }

                } // list lic-peers

                container timeouts {
                    description "Enter the timeouts context";

                    leaf keep-alive {
                        type uint32 {
                            range "300..600";
                        }
                        units "seconds";
                        default "300";
                        description "Keep-alive timeout";
                    }

                    leaf request {
                        type uint32 {
                            range "5..30";
                        }
                        units "seconds";
                        default "5";
                        description "Tx3-normal timeout";
                    }

                    leaf target-retry-wait {
                        type uint32 {
                            range "300..1200";
                        }
                        units "seconds";
                        default "300";
                        description "Retry interval for target tunnel setup";
                    }

                } // container timeouts

            } // container x3

        } // container x-interfaces

    } // container li

}
