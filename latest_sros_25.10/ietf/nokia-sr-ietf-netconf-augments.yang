module nokia-sr-ietf-netconf-augments {

    yang-version "1.1";

    namespace "urn:nokia.com:sros:ns:yang:sr:ietf-netconf-augments";

    prefix "nokia-nc-augs";

    import ietf-netconf                   { prefix "nc"; }
    import nokia-sros-yang-extensions     { prefix "sros-ext"; }

    sros-ext:sros-major-release "rel25";
    organization "Nokia";
    contact
        "Nokia SR OS Support
         Web: <http://www.nokia.com>";
    description
        "This module contains the list of augments against the ietf-netconf
         module for the Nokia SR OS based routers.

         Copyright 2016 Nokia. All rights reserved. Reproduction of this document
         is authorized on the condition that the foregoing copyright notice is included.

         This nokia-sr-ietf-netconf-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    augment /nc:get-config/nc:input/nc:source {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:validate/nc:input/nc:source {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:copy-config/nc:input/nc:source {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:copy-config/nc:input/nc:target {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:edit-config/nc:input/nc:target {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:lock/nc:input/nc:target {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:unlock/nc:input/nc:target {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:get/nc:input {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:discard-changes/nc:input {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

    }

    augment /nc:commit/nc:input {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

        leaf comment {
            type string {
                length "1..2048";
            }
            description "Comment associated with the commit";
        }

    }

    augment /nc:get-config/nc:input/nc:source/nc:config-source {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:validate/nc:input/nc:source/nc:config-source {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:copy-config/nc:input/nc:source/nc:config-source {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:copy-config/nc:input/nc:target/nc:config-target {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:edit-config/nc:input/nc:target/nc:config-target {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:lock/nc:input/nc:target/nc:config-target {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:unlock/nc:input/nc:target/nc:config-target {
        leaf li-candidate {
            type empty;
            description "The li candidate datastore is the config source";
        }

        leaf li-running {
            type empty;
            description "The li running datastore is the config source";
        }

        leaf li-startup {
            type empty;
            description "The li startup datastore is the config source";
        }

        leaf bof-candidate {
            type empty;
            description "The bof candidate datastore is the config source";
        }

        leaf bof-running {
            type empty;
            description "The bof running datastore is the config source";
        }

        leaf bof-startup {
            type empty;
            description "The bof startup datastore is the config source";
        }

        leaf debug-candidate {
            type empty;
            description "The debug candidate datastore is the config source";
        }

        leaf debug-running {
            type empty;
            description "The debug running datastore is the config source";
        }

    }

    augment /nc:get-config/nc:input {
        leaf format {
            type enumeration {
                enum xml {
                    value 0;
                    description "XML output format";
                }
                enum json {
                    value 1;
                    description "JSON IETF output format";
                }
                enum md-cli {
                    value 2;
                    description "MD-CLI output format";
                }
            }
            description "Output format of data";
        }

    }

    augment /nc:get/nc:input {
        leaf format {
            type enumeration {
                enum xml {
                    value 0;
                    description "XML output format";
                }
                enum json {
                    value 1;
                    description "JSON IETF output format";
                }
                enum md-cli {
                    value 2;
                    description "MD-CLI output format";
                }
            }
            description "Output format of data";
        }

    }

}
