module nokia-attributes {

    yang-version "1.1";

    namespace "urn:nokia.com:sros:ns:yang:sr:attributes";

    prefix "attr";

    import ietf-yang-metadata             { prefix "md"; }
    import nokia-sros-yang-extensions     { prefix "sros-ext"; }
    import nokia-types-sros               { prefix "types-sros"; }

    sros-ext:sros-major-release "rel25";
    organization "Nokia";
    contact
        "Nokia SR OS Support
         Web: <http://www.nokia.com>";
    revision "2025-03-12";

    md:annotation comment {
        type types-sros:comment-text-type;
        description "Annotate a configuration element with a comment";
    } // md:annotation comment

    md:annotation managed {
        type types-sros:model-management;
        description "Which model manages the configuration";
    } // md:annotation managed

}
