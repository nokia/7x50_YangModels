module nokia-sr-openconfig-local-routing-deviations {

    namespace "urn:nokia.com:sros:ns:yang:sr:openconfig-local-routing-deviations";

    prefix "nokia-oc-loc-rt-devs";

    import nokia-sros-yang-extensions     { prefix "sros-ext"; }
    import openconfig-local-routing       { prefix "oc-loc-rt"; }
    import openconfig-network-instance    { prefix "oc-netinst"; }

    sros-ext:sros-major-release "rel25";
    organization "Nokia";
    contact
        "Nokia SR OS Support
         Web: <http://www.nokia.com>";
    description
        "This module contains the list of deviations against the openconfig-local-routing
         module for the Nokia SR OS based routers.

         Copyright 2016 Nokia. All rights reserved. Reproduction of this document
         is authorized on the condition that the foregoing copyright notice is included.

         This nokia-sr-openconfig-local-routing-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-07-16";

    deviation /oc-loc-rt:local-routes {
        deviate not-supported;
    }


    deviation /oc-netinst:network-instances/oc-netinst:network-instance/oc-netinst:protocols/oc-netinst:protocol/oc-netinst:static-routes/oc-netinst:static/oc-netinst:config/oc-netinst:set-tag {
        deviate replace {
            type union {
                type uint32 {
                    range "1..4294967295";
                }
            }
        }
    }

    deviation /oc-netinst:network-instances/oc-netinst:network-instance/oc-netinst:protocols/oc-netinst:protocol/oc-netinst:static-routes/oc-netinst:static/oc-netinst:config/oc-netinst:description {
        deviate not-supported;
    }


    deviation /oc-netinst:network-instances/oc-netinst:network-instance/oc-netinst:protocols/oc-netinst:protocol/oc-netinst:static-routes/oc-netinst:static/oc-netinst:state/oc-netinst:set-tag {
        deviate replace {
            type union {
                type uint32 {
                    range "1..4294967295";
                }
            }
        }
    }

    deviation /oc-netinst:network-instances/oc-netinst:network-instance/oc-netinst:protocols/oc-netinst:protocol/oc-netinst:static-routes/oc-netinst:static/oc-netinst:state/oc-netinst:description {
        deviate not-supported;
    }

    deviation /oc-netinst:network-instances/oc-netinst:network-instance/oc-netinst:protocols/oc-netinst:protocol/oc-netinst:static-routes/oc-netinst:static/oc-netinst:next-hops/oc-netinst:next-hop/oc-netinst:config/oc-netinst:index {
        deviate replace {
            type string {
                length "1..80";
            }
        }
    }

    deviation /oc-netinst:network-instances/oc-netinst:network-instance/oc-netinst:protocols/oc-netinst:protocol/oc-netinst:static-routes/oc-netinst:static/oc-netinst:next-hops/oc-netinst:next-hop/oc-netinst:config/oc-netinst:metric {
        deviate replace {
            type uint32 {
                range "0..65535";
            }
        }
    }

    deviation /oc-netinst:network-instances/oc-netinst:network-instance/oc-netinst:protocols/oc-netinst:protocol/oc-netinst:static-routes/oc-netinst:static/oc-netinst:next-hops/oc-netinst:next-hop/oc-netinst:state/oc-netinst:index {
        deviate replace {
            type string {
                length "1..80";
            }
        }
    }

    deviation /oc-netinst:network-instances/oc-netinst:network-instance/oc-netinst:protocols/oc-netinst:protocol/oc-netinst:static-routes/oc-netinst:static/oc-netinst:next-hops/oc-netinst:next-hop/oc-netinst:state/oc-netinst:metric {
        deviate replace {
            type uint32 {
                range "0..65535";
            }
        }
    }

    deviation /oc-netinst:network-instances/oc-netinst:network-instance/oc-netinst:protocols/oc-netinst:protocol/oc-netinst:static-routes/oc-netinst:static/oc-netinst:next-hops/oc-netinst:next-hop/oc-netinst:interface-ref {
        deviate not-supported;
    }


    deviation /oc-netinst:network-instances/oc-netinst:network-instance/oc-netinst:protocols/oc-netinst:protocol/oc-netinst:local-aggregates/oc-netinst:aggregate/oc-netinst:config/oc-netinst:set-tag {
        deviate not-supported;
    }

    deviation /oc-netinst:network-instances/oc-netinst:network-instance/oc-netinst:protocols/oc-netinst:protocol/oc-netinst:local-aggregates/oc-netinst:aggregate/oc-netinst:config/oc-netinst:description {
        deviate not-supported;
    }

    deviation /oc-netinst:network-instances/oc-netinst:network-instance/oc-netinst:protocols/oc-netinst:protocol/oc-netinst:local-aggregates/oc-netinst:aggregate/oc-netinst:state/oc-netinst:set-tag {
        deviate not-supported;
    }

    deviation /oc-netinst:network-instances/oc-netinst:network-instance/oc-netinst:protocols/oc-netinst:protocol/oc-netinst:local-aggregates/oc-netinst:aggregate/oc-netinst:state/oc-netinst:description {
        deviate not-supported;
    }

}
