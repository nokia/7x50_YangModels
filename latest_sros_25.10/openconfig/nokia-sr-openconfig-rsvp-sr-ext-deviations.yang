module nokia-sr-openconfig-rsvp-sr-ext-deviations {

    namespace "urn:nokia.com:sros:ns:yang:sr:openconfig-rsvp-sr-ext-deviations";

    prefix "nokia-oc-sr-rsvp-ext-devs";

    import nokia-sros-yang-extensions     { prefix "sros-ext"; }
    import openconfig-network-instance    { prefix "oc-ni"; }
    import openconfig-rsvp-sr-ext         { prefix "oc-sr-rsvp-ext"; }

    sros-ext:sros-major-release "rel25";
    organization "Nokia";
    contact
        "Nokia SR OS Support
         Web: <http://www.nokia.com>";
    description
        "This module contains the list of deviations against the openconfig-rsvp-sr-ext
         module for the Nokia SR OS based routers.

         Copyright 2016 Nokia. All rights reserved. Reproduction of this document
         is authorized on the condition that the foregoing copyright notice is included.

         This nokia-sr-openconfig-rsvp-sr-ext-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    deviation /oc-ni:network-instances/oc-ni:network-instance/oc-ni:mpls/oc-ni:te-global-attributes/oc-sr-rsvp-ext:bandwidth-measurement/oc-sr-rsvp-ext:config/oc-sr-rsvp-ext:collection-interval {
        deviate replace {
            type uint32 {
                range "10..600";
            }
        }
        deviate add {
            default "30";
        }
    }

    deviation /oc-ni:network-instances/oc-ni:network-instance/oc-ni:mpls/oc-ni:te-global-attributes/oc-sr-rsvp-ext:bandwidth-measurement/oc-sr-rsvp-ext:config/oc-sr-rsvp-ext:adjustment-interval {
        deviate add {
            default "90";
        }
    }

    deviation /oc-ni:network-instances/oc-ni:network-instance/oc-ni:mpls/oc-ni:te-global-attributes/oc-sr-rsvp-ext:bandwidth-measurement/oc-sr-rsvp-ext:config/oc-sr-rsvp-ext:bandwidth-multiplier {
        deviate replace {
            type decimal64 {
                range "0.0000..10.0000";
                fraction-digits 4;
            }
        }
    }

    deviation /oc-ni:network-instances/oc-ni:network-instance/oc-ni:mpls/oc-ni:te-global-attributes/oc-sr-rsvp-ext:bandwidth-measurement/oc-sr-rsvp-ext:state/oc-sr-rsvp-ext:collection-interval {
        deviate replace {
            type uint32 {
                range "10..600";
            }
        }
        deviate add {
            default "30";
        }
    }

    deviation /oc-ni:network-instances/oc-ni:network-instance/oc-ni:mpls/oc-ni:te-global-attributes/oc-sr-rsvp-ext:bandwidth-measurement/oc-sr-rsvp-ext:state/oc-sr-rsvp-ext:adjustment-interval {
        deviate add {
            default "90";
        }
    }

    deviation /oc-ni:network-instances/oc-ni:network-instance/oc-ni:mpls/oc-ni:te-global-attributes/oc-sr-rsvp-ext:bandwidth-measurement/oc-sr-rsvp-ext:state/oc-sr-rsvp-ext:bandwidth-multiplier {
        deviate replace {
            type decimal64 {
                range "0.0000..10.0000";
                fraction-digits 4;
            }
        }
    }

    deviation /oc-ni:network-instances/oc-ni:network-instance/oc-ni:mpls/oc-ni:te-global-attributes/oc-sr-rsvp-ext:bandwidth-measurement/oc-sr-rsvp-ext:state/oc-sr-rsvp-ext:effective-adjustment-interval {
        deviate not-supported;
    }

    deviation /oc-ni:network-instances/oc-ni:network-instance/oc-ni:mpls/oc-ni:te-global-attributes/oc-sr-rsvp-ext:bandwidth-measurement/oc-sr-rsvp-ext:update-trigger/oc-sr-rsvp-ext:config/oc-sr-rsvp-ext:update-trigger {
        deviate not-supported;
    }

    deviation /oc-ni:network-instances/oc-ni:network-instance/oc-ni:mpls/oc-ni:te-global-attributes/oc-sr-rsvp-ext:bandwidth-measurement/oc-sr-rsvp-ext:update-trigger/oc-sr-rsvp-ext:config/oc-sr-rsvp-ext:sr-traffic-pct {
        deviate not-supported;
    }

    deviation /oc-ni:network-instances/oc-ni:network-instance/oc-ni:mpls/oc-ni:te-global-attributes/oc-sr-rsvp-ext:bandwidth-measurement/oc-sr-rsvp-ext:update-trigger/oc-sr-rsvp-ext:state/oc-sr-rsvp-ext:update-trigger {
        deviate not-supported;
    }

    deviation /oc-ni:network-instances/oc-ni:network-instance/oc-ni:mpls/oc-ni:te-global-attributes/oc-sr-rsvp-ext:bandwidth-measurement/oc-sr-rsvp-ext:update-trigger/oc-sr-rsvp-ext:state/oc-sr-rsvp-ext:sr-traffic-pct {
        deviate not-supported;
    }

    deviation /oc-ni:network-instances/oc-ni:network-instance/oc-ni:mpls/oc-ni:signaling-protocols/oc-ni:rsvp-te/oc-ni:interface-attributes/oc-ni:interface/oc-ni:subscription/oc-ni:state/oc-sr-rsvp-ext:adjusted-absolute-subscription-bw {
        deviate replace {
            units "kilobps";
        }
    }

    deviation /oc-ni:network-instances/oc-ni:network-instance/oc-ni:mpls/oc-ni:te-interface-attributes/oc-ni:interface/oc-sr-rsvp-ext:bandwidth-measurement/oc-sr-rsvp-ext:state/oc-sr-rsvp-ext:last-sample-measured-rsvp-util {
        deviate not-supported;
    }

    deviation /oc-ni:network-instances/oc-ni:network-instance/oc-ni:mpls/oc-ni:te-interface-attributes/oc-ni:interface/oc-sr-rsvp-ext:bandwidth-measurement/oc-sr-rsvp-ext:state/oc-sr-rsvp-ext:last-sample-measured-sr-util {
        deviate replace {
            units "kilobps";
        }
    }

}
