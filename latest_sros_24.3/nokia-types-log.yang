module nokia-types-log {

    yang-version "1.1";

    namespace "urn:nokia.com:sros:ns:yang:sr:types-log";

    prefix "types-log";

    import nokia-sros-yang-extensions     { prefix "sros-ext"; }

    sros-ext:sros-major-release "rel24";
    organization "Nokia";
    contact
        "Nokia SR OS Support
         Web: <http://www.nokia.com>";
    description
        "Common log data types used in the SR OS management system.

         Copyright 2016 Nokia. All rights reserved. Reproduction of this document
         is authorized on the condition that the foregoing copyright notice is included.

         This nokia-types-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-03-20";

    typedef log-policy-id {
        type uint32 {
            range "1..99";
        }
        description "Accounting policy unique identifier.";
    }

    typedef filter-action {
        type enumeration {
            enum drop                           { value 1; }
            enum forward                        { value 2; }
        }
        description
            "Action to take on a packet:
             - drop          (1): packets matching the filter entry are dropped.
             - forward       (2): packets matching the filter entry are forwarded.";
    }

    typedef accounting-record-type {
        type enumeration {
            enum service-ingress-octets         { value 1; }
            enum service-egress-octets          { value 2; }
            enum service-ingress-packets        { value 3; }
            enum service-egress-packets         { value 4; }
            enum network-ingress-octets         { value 5; }
            enum network-egress-octets          { value 6; }
            enum network-ingress-packets        { value 7; }
            enum network-egress-packets         { value 8; }
            enum compact-service-ingress-octets { value 9; }
            enum combined-service-ingress       { value 10; }
            enum combined-network-ing-egr-octets { value 11; }
            enum combined-service-ing-egr-octets { value 12; }
            enum complete-service-ingress-egress { value 13; }
            enum combined-sdp-ingress-egress    { value 14; }
            enum complete-sdp-ingress-egress    { value 15; }
            enum complete-subscriber-ingress-egress { value 16; }
            enum aa-protocol                    { value 17; }
            enum aa-application                 { value 18; }
            enum aa-app-group                   { value 19; }
            enum aa-subscriber-protocol         { value 20; }
            enum aa-subscriber-application      { value 21; }
            enum custom-record-subscriber       { value 23; }
            enum custom-record-service          { value 24; }
            enum custom-record-aa-sub           { value 25; }
            enum queue-group-octets             { value 26; }
            enum queue-group-packets            { value 27; }
            enum combined-queue-group           { value 28; }
            enum combined-mpls-lsp-ingress      { value 29; }
            enum combined-mpls-lsp-egress       { value 30; }
            enum combined-ldp-lsp-egress        { value 31; }
            enum saa                            { value 32; }
            enum video                          { value 33; }
            enum aa-performance                 { value 51; }
            enum complete-ethernet-port         { value 52; }
            enum extended-service-ingress-egress { value 53; }
            enum complete-network-ing-egr       { value 54; }
            enum aa-partition                   { value 55; }
            enum complete-pm                    { value 56; }
            enum aa-admit-deny                  { value 63; }
            enum network-interface-ingress-octets { value 65; }
            enum network-interface-egress-octets { value 66; }
            enum network-interface-ingress-packets { value 67; }
            enum network-interface-egress-packets { value 68; }
            enum combined-network-interface-ingress { value 69; }
            enum combined-network-interface-egress { value 70; }
            enum complete-network-interface-ing-egr { value 71; }
            enum access-egress-octets           { value 72; }
            enum access-egress-packets          { value 73; }
            enum combined-access-egress         { value 74; }
            enum combined-network-egress        { value 75; }
            enum complete-service-activation-test { value 76; }
            enum combined-mpls-srte-egress      { value 77; }
            enum combined-sr-policy-egress      { value 78; }
        }
        description "Accounting policy record type.";
    }

    typedef accounting-port-type {
        type enumeration {
            enum none                           { value 0; }
            enum access                         { value 1; }
            enum network                        { value 2; }
            enum sdp                            { value 3; }
            enum subscriber                     { value 4; }
            enum app-assure                     { value 5; }
            enum qgrp                           { value 6; }
            enum saa                            { value 7; }
            enum mpls-lsp-ingress               { value 8; }
            enum mpls-lsp-egress                { value 9; }
            enum ldp-lsp-egress                 { value 10; }
            enum video                          { value 11; }
            enum mobile-gateway                 { value 12; }
            enum ethernet                       { value 13; }
            enum oam-pm                         { value 14; }
            enum nat                            { value 15; }
            enum nw-intf                        { value 16; }
            enum port-queue                     { value 17; }
            enum svc-activ-test                 { value 18; }
            enum mpls-srte-egress               { value 19; }
            enum sr-policy-egress               { value 20; }
        }
        description "Accounting policy port type.";
    }

    typedef access-network {
        type enumeration {
            enum access                         { value 1; }
            enum network                        { value 2; }
        }
        description "Accounting policy port type";
    }

    typedef measurment-interval-duration {
        type enumeration {
            enum raw                            { value 1; }
            enum 15-mins                        { value 2; }
            enum 1-hour                         { value 3; }
            enum 1-day                          { value 4; }
            enum 5-mins                         { value 5; }
            enum 1-min                          { value 6; }
        }
        description "Acc-policy is associated with oam pm with measurment interval duration type";
    }

    typedef file-log-type {
        type enumeration {
            enum none                           { value 0; }
            enum event-log                      { value 1; }
            enum accounting-policy              { value 2; }
        }
        description "The type of information that will be written to a file.";
    }

    typedef compact-flash-drive {
        type enumeration {
            enum cf-unspecified                 { value 0; }
            enum cf1                            { value 1; }
            enum cf2                            { value 2; }
            enum cf3                            { value 3; }
            enum cf4                            { value 4; }
        }
        description "Compact flash on the primary CPM where the log or billing file should be created.";
    }

    typedef severity-level {
        type enumeration {
            enum cleared                        { value 1; }
            enum indeterminate                  { value 2; }
            enum critical                       { value 3; }
            enum major                          { value 4; }
            enum minor                          { value 5; }
            enum warning                        { value 6; }
        }
        description "Log event severity level to be matched.";
    }

    typedef anysec-events {
        type enumeration {
            enum tmnxAnySecMkaPskRollover       { value 2001; }
            enum tmnxAnySecMkaOperStateChanged  { value 2002; }
            enum tmnxAnySecMkaSessionInitiation { value 2003; }
            enum tmnxAnySecMkaSessionTermination { value 2004; }
            enum tmnxAnySecSessionEnabled       { value 2005; }
            enum tmnxAnySecSessionDisabled      { value 2006; }
            enum tmnxAnySecPeerInconsisRxSciDtctd { value 2007; }
            enum tmnxAnySecPeerInconsisRxSciClrd { value 2008; }
        }
        description "Events for ANYsec module.";
    }

    typedef application {
        type enumeration {
            enum application-assurance          { value 1; }
            enum aps                            { value 2; }
            enum bgp                            { value 4; }
            enum cflowd                         { value 6; }
            enum chassis                        { value 7; }
            enum debug                          { value 10; }
            enum dhcp                           { value 11; }
            enum dhcps                          { value 12; }
            enum diameter                       { value 13; }
            enum dot1x                          { value 14; }
            enum efm-oam                        { value 15; }
            enum elmi                           { value 16; }
            enum ering                          { value 17; }
            enum eth-cfm                        { value 18; }
            enum etun                           { value 19; }
            enum filter                         { value 20; }
            enum gsmp                           { value 21; }
            enum igmp                           { value 23; }
            enum igmp-snooping                  { value 24; }
            enum ip                             { value 25; }
            enum ipsec                          { value 26; }
            enum isis                           { value 28; }
            enum l2tp                           { value 29; }
            enum lag                            { value 30; }
            enum ldp                            { value 31; }
            enum li                             { value 32; }
            enum lldp                           { value 33; }
            enum logger                         { value 34; }
            enum mcpath                         { value 36; }
            enum mc-redundancy                  { value 37; }
            enum mirror                         { value 38; }
            enum mld                            { value 39; }
            enum mld-snooping                   { value 40; }
            enum mpls                           { value 41; }
            enum msdp                           { value 43; }
            enum nat                            { value 44; }
            enum ntp                            { value 45; }
            enum oam                            { value 46; }
            enum ospf                           { value 47; }
            enum pim                            { value 48; }
            enum pim-snooping                   { value 49; }
            enum port                           { value 50; }
            enum pppoe                          { value 52; }
            enum ptp                            { value 53; }
            enum rip                            { value 55; }
            enum route-policy                   { value 56; }
            enum rsvp                           { value 57; }
            enum security                       { value 58; }
            enum snmp                           { value 59; }
            enum stp                            { value 60; }
            enum svcmgr                         { value 63; }
            enum system                         { value 64; }
            enum user                           { value 67; }
            enum video                          { value 69; }
            enum vrrp                           { value 70; }
            enum vrtr                           { value 71; }
            enum radius                         { value 73; }
            enum wpp                            { value 74; }
            enum wlan-gw                        { value 75; }
            enum dynsvc                         { value 77; }
            enum mpls-tp                        { value 78; }
            enum bfd                            { value 79; }
            enum python                         { value 80; }
            enum ripng                          { value 81; }
            enum openflow                       { value 82; }
            enum sflow                          { value 84; }
            enum rpki                           { value 85; }
            enum pcep                           { value 90; }
            enum calltrace                      { value 91; }
            enum satellite                      { value 93; }
            enum ldap                           { value 94; }
            enum pppoe-clnt                     { value 95; }
            enum tls                            { value 96; }
            enum adp                            { value 102; }
            enum mgmt-core                      { value 103; }
            enum macsec                         { value 105; }
            enum sr-policy                      { value 106; }
            enum pcap                           { value 107; }
            enum auto-prov                      { value 115; }
            enum bier                           { value 116; }
            enum pfcp                           { value 118; }
            enum tree-sid                       { value 121; }
            enum srv6                           { value 124; }
            enum sr-mpls                        { value 125; }
            enum anysec                         { value 127; }
        }
        description
            "Software entity that reports the log. This typedef should only be
             used by configuration model.";
    }

    typedef application-state {
        type enumeration {
            enum application-assurance          { value 1; }
            enum aps                            { value 2; }
            enum bgp                            { value 4; }
            enum cflowd                         { value 6; }
            enum chassis                        { value 7; }
            enum debug                          { value 10; }
            enum dhcp                           { value 11; }
            enum dhcps                          { value 12; }
            enum diameter                       { value 13; }
            enum dot1x                          { value 14; }
            enum efm-oam                        { value 15; }
            enum elmi                           { value 16; }
            enum ering                          { value 17; }
            enum eth-cfm                        { value 18; }
            enum etun                           { value 19; }
            enum filter                         { value 20; }
            enum gsmp                           { value 21; }
            enum igmp                           { value 23; }
            enum igmp-snooping                  { value 24; }
            enum ip                             { value 25; }
            enum ipsec                          { value 26; }
            enum isis                           { value 28; }
            enum l2tp                           { value 29; }
            enum lag                            { value 30; }
            enum ldp                            { value 31; }
            enum li                             { value 32; }
            enum lldp                           { value 33; }
            enum logger                         { value 34; }
            enum mcpath                         { value 36; }
            enum mc-redundancy                  { value 37; }
            enum mirror                         { value 38; }
            enum mld                            { value 39; }
            enum mld-snooping                   { value 40; }
            enum mpls                           { value 41; }
            enum msdp                           { value 43; }
            enum nat                            { value 44; }
            enum ntp                            { value 45; }
            enum oam                            { value 46; }
            enum ospf                           { value 47; }
            enum pim                            { value 48; }
            enum pim-snooping                   { value 49; }
            enum port                           { value 50; }
            enum pppoe                          { value 52; }
            enum ptp                            { value 53; }
            enum rip                            { value 55; }
            enum route-policy                   { value 56; }
            enum rsvp                           { value 57; }
            enum security                       { value 58; }
            enum snmp                           { value 59; }
            enum stp                            { value 60; }
            enum svcmgr                         { value 63; }
            enum system                         { value 64; }
            enum user                           { value 67; }
            enum video                          { value 69; }
            enum vrrp                           { value 70; }
            enum vrtr                           { value 71; }
            enum radius                         { value 73; }
            enum wpp                            { value 74; }
            enum wlan-gw                        { value 75; }
            enum dynsvc                         { value 77; }
            enum mpls-tp                        { value 78; }
            enum bfd                            { value 79; }
            enum python                         { value 80; }
            enum ripng                          { value 81; }
            enum openflow                       { value 82; }
            enum sflow                          { value 84; }
            enum rpki                           { value 85; }
            enum pcep                           { value 90; }
            enum calltrace                      { value 91; }
            enum satellite                      { value 93; }
            enum ldap                           { value 94; }
            enum pppoe-clnt                     { value 95; }
            enum tls                            { value 96; }
            enum adp                            { value 102; }
            enum mgmt-core                      { value 103; }
            enum macsec                         { value 105; }
            enum sr-policy                      { value 106; }
            enum pcap                           { value 107; }
            enum auto-prov                      { value 115; }
            enum bier                           { value 116; }
            enum pfcp                           { value 118; }
            enum tree-sid                       { value 121; }
            enum srv6                           { value 124; }
            enum sr-mpls                        { value 125; }
            enum anysec                         { value 127; }
        }
        description
            "Software entity that reports the log. This typedef should only be
             used by state model.";
    }

    typedef application-obsolete {
        status obsolete;
        type enumeration {
            enum application-assurance          { value 1; }
            enum aps                            { value 2; }
            enum bgp                            { value 4; }
            enum cflowd                         { value 6; }
            enum chassis                        { value 7; }
            enum debug                          { value 10; }
            enum dhcp                           { value 11; }
            enum dhcps                          { value 12; }
            enum diameter                       { value 13; }
            enum dot1x                          { value 14; }
            enum efm-oam                        { value 15; }
            enum elmi                           { value 16; }
            enum ering                          { value 17; }
            enum eth-cfm                        { value 18; }
            enum etun                           { value 19; }
            enum filter                         { value 20; }
            enum gsmp                           { value 21; }
            enum igmp                           { value 23; }
            enum igmp-snooping                  { value 24; }
            enum ip                             { value 25; }
            enum ipsec                          { value 26; }
            enum isis                           { value 28; }
            enum l2tp                           { value 29; }
            enum lag                            { value 30; }
            enum ldp                            { value 31; }
            enum li                             { value 32; }
            enum lldp                           { value 33; }
            enum logger                         { value 34; }
            enum mcpath                         { value 36; }
            enum mc-redundancy                  { value 37; }
            enum mirror                         { value 38; }
            enum mld                            { value 39; }
            enum mld-snooping                   { value 40; }
            enum mpls                           { value 41; }
            enum msdp                           { value 43; }
            enum nat                            { value 44; }
            enum ntp                            { value 45; }
            enum oam                            { value 46; }
            enum ospf                           { value 47; }
            enum pim                            { value 48; }
            enum pim-snooping                   { value 49; }
            enum port                           { value 50; }
            enum pppoe                          { value 52; }
            enum ptp                            { value 53; }
            enum rip                            { value 55; }
            enum route-policy                   { value 56; }
            enum rsvp                           { value 57; }
            enum security                       { value 58; }
            enum snmp                           { value 59; }
            enum stp                            { value 60; }
            enum svcmgr                         { value 63; }
            enum system                         { value 64; }
            enum user                           { value 67; }
            enum video                          { value 69; }
            enum vrrp                           { value 70; }
            enum vrtr                           { value 71; }
            enum radius                         { value 73; }
            enum wpp                            { value 74; }
            enum wlan-gw                        { value 75; }
            enum dynsvc                         { value 77; }
            enum mpls-tp                        { value 78; }
            enum bfd                            { value 79; }
            enum python                         { value 80; }
            enum ripng                          { value 81; }
            enum openflow                       { value 82; }
            enum sflow                          { value 84; }
            enum rpki                           { value 85; }
            enum calltrace                      { value 91; }
            enum satellite                      { value 93; }
            enum ldap                           { value 94; }
            enum pppoe-clnt                     { value 95; }
            enum tls                            { value 96; }
            enum adp                            { value 102; }
            enum mgmt-core                      { value 103; }
            enum macsec                         { value 105; }
            enum pcap                           { value 107; }
            enum auto-prov                      { value 115; }
            enum bier                           { value 116; }
            enum tree-sid                       { value 121; }
            enum atm                            { status obsolete; }
            enum igh                            { status obsolete; }
            enum ppp                            { status obsolete; }
            enum gmpls                          { status obsolete; }
            enum lmp                            { status obsolete; }
            enum mobile-gateway                 { status obsolete; }
            enum mobile-pdn                     { status obsolete; }
            enum mobile-pdn-cups                { status obsolete; }
            enum mobile-profile                 { status obsolete; }
            enum mobile-profile-cups            { status obsolete; }
            enum mobile-serving                 { status obsolete; }
        }
        description
            "Software entity that reports the log. This typedef has been
             obsoleted.";
    }

    typedef application-assurance-events {
        type enumeration {
            enum tmnxBsxIsaAaGrpFailureV2       { value 4401; }
            enum tmnxBsxIsaAaGrpFailureClearV2  { value 4402; }
            enum tmnxBsxIsaAaGrpNonRedundantV2  { value 4403; }
            enum tmnxBsxIsaAaGrpSwitchover      { value 4404; }
            enum tmnxBsxIsaAaGrpFlowFull        { value 4405; }
            enum tmnxBsxIsaAaGrpFlowFullClear   { value 4407; }
            enum tmnxBsxIsaAaSubLoadBalance     { value 4408; }
            enum tmnxBsxIsaAaGrpCapCostThres    { value 4409; }
            enum tmnxBsxIsaAaGrpCapCostThresClear { value 4410; }
            enum tmnxBsxAaSubscribersUnassigned { value 4411; }
            enum tmnxBsxAaSubscriberAcctDataLoss { value 4412; }
            enum tmnxBsxAaSubPolResExceeded     { value 4413; }
            enum tmnxBsxAaSubPolResExceededClear { value 4414; }
            enum tmnxBsxIsaAaGrpFlowSetup       { value 4415; }
            enum tmnxBsxIsaAaGrpFlowSetupClear  { value 4416; }
            enum tmnxBsxIsaAaGrpPacketRate      { value 4417; }
            enum tmnxBsxIsaAaGrpPacketRateClear { value 4418; }
            enum tmnxBsxIsaAaGrpBitRate         { value 4419; }
            enum tmnxBsxIsaAaGrpBitRateClear    { value 4420; }
            enum tmnxBsxTransIpPolAaSubCreated  { value 4421; }
            enum tmnxBsxTransIpPolAaSubDeleted  { value 4422; }
            enum tmnxBsxTransIpPolRadCoAAudit   { value 4423; }
            enum tmnxBsxTransIpPolRadCoAError   { value 4424; }
            enum tmnxBsxTransIpPolRadDiscError  { value 4425; }
            enum tmnxBsxTransIpPolDhcpAddWarning { value 4426; }
            enum tmnxBsxTransIpPolDhcpDelWarning { value 4427; }
            enum tmnxBsxIsaAaGrpFmSbWaSBufOvld  { value 4428; }
            enum tmnxBsxIsaAaGrpFmSbWaSBufOvldClr { value 4429; }
            enum tmnxBsxIsaAaGrpToSbWaSBufOvld  { value 4430; }
            enum tmnxBsxIsaAaGrpToSbWaSBufOvldClr { value 4431; }
            enum tmnxBsxIsaAaGrpOvrldCutthru    { value 4432; }
            enum tmnxBsxIsaAaGrpOvrldCutthruClr { value 4433; }
            enum tmnxBsxTransitIpPersistenceWarn { value 4434; }
            enum tmnxBsxAarpInstOperStateChanged { value 4435; }
            enum tmnxBsxAarpInstStateChanged    { value 4436; }
            enum tmnxBsxRadApFailure            { value 4437; }
            enum tmnxBsxRadApServOperStateChange { value 4438; }
            enum tmnxBsxMobileSubModifyFailure  { value 4439; }
            enum tmnxBsxRadApIntrmUpdateSkipped { value 4440; }
            enum tmnxBsxHttpUrlParamLimitExceeded { value 4441; }
            enum tmnxBsxUrlFilterOperStateChange { value 4442; }
            enum tmnxBsxSubModifyFailure        { value 4443; }
            enum tmnxBsxDnsIpCacheFull          { value 4444; }
            enum tmnxBsxDnsIpCacheFullClear     { value 4445; }
            enum tmnxBsxUrlListUpdate           { value 4446; }
            enum tmnxBsxUrlListFailure          { value 4447; }
            enum tmnxBsxIsaAaTimFileProcFailure { value 4448; }
            enum tmnxBsxStatTcaThreshCrossed    { value 4449; }
            enum tmnxBsxStatTcaThreshCrossedClear { value 4450; }
            enum tmnxBsxStatPolcrTcaThreshCrossed { value 4451; }
            enum tmnxBsxStatPolcrTcaThreshCrClear { value 4452; }
            enum tmnxBsxStatFtrTcaThreshCrossed { value 4453; }
            enum tmnxBsxStatFtrTcaThreshCrClear { value 4454; }
            enum tmnxBsxStatFtrEnTcaThreshCrossed { value 4455; }
            enum tmnxBsxStatFtrEnTcaThreshCrClear { value 4456; }
            enum tmnxBsxTransIpPolDiamGxError   { value 4457; }
            enum tmnxBsxDatapathCpuUsage        { value 4458; }
            enum tmnxBsxDatapathCpuUsageClear   { value 4459; }
            enum tmnxBsxTcpValTcaCrossed        { value 4460; }
            enum tmnxBsxTcpValTcaCrossedClear   { value 4461; }
            enum tmnxBsxCertProfileOperStateChngd { value 4462; }
            enum tmnxBsxSubQuarantined          { value 4463; }
            enum tmnxBsxSubQuarantinedClear     { value 4464; }
            enum tmnxBsxUrlFltrWebServOprStateChg { value 4465; }
        }
        description "Events for application-assurance module.";
    }

    typedef calltrace-events {
        type enumeration {
            enum tmnxCallTraceMaxFilesNumReached { value 2001; }
            enum tmnxCallTraceLocSizeLimitReached { value 2002; }
            enum calltraceDebugEvent            { value 2003; }
        }
        description "Events for calltrace module.";
    }

    typedef aps-events {
        type enumeration {
            enum apsEventSwitchover             { value 2001; }
            enum apsEventModeMismatch           { value 2002; }
            enum apsEventChannelMismatch        { value 2003; }
            enum apsEventPSBF                   { value 2004; }
            enum apsEventFEPLF                  { value 2005; }
            enum tApsModeMismatchClear          { value 2006; }
            enum tApsChannelMismatchClear       { value 2007; }
            enum tApsPSBFClear                  { value 2008; }
            enum tApsFEPLFClear                 { value 2009; }
            enum tApsLocalSwitchCommandSet      { value 2010; }
            enum tApsLocalSwitchCommandClear    { value 2011; }
            enum tApsRemoteSwitchCommandSet     { value 2012; }
            enum tApsRemoteSwitchCommandClear   { value 2013; }
            enum tApsMcApsCtlLinkStateChange    { value 2014; }
            enum tApsChanTxLaisStateChange      { value 2015; }
            enum tApsPrimaryChannelChange       { value 2016; }
        }
        description "Events for aps module.";
    }

    typedef bgp-events {
        type enumeration {
            enum sendNotification               { value 2005; }
            enum receiveNotification            { value 2006; }
            enum bgpInterfaceDown               { value 2007; }
            enum bgpConnNoKA                    { value 2008; }
            enum bgpConnNoOpenRcvd              { value 2009; }
            enum bgpRejectConnBadLocAddr        { value 2010; }
            enum bgpRemoteEndClosedConn         { value 2011; }
            enum bgpPeerNotFound                { value 2012; }
            enum bgpConnMgrTerminated           { value 2013; }
            enum bgpTerminated                  { value 2014; }
            enum bgpNoMemoryPeer                { value 2015; }
            enum bgpVariableRangeViolation      { value 2016; }
            enum bgpCfgViol                     { value 2017; }
            enum tBgpPeerGRStatusChange         { value 2018; }
            enum tBgpNgEstablished              { value 2019; }
            enum tBgpNgBackwardTransition       { value 2020; }
            enum tBgpPeerNgHoldTimeInconsistent { value 2021; }
            enum tBgpFlowspecUnsupportdComAction { value 2022; }
            enum tBgp4RouteInvalid              { value 2027; }
            enum tBgp4PathAttrInvalid           { value 2028; }
            enum tBgp4WithdrawnRtFromUpdateError { value 2029; }
            enum tBgp4UpdateInvalid             { value 2030; }
            enum tBgpGeneral                    { value 2031; }
            enum tBgpFibResourceFailPeer        { value 2032; }
            enum tBgpReceivedInvalidNlri        { value 2033; }
            enum tBgpMaxNgPfxLmt                { value 2034; }
            enum tBgpMaxNgPfxLmtThresholdReached { value 2035; }
            enum tBgpInstanceDynamicPeerLmtReachd { value 2036; }
            enum tBgpPGDynamicPeerLmtReached    { value 2037; }
            enum bgpEstablishedNotification     { value 2038; }
            enum bgpBackwardTransNotification   { value 2039; }
            enum tBgp4PathAttrDiscarded         { value 2040; }
            enum tmnxBmpSessionStatusChange     { value 2041; }
            enum tBgpInstConvStateTransition    { value 2042; }
            enum tBgpPeerNgGRStatusChange       { value 2043; }
            enum tBgpPGDynNbrIfMaxSessLmtReachd { value 2044; }
        }
        description "Events for atm module.";
    }

    typedef bier-events {
        type enumeration {
            enum vRtrBierBfrIdCollision         { value 2001; }
            enum vRtrBierMtMismatch             { value 2002; }
            enum vRtrBierSubDomainMismatch      { value 2003; }
            enum vRtrBierUnsupportedNhop        { value 2004; }
        }
        description "Events for bier module.";
    }

    typedef cflowd-events {
        type enumeration {
            enum tmnxCflowdCreateFailure        { value 2002; }
            enum tmnxCflowdStateChange          { value 2004; }
            enum tmnxCflowdFlowCreateFailure    { value 2006; }
            enum tmnxCflowdPacketTxFailure      { value 2009; }
        }
        description "Events for cflowd module.";
    }

    typedef chassis-events {
        type enumeration {
            enum tmnxEqCardFailure              { value 2001; }
            enum tmnxEqCardInserted             { value 2002; }
            enum tmnxEqCardRemoved              { value 2003; }
            enum tmnxEqWrongCard                { value 2004; }
            enum tmnxEnvTempTooHigh             { value 2005; }
            enum tmnxEqPowerSupplyInserted      { value 2010; }
            enum tmnxEqPowerSupplyRemoved       { value 2011; }
            enum tmnxRedPrimaryCPMFail          { value 2012; }
            enum tmnxChassisNotificationClear   { value 2016; }
            enum tmnxEqSyncIfTimingHoldover     { value 2017; }
            enum tmnxEqSyncIfTimingHoldoverClear { value 2018; }
            enum tmnxEqSyncIfTimingRef1Alarm    { value 2019; }
            enum tmnxEqSyncIfTimingRef1AlarmClear { value 2020; }
            enum tmnxEqSyncIfTimingRef2Alarm    { value 2021; }
            enum tmnxEqSyncIfTimingRef2AlarmClear { value 2022; }
            enum tmnxEqFlashDataLoss            { value 2023; }
            enum tmnxEqFlashDiskFull            { value 2024; }
            enum tmnxPeSoftwareVersionMismatch  { value 2025; }
            enum tmnxPeSoftwareLoadFailed       { value 2026; }
            enum tmnxPeBootloaderVersionMismatch { value 2027; }
            enum tmnxPeBootromVersionMismatch   { value 2028; }
            enum tmnxPeFPGAVersionMismatch      { value 2029; }
            enum tmnxEqSyncIfTimingBITSAlarm    { value 2030; }
            enum tmnxEqSyncIfTimingBITSAlarmClear { value 2031; }
            enum tmnxEqCardFirmwareUpgraded     { value 2032; }
            enum tmnxChassisUpgradeInProgress   { value 2033; }
            enum tmnxChassisUpgradeComplete     { value 2034; }
            enum tmnxChassisHiBwMcastAlarm      { value 2052; }
            enum tmnxEqOperStateChange          { value 2055; }
            enum tmnxEqMdaCfgNotCompatible      { value 2056; }
            enum tmnxCpmCardSyncFileNotPresent  { value 2057; }
            enum tmnxEqMdaXplError              { value 2058; }
            enum tmnxEqCardPChipError           { value 2059; }
            enum tmnxEqCardSoftResetAlarm       { value 2060; }
            enum tmnxEqMdaSyncENotCompatible    { value 2061; }
            enum tmnxIPsecIsaGrpActiveIsaChgd   { value 2062; }
            enum tmnxEqCardPChipMemoryEvent     { value 2063; }
            enum tmnxIPsecIsaGrpUnableToSwitch  { value 2064; }
            enum tmnxIPsecIsaGrpTnlLowWMark     { value 2065; }
            enum tmnxIPsecIsaGrpTnlHighWMark    { value 2066; }
            enum tmnxIPsecIsaGrpTnlMax          { value 2067; }
            enum tmnxEqSyncIfTimingRef1Quality  { value 2068; }
            enum tmnxEqSyncIfTimingRef2Quality  { value 2069; }
            enum tmnxEqSyncIfTimingBITSQuality  { value 2070; }
            enum tmnxEqSyncIfTimingBITS2Quality { value 2071; }
            enum tmnxEqSyncIfTimingRefSwitch    { value 2072; }
            enum tmnxEqSyncIfTimingBITS2Alarm   { value 2073; }
            enum tmnxEqSyncIfTimingBITS2AlarmClr { value 2074; }
            enum tmnxEqSyncIfTimingBITSOutRefChg { value 2075; }
            enum tmnxEqCardPChipCamEvent        { value 2076; }
            enum tmnxEqSyncIfTimingSystemQuality { value 2077; }
            enum tmnxEqHwEnhancedCapability     { value 2078; }
            enum tmnxEqSyncIfTimingPTPQuality   { value 2079; }
            enum tmnxEqSyncIfTimingPTPAlarm     { value 2080; }
            enum tmnxEqSyncIfTimingPTPAlarmClr  { value 2081; }
            enum tmnxPeFirmwareVersionWarning   { value 2082; }
            enum tmnxMDAIsaTunnelGroupChange    { value 2083; }
            enum tmnxEqPowerCapacityExceeded    { value 2092; }
            enum tmnxEqPowerCapacityExceededClear { value 2093; }
            enum tmnxEqPowerLostCapacity        { value 2094; }
            enum tmnxEqPowerLostCapacityClear   { value 2095; }
            enum tmnxEqPowerOverloadState       { value 2096; }
            enum tmnxEqPowerOverloadStateClear  { value 2097; }
            enum tmnxEqCardQChipBufMemoryEvent  { value 2098; }
            enum tmnxEqCardQChipStatsMemoryEvent { value 2099; }
            enum tmnxEqCardQChipIntMemoryEvent  { value 2101; }
            enum tmnxEqCardChipIfDownEvent      { value 2102; }
            enum tmnxEqCardChipIfCellEvent      { value 2103; }
            enum tmnxEqLowSwitchFabricCap       { value 2104; }
            enum tmnxEqLowSwitchFabricCapClear  { value 2105; }
            enum tmnxEqPowerSafetyAlertThreshold { value 2106; }
            enum tmnxEqPowerSafetyAlertClear    { value 2107; }
            enum tmnxEqPowerSafetyLevelThreshold { value 2108; }
            enum tmnxEqPowerSafetyLevelClear    { value 2109; }
            enum tmnxEqCardTChipParityEvent     { value 2110; }
            enum tmnxEqProvPowerCapacityAlm     { value 2115; }
            enum tmnxEqProvPowerCapacityAlmClr  { value 2116; }
            enum tmnxPlcyAcctStatsPoolExcResource { value 2117; }
            enum tmnxPlcyAcctStatsPoolLowResource { value 2118; }
            enum tmnxPlcyAcctStatsEventOvrflwClr { value 2119; }
            enum tmnxPlcyAcctStatsEventOvrflw   { value 2120; }
            enum tmnxIomResHighLimitReached     { value 2121; }
            enum tmnxIomResExhausted            { value 2122; }
            enum tmnxIomResStateClr             { value 2123; }
            enum tmnxIomEventOverflow           { value 2124; }
            enum tmnxIomEventOverflowClr        { value 2125; }
            enum tmnxEqDataPathFailureProtImpact { value 2126; }
            enum tmnxExtStandbyCpmReboot        { value 2127; }
            enum tmnxExtStandbyCpmRebootFail    { value 2128; }
            enum tmnxEqMdaIngrXplError          { value 2129; }
            enum tmnxSyncIfTimBITS2048khzUnsup  { value 2134; }
            enum tmnxSyncIfTimBITS2048khzUnsupClr { value 2135; }
            enum tmnxEqMgmtEthRedStandbyRaise   { value 2136; }
            enum tmnxEqMgmtEthRedStandbyClear   { value 2137; }
            enum tmnxEqPhysChassPowerSupOvrTmp  { value 2138; }
            enum tmnxEqPhysChassPowerSupOvrTmpClr { value 2139; }
            enum tmnxEqPhysChassPowerSupAcFail  { value 2140; }
            enum tmnxEqPhysChassPowerSupAcFailClr { value 2141; }
            enum tmnxEqPhysChassPowerSupDcFail  { value 2142; }
            enum tmnxEqPhysChassPowerSupDcFailClr { value 2143; }
            enum tmnxEqPhysChassPowerSupInFail  { value 2144; }
            enum tmnxEqPhysChassPowerSupInFailClr { value 2145; }
            enum tmnxEqPhysChassPowerSupOutFail { value 2146; }
            enum tmnxEqPhysChassPowerSupOutFailCl { value 2147; }
            enum tmnxEqPhysChassisFanFailure    { value 2148; }
            enum tmnxEqPhysChassisFanFailureClear { value 2149; }
            enum tIPsecIsaMemLowWatermark       { value 2150; }
            enum tIPsecIsaMemHighWatermark      { value 2151; }
            enum tIPsecIsaMemMax                { value 2152; }
            enum tmnxCpmMemSizeMismatch         { value 2153; }
            enum tmnxCpmMemSizeMismatchClear    { value 2154; }
            enum tmnxPhysChassPwrSupWrgFanDir   { value 2155; }
            enum tmnxPhysChassPwrSupWrgFanDirClr { value 2156; }
            enum tmnxPhysChassPwrSupPemACRect   { value 2157; }
            enum tmnxPhysChassPwrSupPemACRectClr { value 2158; }
            enum tmnxPhysChassPwrSupInputFeed   { value 2159; }
            enum tmnxPhysChassPwrSupInputFeedClr { value 2160; }
            enum tmnxEqBpEpromFail              { value 2161; }
            enum tmnxEqBpEpromFailClear         { value 2162; }
            enum tmnxEqBpEpromWarning           { value 2163; }
            enum tmnxEqBpEpromWarningClear      { value 2164; }
            enum tmnxPhysChassisPCMInputFeed    { value 2165; }
            enum tmnxPhysChassisPCMInputFeedClr { value 2166; }
            enum tmnxIPMacQosIngOverload        { value 2167; }
            enum tmnxIPMacQosIngOverloadClear   { value 2168; }
            enum tmnxIPQosEgrOverload           { value 2169; }
            enum tmnxIPQosEgrOverloadClear      { value 2170; }
            enum tmnxIPv6QosIngOverload         { value 2171; }
            enum tmnxIPv6QosIngOverloadClear    { value 2172; }
            enum tmnxIPv6QosEgrOverload         { value 2173; }
            enum tmnxIPv6QosEgrOverloadClear    { value 2174; }
            enum tmnxIPMacFilterIngOverload     { value 2175; }
            enum tmnxIPMacFilterIngOverloadClear { value 2176; }
            enum tmnxIPMacFilterEgrOverload     { value 2177; }
            enum tmnxIPMacFilterEgrOverloadClear { value 2178; }
            enum tmnxIPv6FilterIngOverload      { value 2179; }
            enum tmnxIPv6FilterIngOverloadClear { value 2180; }
            enum tmnxIPv6FilterEgrOverload      { value 2181; }
            enum tmnxIPv6FilterEgrOverloadClear { value 2182; }
            enum tmnxIPMacCpmFilterOverload     { value 2183; }
            enum tmnxIPMacCpmFilterOverloadClear { value 2184; }
            enum tmnxIPv6CpmFilterOverload      { value 2185; }
            enum tmnxIPv6CpmFilterOverloadClear { value 2186; }
            enum tmnxBluetoothModuleConnectionChg { value 2187; }
            enum tmnxGnssAcquiringFix           { value 2188; }
            enum tmnxGnssAcquiredFix            { value 2189; }
            enum tmnxPhysChassisPMOutFail       { value 2190; }
            enum tmnxPhysChassisPMOutFailClr    { value 2191; }
            enum tmnxPhysChassisPMInputFeed     { value 2192; }
            enum tmnxPhysChassisPMInputFeedClr  { value 2193; }
            enum tmnxPhysChassisFilterDoorOpen  { value 2194; }
            enum tmnxPhysChassisFilterDoorClosed { value 2195; }
            enum tmnxPhysChassisPMOverTemp      { value 2196; }
            enum tmnxPhysChassisPMOverTempClr   { value 2197; }
            enum tmnxEqFpgaSoftError            { value 2200; }
            enum tmnxEqSyncIfTimingSyncEQuality { value 2201; }
            enum tmnxEqSyncIfTimingSyncE2Quality { value 2202; }
            enum tmnxEqSyncIfTimingSyncEAlarm   { value 2203; }
            enum tmnxEqSyncIfTimingSyncEAlarmClr { value 2204; }
            enum tmnxEqSyncIfTimingSyncE2Alarm  { value 2205; }
            enum tmnxEqSyncIfTimingSyncE2AlarmClr { value 2206; }
            enum tmnxEqHwEventDetected          { value 2207; }
            enum tmnxTunnelGrpEsaVmActivity     { value 2208; }
            enum tmnxEsaDiscovered              { value 2209; }
            enum tmnxEsaConnected               { value 2210; }
            enum tmnxEsaDisconnected            { value 2211; }
            enum tmnxEsaFailure                 { value 2212; }
            enum tmnxEsaCleared                 { value 2213; }
            enum tmnxEsaVmCreated               { value 2214; }
            enum tmnxEsaVmBooted                { value 2215; }
            enum tmnxEsaVmRemoved               { value 2216; }
            enum tmnxEsaVmCleared               { value 2217; }
            enum tmnxEsaVmFailure               { value 2218; }
            enum tIPsecEsaVmMemLowWatermark     { value 2219; }
            enum tIPsecEsaVmMemHighWatermark    { value 2220; }
            enum tmnxPeKernelVersionMismatch    { value 2221; }
            enum tmnxFPResourcePolicyModified   { value 2222; }
            enum tmnxFPResourcePolicyModifiedClr { value 2223; }
            enum tmnxEqSyncIfTimingGnssQuality  { value 2224; }
            enum tmnxEqSyncIfTimingGnss2Quality { value 2225; }
            enum tmnxEqSyncIfTimingGnssAlarm    { value 2226; }
            enum tmnxEqSyncIfTimingGnss2Alarm   { value 2227; }
            enum tmnxEqSyncIfTimingGnssAlarmClr { value 2228; }
            enum tmnxEqSyncIfTimingGnss2AlarmClr { value 2229; }
            enum tmnxEsaFirmwareUpgradeStarted  { value 2230; }
            enum tmnxPlcyAcctPlcrPoolExcResource { value 2231; }
            enum tmnxPlcyAcctPlcrPoolLowResource { value 2232; }
            enum tChassisAirflowDirMismatch     { value 2233; }
            enum tChassisAirflowDirMismatchClr  { value 2234; }
            enum tChassisPowerSupplyMismatch    { value 2235; }
            enum tChassisPowerSupplyMismatchClr { value 2236; }
            enum tChassisPowerSupplyUnsup       { value 2237; }
            enum tmnxHwAggShpSchedEventOvrflwClr { value 2242; }
            enum tmnxHwAggShpSchedEventOvrflw   { value 2243; }
            enum tmnxFPResOversubscribed        { value 2246; }
            enum tmnxFPResOversubscribedCleared { value 2247; }
            enum tmnxIPMacFilterIngNearFull     { value 2275; }
            enum tmnxIPMacFilterIngNearFullClear { value 2276; }
            enum tmnxIPMacFilterEgrNearFull     { value 2277; }
            enum tmnxIPMacFilterEgrNearFullClear { value 2278; }
            enum tmnxIPv6FilterIngNearFull      { value 2279; }
            enum tmnxIPv6FilterIngNearFullClear { value 2280; }
            enum tmnxIPv6FilterEgrNearFull      { value 2281; }
            enum tmnxIPv6FilterEgrNearFullClear { value 2282; }
            enum tmnxEsaStolenTimeDetected      { value 2399; }
            enum tmnxEsaHwStatusDegraded        { value 2400; }
            enum tmnxEsaHwStatusDegradedClr     { value 2401; }
            enum tmnxEsaHwStatusCritical        { value 2402; }
            enum tmnxEsaHwStatusCriticalClr     { value 2403; }
            enum tmnxEsaHwPwrSup1Degraded       { value 2404; }
            enum tmnxEsaHwPwrSup1DegradedClr    { value 2405; }
            enum tmnxEsaHwPwrSup1Failed         { value 2406; }
            enum tmnxEsaHwPwrSup1FailedClr      { value 2407; }
            enum tmnxEsaHwPwrSup2Degraded       { value 2408; }
            enum tmnxEsaHwPwrSup2DegradedClr    { value 2409; }
            enum tmnxEsaHwPwrSup2Failed         { value 2410; }
            enum tmnxEsaHwPwrSup2FailedClr      { value 2411; }
            enum tmnxEsaHwFanBankNonRedun       { value 2412; }
            enum tmnxEsaHwFanBankNonRedunClr    { value 2413; }
            enum tmnxEsaHwFanBankFailRedun      { value 2414; }
            enum tmnxEsaHwFanBankFailRedunClr   { value 2415; }
            enum tmnxEsaHwFanStatusDegraded     { value 2416; }
            enum tmnxEsaHwFanStatusDegradedClr  { value 2417; }
            enum tmnxEsaHwFanStatusFailed       { value 2418; }
            enum tmnxEsaHwFanStatusFailedClr    { value 2419; }
            enum tmnxEsaHwPwrSupMismatch        { value 2420; }
            enum tmnxEsaHwPwrSupMismatchClr     { value 2421; }
            enum tmnxEsaHwPwrSupBankNonRedun    { value 2422; }
            enum tmnxEsaHwPwrSupBankNonRedunClr { value 2423; }
            enum tmnxEsaHwPwrSupBankFailRedun   { value 2424; }
            enum tmnxEsaHwPwrSupBankFailRedunClr { value 2425; }
            enum tmnxEsaHwTemperatureDegraded   { value 2426; }
            enum tmnxEsaHwTemperatureDegradedClr { value 2427; }
            enum tmnxEsaHwTemperatureFailed     { value 2428; }
            enum tmnxEsaHwTemperatureFailedClr  { value 2429; }
            enum tmnxPowerSupplyFanFailed       { value 2430; }
            enum tmnxPowerSupplyFanFailedClear  { value 2431; }
            enum tmnxIxrResourceHighUsage       { value 2432; }
            enum tmnxIxrResourceExhausted       { value 2433; }
            enum tmnxIxrResourceRecovered       { value 2434; }
            enum tmnxIxrResourceHighUsageByOwner { value 2435; }
            enum tmnxIxrResourceExhaustedByOwner { value 2436; }
            enum tmnxIxrResourceRecoveredByOwner { value 2437; }
            enum tmnxSasAlarminput1StateChanged { value 3001; }
            enum tmnxSasAlarminput2StateChanged { value 3002; }
            enum tmnxSasAlarminput3StateChanged { value 3003; }
            enum tmnxSasAlarminput4StateChanged { value 3004; }
            enum tmnxAlarmInputVoltageFailure   { value 3014; }
            enum tmnxIomRsrcUsageHighLimitReached { value 3252; }
            enum tmnxIomRsrcUsageExhausted      { value 3253; }
            enum tmnxIomRsrcUsageRecovered      { value 3254; }
            enum tmnxIomRsrcEventOverflow       { value 3257; }
            enum tmnxIomRsrcEventOverflowClr    { value 3258; }
            enum tmnxIomRsrcOwnerOversubscribed { value 3259; }
            enum tmnxIomRsrcOwnerOversubscrbdClr { value 3260; }
            enum tmnxInterChassisCommsDown      { value 4001; }
            enum tmnxInterChassisCommsUp        { value 4002; }
            enum tmnxCpmIcPortDown              { value 4003; }
            enum tmnxCpmIcPortUp                { value 4004; }
            enum tmnxCpmIcPortSFFInserted       { value 4005; }
            enum tmnxCpmIcPortSFFRemoved        { value 4006; }
            enum tmnxCpmANoLocalIcPort          { value 4007; }
            enum tmnxCpmBNoLocalIcPort          { value 4008; }
            enum tmnxCpmALocalIcPortAvail       { value 4009; }
            enum tmnxCpmBLocalIcPortAvail       { value 4010; }
            enum CpmIcPortSFFStatusFailure      { value 4011; }
            enum CpmIcPortSFFStatusDDMCorrupt   { value 4012; }
            enum CpmIcPortSFFStatusReadError    { value 4013; }
            enum CpmIcPortSFFStatusUnsupported  { value 4014; }
            enum tmnxCpmIcPortDDMFailure        { value 4015; }
            enum tmnxCpmIcPortDDMClear          { value 4016; }
            enum tmnxSfmIcPortDown              { value 4017; }
            enum tmnxSfmIcPortUp                { value 4018; }
            enum tmnxSfmIcPortSFFInserted       { value 4019; }
            enum tmnxSfmIcPortSFFRemoved        { value 4020; }
            enum SfmIcPortSFFStatusFailure      { value 4021; }
            enum SfmIcPortSFFStatusDDMCorrupt   { value 4022; }
            enum SfmIcPortSFFStatusReadError    { value 4023; }
            enum SfmIcPortSFFStatusUnsupported  { value 4024; }
            enum tmnxSfmIcPortDDMFailure        { value 4025; }
            enum tmnxSfmIcPortDDMClear          { value 4026; }
            enum tmnxSfmIcPortDegraded          { value 4027; }
            enum tmnxSfmIcPortDegradedClear     { value 4028; }
            enum tmnxCardResMacFdbHighUsgSet    { value 5163; }
            enum tmnxCardResMacFdbHighUsgClr    { value 5164; }
            enum tmnxPowerShelfInputPwrModeSwitch { value 6001; }
            enum tmnxPowerShelfCommsDown        { value 6002; }
            enum tmnxPowerShelfCommsUp          { value 6003; }
            enum tmnxPowerShelfOutputStatusSwitch { value 6004; }
            enum tmnxPowerShelfOutputStatusDown { value 6005; }
            enum tmnxPowerShelfOutputStatusUp   { value 6006; }
            enum tmnxEqCardMissing              { value 6007; }
            enum tmnxEqCardMissingClear         { value 6008; }
            enum tmnxIomRsrcUserOversubscribed  { status obsolete; }
            enum tmnxIomRsrcUserOversubscribedClr { status obsolete; }
        }
        description "Events for chassis module.";
    }

    typedef auto-prov-events {
        type enumeration {
            enum autoNodeProv                   { value 2001; }
        }
        description "Events for auto-node-provisioning module.";
    }

    typedef debug-events {
        type enumeration {
            enum traceEvent                     { value 2001; }
        }
        description "Events for debug module.";
    }

    typedef dhcps-events {
        type enumeration {
            enum tmnxDhcpSvrSubnetMinFreeExc    { value 2001; }
            enum tmnxDhcpSvrHostConflict        { value 2002; }
            enum tmnxDhcpSvrPoolUnknown         { value 2003; }
            enum tmnxDhcpSvrLeaseNotOwner       { value 2004; }
            enum tmnxDhcpSvrDeclineStaticAddr   { value 2005; }
            enum tmnxDhcpSvrMsgTooLong          { value 2006; }
            enum tmnxDhcpsFoStateChange         { value 2007; }
            enum tmnxDhcpsFoLeaseUpdateFailed   { value 2008; }
            enum tmnxDhcpSvrUserDbUnknown       { value 2009; }
            enum tmnxDhcpSvrMaxLeasesReached    { value 2010; }
            enum tmnxDhcpSvrNoSubnetFixAddr     { value 2011; }
            enum tmnxDhcpSvrLeaseDefaultTimers  { value 2012; }
            enum tmnxDhcpSvrPoolMinFreeExc      { value 2013; }
            enum tmnxDhcpSvrSubnetDepleted      { value 2014; }
            enum tmnxDhcpSvrPoolDepleted        { value 2015; }
            enum tmnxDhcpSvrIntLseConflict      { value 2016; }
            enum tmnxDhcpSvrLeaseModify         { value 2017; }
            enum tmnxDhcpSvrLeaseCreate         { value 2018; }
            enum tmnxDhcpSvrLeaseDelete         { value 2019; }
            enum tmnxLudbDhcpGroupIfTooLong     { value 2020; }
            enum tmnxLudbPppoeGroupIfTooLong    { value 2021; }
            enum tmnxDhcpSvrNoContFreeBlocks    { value 2022; }
            enum tmnxDhcpsPoolFoStateChange     { value 2024; }
            enum tmnxDhcpsPoolFoLeaseUpdateFailed { value 2025; }
            enum tmnxDhcpSvrPlThTooLowV6        { value 2030; }
            enum tmnxDhcpSvrPlThDepletedV6      { value 2031; }
            enum tmnxDhcpSvrPfxThTooLowV6       { value 2032; }
            enum tmnxDhcpSvrPfxThDepletedV6     { value 2033; }
            enum tmnxDhcpsLeaseOfferedExpired   { value 2034; }
            enum tmnxDhcpsAddrAllocationFailure { value 2035; }
            enum tmnxDhcpsPacketDropped         { value 2036; }
        }
        description "Events for dhcps module.";
    }

    typedef diameter-events {
        type enumeration {
            enum tmnxDiamPolicyPeerStateChange  { value 2001; }
            enum tmnxDiamAppSessionFailure      { value 2003; }
            enum tmnxDiamSessionEvent           { value 2004; }
            enum tmnxDiamPpPrxMcLocStateChanged { value 2005; }
            enum tmnxDiamMessageDropped         { value 2007; }
            enum tmnxDiamNdPeerStatActiveChanged { value 2008; }
        }
        description "Events for diameter module.";
    }

    typedef efm-oam-events {
        type enumeration {
            enum tmnxDot3OamPeerChanged         { value 2001; }
            enum tmnxDot3OamLoopDetected        { value 2002; }
            enum tmnxDot3OamLoopCleared         { value 2003; }
            enum dot3OamThresholdEvent          { value 2004; }
            enum dot3OamNonThresholdEvent       { value 2005; }
            enum tmnxDot3OamSdThresholdEvent    { value 2006; }
            enum tmnxDot3OamThresholdEventClr   { value 2007; }
            enum tmnxDot3OamNonThresholdEventClr { value 2008; }
        }
        description "Events for efm-oam module.";
    }

    typedef elmi-events {
        type enumeration {
            enum tmnxElmiIfStatusChangeEvent    { value 2001; }
            enum tmnxElmiEVCStatusChangeEvent   { value 2002; }
        }
        description "Events for elmi module.";
    }

    typedef ethring-events {
        type enumeration {
            enum tmnxEthRingPathFwdStateChange  { value 2001; }
            enum tmnxEthRingApsPrvsnRaiseAlarm  { value 2002; }
            enum tmnxEthRingApsPrvsnClearAlarm  { value 2003; }
        }
        description "Events for ethring module.";
    }

    typedef ethcfm-events {
        type enumeration {
            enum dot1agCfmFaultAlarm            { value 2001; }
            enum tmnxDot1agCfmMepLbmTestComplete { value 2002; }
            enum tmnxDot1agCfmMepLtmTestComplete { value 2003; }
            enum tmnxDot1agCfmMepEthTestComplete { value 2004; }
            enum tmnxDot1agCfmMepDMTestComplete { value 2005; }
            enum tmnxDot1agCfmMepAisStateChanged { value 2006; }
            enum tmnxDot1agCfmMipEvaluation     { value 2007; }
            enum tmnxDot1agCfmMepSLMTestComplete { value 2008; }
            enum tmnxDot1agCfmMepCsfStateChanged { value 2009; }
            enum tmnxDot1agCfmMepFcltyFaultRaise { value 2010; }
            enum tmnxDot1agCfmMepFcltyFaultClear { value 2011; }
        }
        description "Events for ethcfm module.";
    }

    typedef etun-events {
        type enumeration {
            enum tmnxEthTunnelApsCfgRaiseAlarm  { value 2001; }
            enum tmnxEthTunnelApsCfgClearAlarm  { value 2002; }
            enum tmnxEthTunnelApsPrvsnRaiseAlarm { value 2003; }
            enum tmnxEthTunnelApsPrvsnClearAlarm { value 2004; }
            enum tmnxEthTunnelApsNoRspRaiseAlarm { value 2005; }
            enum tmnxEthTunnelApsNoRspClearAlarm { value 2006; }
            enum tmnxEthTunnelApsSwitchoverAlarm { value 2007; }
        }
        description "Events for etun module.";
    }

    typedef filter-events {
        type enumeration {
            enum tIPFilterPBRPacketsDrop        { value 2001; }
            enum tFilterSubInsSpaceAlarmRaised  { value 2004; }
            enum tFilterSubInsSpaceAlarmCleared { value 2005; }
            enum tFilterSubInsFltrEntryDropped  { value 2006; }
            enum tFilterBgpFlowSpecProblem      { value 2007; }
            enum tFilterApplyPathProblem        { value 2008; }
            enum tFilterRadSharedFltrAlarmRaised { value 2009; }
            enum tFilterRadSharedFltrAlarmClear { value 2010; }
            enum tFilterEmbeddingOperStateChange { value 2011; }
            enum tFilterEmbedOpenflowOperStateChg { value 2012; }
            enum tFilterOpenflowRequestRejected { value 2013; }
            enum tFilterEmbedFlowspecOperStateChg { value 2015; }
            enum tFilterRPActiveDestChangeEvent { value 2017; }
            enum tFilterEmbedVsdOperStateChg    { status obsolete; }
        }
        description "Events for filter module.";
    }

    typedef gsmp-events {
        type enumeration {
            enum tmnxAncpIngRateMonitorEvent    { value 2001; }
            enum tmnxAncpIngRateMonitorEventL   { value 2002; }
            enum tmnxAncpEgrRateMonitorEvent    { value 2003; }
            enum tmnxAncpEgrRateMonitorEventL   { value 2004; }
            enum tmnxAncpShcvDisabledEvent      { value 2005; }
            enum tmnxAncpShcvDisabledEventL     { value 2006; }
            enum tmnxAncpSesRejected            { value 2007; }
            enum tmnxAncpStringRejected         { value 2008; }
        }
        description "Events for gsmp module.";
    }

    typedef igmp-events {
        type enumeration {
            enum vRtrIgmpIfRxQueryVerMismatch   { value 2001; }
            enum vRtrIgmpIfCModeRxQueryMismatch { value 2002; }
            enum vRtrIgmpMaxGrpsLimitExceeded   { value 2003; }
            enum vRtrIgmpMcacPlcyDropped        { value 2004; }
            enum vRtrIgmpHostInstantiationFail  { value 2005; }
            enum vRtrIgmpHostMaxGrpsLimitExceeded { value 2006; }
            enum vRtrIgmpHostMcacPlcyDropped    { value 2007; }
            enum vRtrIgmpHostCModeRxQueryMismatch { value 2008; }
            enum vRtrIgmpHostRxQueryVerMismatch { value 2009; }
            enum vRtrIgmpHostMaxSrcsLimitExceeded { value 2010; }
            enum vRtrIgmpMaxSrcsLimitExceeded   { value 2011; }
            enum vRtrIgmpGrpIfSapMaxGrpsLimExceed { value 2012; }
            enum vRtrIgmpGrpIfSapMaxSrcsLimExceed { value 2013; }
            enum vRtrIgmpGrpIfSapMcacPlcyDropped { value 2014; }
            enum vRtrIgmpGrpIfSapCModeRxQueryMism { value 2015; }
            enum vRtrIgmpGrpIfSapRxQueryVerMism { value 2016; }
            enum vRtrIgmpHostMaxGrpSrcsLimitExcd { value 2017; }
            enum vRtrIgmpMaxGrpSrcsLimitExceeded { value 2018; }
            enum vRtrIgmpGrpIfSapMaxGrpSrcLimExcd { value 2019; }
            enum vRtrIgmpHostQryIntervalConflict { value 2020; }
            enum vRtrIgmpNotifyNumOfIPsecIfLowWm { value 2021; }
            enum vRtrIgmpNotifyNumOfIPsecIfHighWm { value 2022; }
            enum vRtrIgmpNotifyNumOfIPsecIfMaxRch { value 2023; }
            enum vRtrIgmpSlaProfInstMcacPlcyDrop { value 2024; }
        }
        description "Events for igmp module.";
    }

    typedef igmp-snooping-events {
        type enumeration {
            enum sapIgmpSnpgGrpLimitExceeded    { value 2001; }
            enum sapIgmpSnpgMcacPlcyDropped     { value 2002; }
            enum sdpBndIgmpSnpgGrpLimitExceeded { value 2003; }
            enum sdpBndIgmpSnpgMcacPlcyDropped  { value 2004; }
            enum sapIgmpSnpgMcsFailure          { value 2005; }
            enum sapIgmpSnpgSrcLimitExceeded    { value 2006; }
            enum sdpBndIgmpSnpgSrcLimitExceeded { value 2007; }
            enum sdpBndIgmpSnpgGrpSrcLimitExceed { value 2008; }
            enum sapIgmpSnpgGrpSrcLimitExceeded { value 2009; }
            enum eMplsIgmpSnpgMfibFailure       { value 2010; }
        }
        description "Events for igmp-snooping module.";
    }

    typedef ip-events {
        type enumeration {
            enum clearRTMError                  { value 2001; }
            enum ipEtherBroadcast               { value 2002; }
            enum ipDuplicateAddress             { value 2003; }
            enum ipArpInfoOverwritten           { value 2004; }
            enum fibAddFailed                   { value 2005; }
            enum qosNetworkPolicyMallocFailed   { value 2006; }
            enum ipArpBadInterface              { value 2007; }
            enum ipArpDuplicateIpAddress        { value 2008; }
            enum ipArpDuplicateMacAddress       { value 2009; }
            enum ipAnyDuplicateAddress          { value 2010; }
            enum labelIndexAllocFailed          { value 2011; }
        }
        description "Events for debug module.";
    }

    typedef ipsec-events {
        type enumeration {
            enum tIPsecRUTnlFailToCreate        { value 2001; }
            enum tIPsecRUSAFailToAddRoute       { value 2002; }
            enum tIPsecBfdIntfSessStateChgd     { value 2003; }
            enum tIPsecRadAcctPlcyFailure       { value 2004; }
            enum tIPSecTrustAnchorPrfOprChg     { value 2005; }
            enum tIPsecTunnelEncapIpMtuTooSmall { value 2006; }
            enum tIPsecRuTnlEncapIpMtuTooSmall  { value 2007; }
            enum tmnxSecNotifCmptedCertHashChngd { value 2008; }
            enum tmnxSecNotifCmptedCertChnChngd { value 2009; }
            enum tmnxSecNotifSendChnNotInCmptChn { value 2010; }
            enum tmnxIPsecTunnelOperStateChange { value 2011; }
            enum tmnxIPsecGWOperStateChange     { value 2012; }
            enum tIPsecRUTnlRemoved             { value 2013; }
            enum tIPsecTunnelProtocolFailed     { value 2014; }
        }
        description "Events for IPSEC module.";
    }

    typedef isis-events {
        type enumeration {
            enum vRtrIsisSpbNbrMultAdjExists    { value 2025; }
            enum vRtrIsisSpbNbrMultAdjExistsClear { value 2026; }
            enum vRtrSpbEctFidCfgChg            { value 2027; }
            enum tmnxIsisDatabaseOverload       { value 2029; }
            enum tmnxIsisManualAddressDrops     { value 2030; }
            enum tmnxIsisCorruptedLSPDetected   { value 2031; }
            enum tmnxIsisMaxSeqExceedAttempt    { value 2032; }
            enum tmnxIsisIDLenMismatch          { value 2033; }
            enum tmnxIsisMaxAreaAddrsMismatch   { value 2034; }
            enum tmnxIsisOwnLSPPurge            { value 2035; }
            enum tmnxIsisSequenceNumberSkip     { value 2036; }
            enum tmnxIsisAutTypeFail            { value 2037; }
            enum tmnxIsisAuthFail               { value 2038; }
            enum tmnxIsisVersionSkew            { value 2039; }
            enum tmnxIsisAreaMismatch           { value 2040; }
            enum tmnxIsisRejectedAdjacency      { value 2041; }
            enum tmnxIsisLSPTooLargeToPropagate { value 2042; }
            enum tmnxIsisOrigLSPBufSizeMismatch { value 2043; }
            enum tmnxIsisProtoSuppMismatch      { value 2044; }
            enum tmnxIsisAdjacencyChange        { value 2045; }
            enum tmnxIsisCircIdExhausted        { value 2046; }
            enum tmnxIsisAdjRestartStatusChange { value 2047; }
            enum tmnxIsisLdpSyncTimerStarted    { value 2048; }
            enum tmnxIsisLdpSyncExit            { value 2049; }
            enum tmnxIsisExportLimitReached     { value 2050; }
            enum tmnxIsisExportLimitWarning     { value 2051; }
            enum tmnxIsisRoutesExpLmtDropped    { value 2052; }
            enum tmnxIsisFailureDisabled        { value 2056; }
            enum tmnxIsisSidError               { value 2057; }
            enum tmnxIsisSidNotInLabelRange     { value 2058; }
            enum tmnxIsisRejectedAdjacencySid   { value 2059; }
            enum tmnxIsisLSPPurge               { value 2060; }
            enum tmnxIsisPfxLimitOverloadWarning { value 2061; }
            enum tmnxIsisAdjBfdSessionSetupFail { value 2062; }
            enum tmnxIsisSrgbBadLabelRange      { value 2063; }
            enum tmnxIsisCircMtuTooLow          { value 2064; }
            enum tmnxIsisRejectedAdjacencySet   { value 2065; }
            enum tmnxIsisCorruptRemainingLifetime { value 2066; }
            enum tmnxIsisSidStatsIndexAlloc     { value 2067; }
            enum tmnxIsisFaOperParticipationDown { value 2068; }
            enum tmnxIsisRejectedEndXSid        { value 2069; }
            enum tmnxIsisRejectedPgId           { value 2070; }
            enum tmnxIsisSrv6LocError           { value 2071; }
            enum tmnxIsisSrv6StaticSidIfTypeError { value 2072; }
        }
        description "Events for debug module.";
    }

    typedef l2tp-events {
        type enumeration {
            enum tmnxL2tpPeerUnreachable        { value 2001; }
            enum tmnxL2tpIsaMdaVRtrStateChange  { value 2002; }
            enum tmnxL2tpLnsSePppSessionFailure { value 2003; }
            enum tmnxL2tpVappVRtrStateChange    { value 2004; }
            enum tmnxL2tpTunnelBlacklisted      { value 2006; }
            enum tmnxL2tpTunnelSelBlacklistFull { value 2007; }
            enum tmnxL2tpLnsPppNcpFailure       { value 2010; }
            enum tmnxL2tpApFailure              { value 2011; }
        }
        description "Events for l2tp module.";
    }

    typedef lag-events {
        type enumeration {
            enum DynamicCostOn                  { value 2001; }
            enum DynamicCostOff                 { value 2002; }
            enum LagPortAddFailed               { value 2003; }
            enum LagSubGroupSelected            { value 2004; }
            enum LagPortAddFailureCleared       { value 2005; }
            enum LagStateEvent                  { value 2006; }
            enum tLagMemberStateEvent           { value 2007; }
            enum tmnxLagBfdMemStateChanged      { value 2008; }
            enum tLagAdaptiveLoadbalancingChanged { value 2009; }
        }
        description "Events for debug module.";
    }

    typedef ldp-events {
        type enumeration {
            enum vRtrLdpStateChange             { value 2001; }
            enum vRtrLdpGroupIdMismatch         { value 2004; }
            enum vRtrLdpNgIpv4InstStateChange   { value 2011; }
            enum vRtrLdpNgIpv6InstStateChange   { value 2012; }
            enum vRtrLdpNgIfStateChange         { value 2013; }
            enum vRtrLdpNgInetIfStateChange     { value 2014; }
            enum vRtrLdpNgTargPeerStateChange   { value 2015; }
            enum vRtrLdpNgSessionStateChange    { value 2016; }
            enum vRtrLdpNgSessMaxFecThresChanged { value 2017; }
            enum vRtrLdpNgSessMaxFecLimitReached { value 2018; }
            enum vRtrLdpNgResourceExhaustion    { value 2019; }
            enum vRtrLdpNgAddrFecCommMismatch   { value 2021; }
        }
        description "Events for debug module.";
    }

    typedef li-events {
        type enumeration {
            enum sbiBootLiConfig                { value 2001; }
            enum sourceEnabled                  { value 2011; }
            enum sourceDisabled                 { value 2012; }
            enum destinationEnabled             { value 2013; }
            enum destinationDisabled            { value 2014; }
            enum sourceSapChange                { value 2018; }
            enum sourceSubscriberChange         { value 2019; }
            enum tMirrorSourceIPFltrChangeReject { value 2020; }
            enum tMirrorSourceMacFltrChangeReject { value 2021; }
            enum tMirrorSourceFilterAssignReject { value 2022; }
            enum tMirrorDestinationChangeReject { value 2023; }
            enum tMirrorSourceFilterOverruled   { value 2026; }
            enum tMirrorSourceFilterAssignWarn  { value 2027; }
            enum tMirrorFilterAssignToSapWarn   { value 2028; }
            enum tMirrorFilterAssignToSdpWarn   { value 2029; }
            enum tMirrorFilterAssignToItfWarn   { value 2030; }
            enum tMirrorSourceLiFilterChanged   { value 2031; }
            enum tMirrorSourceLiSubProblem      { value 2032; }
            enum tMirrorSourceIPv6FltrChangeRej { value 2033; }
            enum tMirrorLiNatLsnSubOperStateCh  { value 2034; }
            enum tMirrorLiNatL2awSubOperStateCh { value 2035; }
            enum tMirrorLiNat64SubOperStateCh   { value 2036; }
            enum tMirrorLiX2Alarm               { value 2037; }
            enum tFltrLiRsvdBlockRangeChangeEvent { value 2038; }
            enum tMirrorLiSrcPortLicInvalid     { value 2039; }
            enum tMirrorLiXIfLicenseInvalid     { value 2040; }
            enum tMirrorLiUpSubFailed           { value 2041; }
            enum tMirrorLiUpSubSuccess          { value 2042; }
            enum tMirrorLiUpIeInvalid           { value 2043; }
            enum cli_user_login                 { value 2101; }
            enum cli_user_logout                { value 2102; }
            enum cli_user_login_failed          { value 2103; }
            enum cli_user_login_max_attempts    { value 2104; }
            enum ftp_user_login                 { value 2105; }
            enum ftp_user_logout                { value 2106; }
            enum ftp_user_login_failed          { value 2107; }
            enum ftp_user_login_max_attempts    { value 2108; }
            enum ssh_user_login                 { value 2109; }
            enum ssh_user_logout                { value 2110; }
            enum ssh_user_login_failed          { value 2111; }
            enum ssh_user_login_max_attempts    { value 2112; }
            enum cli_user_io                    { value 2113; }
            enum snmp_user_set                  { value 2114; }
            enum cli_config_io                  { value 2115; }
            enum cli_unauth_user_io             { value 2116; }
            enum cli_unauth_config_io           { value 2117; }
            enum grpc_user_login                { value 2118; }
            enum grpc_user_logout               { value 2119; }
            enum grpc_user_login_failed         { value 2120; }
            enum grpc_user_login_max_attempts   { value 2121; }
            enum host_snmp_attempts             { value 2123; }
            enum radiusFailed                   { value 2124; }
            enum netconf_user_login             { value 2125; }
            enum netconf_user_logout            { value 2126; }
            enum netconf_user_login_failed      { value 2127; }
            enum netconf_user_login_max_attempts { value 2128; }
            enum mdSaveCommitHistoryFailed      { value 2129; }
            enum sbiBootMdReadCommitHistoryFailed { value 2130; }
            enum mdCommitSucceeded              { value 2131; }
            enum ssiSaveConfigSucceeded         { value 2202; }
            enum ssiSaveConfigFailed            { value 2203; }
            enum tmnxConfigModify               { value 2206; }
            enum tmnxConfigCreate               { value 2207; }
            enum tmnxConfigDelete               { value 2208; }
            enum tmnxStateChange                { value 2209; }
            enum mdLiConfigChange               { value 2210; }
            enum ssiSyncConfigOK                { value 2212; }
            enum ssiSyncConfigFailed            { value 2213; }
            enum md_cli_io                      { value 2223; }
            enum md_cli_unauth_io               { value 2224; }
            enum tmnxClear                      { value 2300; }
            enum netconf_auth                   { value 2401; }
            enum netconf_unauth                 { value 2402; }
            enum grpc_auth                      { value 2403; }
            enum grpc_unauth                    { value 2404; }
        }
        description "Events for li module.";
    }

    typedef lldp-events {
        type enumeration {
            enum lldpRemTablesChange            { value 2001; }
            enum tmnxLldpRemEntryPeerAdded      { value 2101; }
            enum tmnxLldpRemEntryPeerUpdated    { value 2102; }
            enum tmnxLldpRemEntryPeerRemoved    { value 2103; }
            enum tmnxLldpRemManAddrEntryAdded   { value 2104; }
            enum tmnxLldpRemManAddrEntryRemoved { value 2105; }
        }
        description "Events for lldp module.";
    }

    typedef logger-events {
        type enumeration {
            enum STARTED                        { value 2001; }
            enum tmnxLogTraceError              { value 2002; }
            enum tmnxLogSpaceContention         { value 2005; }
            enum tmnxLogAdminLocFailed          { value 2006; }
            enum tmnxLogBackupLocFailed         { value 2007; }
            enum tmnxLogFileRollover            { value 2008; }
            enum tmnxLogFileDeleted             { value 2009; }
            enum tmnxClear                      { value 2010; }
            enum tmnxTestEvent                  { value 2011; }
            enum tmnxLogEventThrottled          { value 2012; }
            enum tmnxSysLogTargetProblem        { value 2013; }
            enum tmnxLogAccountingDataLoss      { value 2014; }
            enum tmnxStdEventsReplayed          { value 2015; }
            enum tmnxLogOnlyEventThrottled      { value 2016; }
            enum tmnxLogEventOverrun            { value 2017; }
            enum tmnxLogOnlyEventOverrun        { value 2018; }
            enum started                        { status obsolete; }
        }
        description "Events for logger module.";
    }

    typedef macsec-events {
        type enumeration {
            enum tmnxMacsecConfiguredPortCA     { value 2001; }
            enum tmnxMacsecUnconfiguredPortCA   { value 2002; }
            enum tmnxMacsecEnabledPort          { value 2003; }
            enum tmnxMacsecDisabledPort         { value 2004; }
            enum tmnxMacsecMaxPeerLimitExceeded { value 2005; }
            enum tmnxMkaSessionEstablished      { value 2006; }
            enum tmnxMkaPskRollover             { value 2007; }
            enum tmnxMkaSessionEnded            { value 2008; }
            enum tmnxMkaOperStateChanged        { value 2009; }
            enum tmnxMacsecMaxPeerLimitCleared  { value 2010; }
            enum tmnxMacsecCaCreate             { value 2011; }
            enum tmnxMacsecSakCreate            { value 2012; }
            enum tmnxMacsecSakInstalledRx       { value 2013; }
            enum tmnxMacsecSakInstalledTx       { value 2014; }
            enum tmnxMacsecMkaReplayAttemptDisc { value 2015; }
            enum tmnxMacsecDpReplayAttempt      { value 2016; }
            enum tmnxMacsecSakDelete            { value 2017; }
        }
        description "Events for macsec module.";
    }

    typedef mcpath-events {
        type enumeration {
            enum tmnxMcPathSrcGrpBlackHole      { value 2005; }
            enum tmnxMcPathSrcGrpBlackHoleCleared { value 2006; }
            enum tmnxMcPathAvailBwLimitExceeded { value 2007; }
            enum tmnxMcPathAvailBwLimitCleared  { value 2008; }
            enum tmnxMcPathSrcGrpBlkHole        { status obsolete; }
            enum tmnxMcPathSrcGrpBlkHoleClear   { status obsolete; }
            enum tmnxMcPathAvailBwLimitReached  { status obsolete; }
            enum tmnxMcPathAvailBwValWithinRange { status obsolete; }
        }
        description "Events for mcpath module.";
    }

    typedef mc-redundancy-events {
        type enumeration {
            enum tmnxMcRedundancyPeerStateChanged { value 2001; }
            enum tmnxMcRedundancyMismatchDetected { value 2002; }
            enum tmnxMcRedundancyMismatchResolved { value 2003; }
            enum tmnxMcPeerSyncStatusChanged    { value 2004; }
            enum tmnxMcSyncClientAlarmRaised    { value 2005; }
            enum tmnxMcSyncClientAlarmCleared   { value 2006; }
            enum tmnxSrrpSubnetMismatch         { value 2007; }
            enum tmnxSrrpSubnetMismatchCleared  { value 2008; }
            enum tmnxSrrpInstanceIdMismatch     { value 2009; }
            enum tmnxSrrpSapMismatch            { value 2010; }
            enum tmnxSrrpSapTagMismatch         { value 2011; }
            enum tmnxSrrpRedIfMismatch          { value 2012; }
            enum tmnxSrrpDualMaster             { value 2013; }
            enum tmnxMcLagInfoLagChanged        { value 2014; }
            enum tmnxSrrpSystemIpNotSet         { value 2015; }
            enum tmnxMcRingOperStateChanged     { value 2016; }
            enum tmnxMcRingInbCtrlOperStateChgd { value 2017; }
            enum tmnxMcRingNodeLocOperStateChgd { value 2018; }
            enum tmnxMcSyncClockSkewRaised      { value 2019; }
            enum tmnxMcSyncClockSkewCleared     { value 2020; }
            enum tmnxSrrpDuplicateSubIfAddress  { value 2021; }
            enum tmnxMcPeerRingsOperStateChanged { value 2022; }
            enum tmnxSrrpTrapNewMaster          { value 2023; }
            enum tmnxSrrpBecameBackup           { value 2024; }
            enum srrpPacketDiscarded            { value 2025; }
            enum tmnxSrrpBfdIntfSessStateChgd   { value 2026; }
            enum tmnxMcPeerEPBfdSessionOpen     { value 2027; }
            enum tmnxMcPeerEPBfdSessionClose    { value 2028; }
            enum tmnxMcPeerEPBfdSessionUp       { value 2029; }
            enum tmnxMcPeerEPBfdSessionDown     { value 2030; }
            enum tmnxMcPeerEPOperDown           { value 2031; }
            enum tmnxMcPeerEPOperUp             { value 2032; }
            enum tmnxMCEPSessionPsvModeEnabled  { value 2033; }
            enum tmnxMCEPSessionPsvModeDisabled { value 2034; }
            enum tMcPeerIPsecTnlGrpMasterStateChg { value 2035; }
            enum tMcPeerIPsecTnlGrpProtStatusChg { value 2036; }
            enum tmnxMcOmcrStatFailedChanged    { value 2037; }
            enum tmnxMcOmcrClientNumEntriesHigh { value 2038; }
            enum tmnxSrrpOperDownInvalidMac     { value 2043; }
            enum tmnxSrrpOperDownInvalidMacClear { value 2044; }
            enum tmnxSrrpPrivRetailMismatch     { value 2045; }
            enum tMcIPsecDomainActivityStateChg { value 2046; }
            enum tMcIpsecDomainProtStatusChg    { value 2047; }
        }
        description "Events for mc-redundancy module.";
    }

    typedef mirror-events {
        type enumeration {
            enum sourceEnabled                  { value 2001; }
            enum sourceDisabled                 { value 2002; }
            enum destinationEnabled             { value 2003; }
            enum destinationDisabled            { value 2004; }
            enum sourceIpFilterChange           { value 2006; }
            enum sourceMacFilterChange          { value 2007; }
            enum sourceSapChange                { value 2008; }
            enum sourceSubscriberChange         { value 2009; }
            enum tMirrorSourceIpv6FilterChange  { value 2022; }
        }
        description "Events for mirror module.";
    }

    typedef mld-events {
        type enumeration {
            enum vRtrMldIfRxQueryVerMismatch    { value 2001; }
            enum vRtrMldIfCModeRxQueryMismatch  { value 2002; }
            enum vRtrMldMaxGrpsLimitExceeded    { value 2003; }
            enum vRtrMldMcacPlcyDropped         { value 2004; }
            enum vRtrMldHostInstantiationFail   { value 2005; }
            enum vRtrMldHostMaxGrpsLimitExceeded { value 2006; }
            enum vRtrMldHostMcacPlcyDropped     { value 2007; }
            enum vRtrMldHostCModeRxQueryMismatch { value 2008; }
            enum vRtrMldHostRxQueryVerMismatch  { value 2009; }
            enum vRtrMldHostMaxSrcsLimitExceeded { value 2010; }
            enum vRtrMldMaxSrcsLimitExceeded    { value 2011; }
            enum vRtrMldGrpIfSapMaxGrpsLimExceed { value 2012; }
            enum vRtrMldGrpIfSapMaxSrcsLimExceed { value 2013; }
            enum vRtrMldGrpIfSapMcacPlcyDropped { value 2014; }
            enum vRtrMldGrpIfSapCModeRxQueryMism { value 2015; }
            enum vRtrMldGrpIfSapRxQueryVerMism  { value 2016; }
            enum vRtrMldHostMaxGrpSrcsLimitExcd { value 2017; }
            enum vRtrMldMaxGrpSrcsLimitExceeded { value 2018; }
            enum vRtrMldGrpIfSapMaxGrpSrcLimExcd { value 2019; }
            enum vRtrMldHostQryIntervalConflict { value 2020; }
            enum vRtrMldSlaProfInstMcacPlcyDrop { value 2021; }
        }
        description "Events for mld module.";
    }

    typedef mld-snooping-events {
        type enumeration {
            enum sapMldSnpgGrpLimitExceeded     { value 2001; }
            enum sdpBndMldSnpgGrpLimitExceeded  { value 2002; }
            enum sapMldSnpgMcsFailure           { value 2003; }
        }
        description "Events for mld-snooping module.";
    }

    typedef mpls-events {
        type enumeration {
            enum mplsXCUp                       { value 2001; }
            enum mplsXCDown                     { value 2002; }
            enum mplsTunnelUp                   { value 2003; }
            enum mplsTunnelDown                 { value 2004; }
            enum mplsTunnelRerouted             { value 2005; }
            enum mplsTunnelReoptimized          { value 2006; }
            enum vRtrMplsStateChange            { value 2007; }
            enum vRtrMplsIfStateChange          { value 2008; }
            enum vRtrMplsLspUp                  { value 2009; }
            enum vRtrMplsLspDown                { value 2010; }
            enum vRtrMplsLspPathUp              { value 2011; }
            enum vRtrMplsLspPathDown            { value 2012; }
            enum vRtrMplsLspPathRerouted        { value 2013; }
            enum vRtrMplsLspPathResignaled      { value 2014; }
            enum vRtrMplsP2mpInstanceUp         { value 2015; }
            enum vRtrMplsP2mpInstanceDown       { value 2016; }
            enum vRtrMplsS2lSubLspUp            { value 2017; }
            enum vRtrMplsS2lSubLspDown          { value 2018; }
            enum vRtrMplsS2lSubLspRerouted      { value 2019; }
            enum vRtrMplsS2lSubLspResignaled    { value 2020; }
            enum vRtrMplsLspPathSoftPreempted   { value 2021; }
            enum vRtrMplsLspPathLstFillReoptElig { value 2022; }
            enum vRtrMplsP2mpInstanceResignaled { value 2023; }
            enum vRtrMplsResignalTimerExpired   { value 2024; }
            enum vRtrMplsLspPathMbbStatusEvent  { value 2025; }
            enum vRtrMplsLspSwitchStbyFailure   { value 2026; }
            enum vRtrMplsLspActivePathChanged   { value 2027; }
            enum vRtrMplsXCBundleChange         { value 2028; }
            enum vRtrMplsNodeInIgpOverload      { value 2030; }
            enum vRtrMplsIPv6StateChange        { value 2031; }
            enum vRtrMplsIfIPv6StateChange      { value 2032; }
            enum vRtrMplsLspResourceExhaustion  { value 2033; }
            enum vRtrMplsLspManualSwitchFailure { value 2034; }
            enum vRtrMplsLspPathManualDegStateChg { value 2035; }
            enum vRtrMplsS2lSubLspPreempted     { value 2036; }
            enum vRtrMplsNodeInIgpOverloadIpv6  { value 2037; }
            enum tmnxMplsResourceHighUsage      { value 2038; }
            enum tmnxMplsResourceExhausted      { value 2039; }
            enum tmnxMplsResourceRecovered      { value 2040; }
        }
        description "Events for mpls module.";
    }

    typedef msdp-events {
        type enumeration {
            enum msdpEstablished                { value 2001; }
            enum msdpBackwardTransition         { value 2002; }
            enum tmnxMsdpNgActSrcLimExcd        { value 2008; }
            enum tmnxMsdpNgPeerActSrcLimExcd    { value 2009; }
            enum tmnxMsdpNgRPFFailure           { value 2010; }
            enum tmnxMsdpNgSourceSrcActMsgsExcd { value 2011; }
            enum tmnxMsdpNgGroupSrcActMsgsExcd  { value 2012; }
        }
        description "Events for msdp module.";
    }

    typedef nat-events {
        type enumeration {
            enum tmnxNatPlL2AwBlockUsageHigh    { value 2001; }
            enum tmnxNatIsaMemberSessionUsageHigh { value 2002; }
            enum tmnxNatPlLsnMemberBlockUsageHigh { value 2003; }
            enum tmnxNatL2AwSubIcmpPortUsageHigh { value 2007; }
            enum tmnxNatL2AwSubUdpPortUsageHigh { value 2008; }
            enum tmnxNatL2AwSubTcpPortUsageHigh { value 2009; }
            enum tmnxNatL2AwSubSessionUsageHigh { value 2010; }
            enum tmnxNatPlBlockAllocationLsn    { value 2012; }
            enum tmnxNatPlBlockAllocationL2Aw   { value 2013; }
            enum tmnxNatResourceProblemDetected { value 2014; }
            enum tmnxNatResourceProblemCause    { value 2015; }
            enum tmnxNatPlAddrFree              { value 2016; }
            enum tmnxNatPlLsnRedActiveChanged   { value 2017; }
            enum tmnxNatPcpSrvStateChanged      { value 2018; }
            enum tmnxNatMdaActive               { value 2020; }
            enum tmnxNatLsnSubBlksFree          { value 2021; }
            enum tmnxNatDetPlcyChanged          { value 2022; }
            enum tmnxNatMdaDetectsLoadSharingErr { value 2023; }
            enum tmnxNatIsaGrpOperStateChanged  { value 2024; }
            enum tmnxNatIsaGrpIsDegraded        { value 2025; }
            enum tmnxNatLsnSubIcmpPortUsgHigh   { value 2026; }
            enum tmnxNatLsnSubUdpPortUsgHigh    { value 2027; }
            enum tmnxNatLsnSubTcpPortUsgHigh    { value 2028; }
            enum tmnxNatLsnSubSessionUsgHigh    { value 2029; }
            enum tmnxNatInAddrPrefixBlksFree    { value 2030; }
            enum tmnxNatFwd2EntryAdded          { value 2031; }
            enum tmnxNatFwd2OperStateChanged    { value 2034; }
            enum tmnxNatVrtrOutDnatOnlyRoutesHigh { value 2035; }
            enum tmnxNatMapRuleChange           { value 2036; }
            enum tmnxNatMaxNbrSubsOrHostsExceeded { value 2037; }
            enum tmnxNatNbrSubsOrHostsBelowThrsh { value 2038; }
            enum tmnxNatVappActive              { value 2039; }
            enum tmnxNatVappDetectsLoadSharingErr { value 2040; }
            enum tmnxNatDetPfxMapOperStateChanged { value 2041; }
            enum tmnxNatDetMap2OperStateChanged { value 2042; }
            enum tmnxNatDynamicConfigMismatch   { value 2043; }
            enum tmnxNatPlL2AwMembrBlockUsageHigh { value 2044; }
            enum tmnxNatPlMemberExtBlockUsageHigh { value 2045; }
            enum tmnxNatPlLsnMemberPortUsageHigh { value 2046; }
            enum tmnxNatDetPlcyOperStateChanged { status obsolete; }
            enum tmnxNatDetMapOperStateChanged  { status obsolete; }
        }
        description "Events for nat module.";
    }

    typedef ntp-events {
        type enumeration {
            enum tmnxNtpAuthMismatch            { value 2001; }
            enum tmnxNtpNoServersAvail          { value 2002; }
            enum tmnxNtpServersAvail            { value 2003; }
            enum tmnxNtpOperChange              { value 2008; }
            enum tmnxNtpServerChange            { value 2009; }
        }
        description "Events for ntp module.";
    }

    typedef oam-events {
        type enumeration {
            enum tmnxOamPingProbeFailedV3       { value 2001; }
            enum tmnxOamPingTestFailedV3        { value 2002; }
            enum tmnxOamPingTestCompletedV3     { value 2003; }
            enum tmnxAncpLoopbackTestCompleted  { value 2004; }
            enum tmnxAncpLoopbackTestCompletedL { value 2005; }
            enum tmnxOamTrPathChange            { value 2050; }
            enum tmnxOamTrTestFailed            { value 2051; }
            enum tmnxOamTrTestCompleted         { value 2052; }
            enum svcIdInvalid                   { value 2053; }
            enum svcIdWrongType                 { value 2054; }
            enum tmnxOamLdpTtraceAutoDiscState  { value 2055; }
            enum tmnxOamLdpTtraceFecProbeState  { value 2056; }
            enum tmnxOamLdpTtraceFecDisStatus   { value 2057; }
            enum tmnxOamLdpTtraceFecPFailUpdate { value 2058; }
            enum tmnxOamSaaThreshold            { value 2101; }
            enum tmnxOamDiagTestCompleted       { value 2150; }
            enum tmnxTwampSrvInactivityTimeout  { value 2200; }
            enum tmnxTwampSrvMaxConnsExceeded   { value 2201; }
            enum tmnxTwampSrvPfxMaxConnsExceeded { value 2202; }
            enum tmnxTwampSrvMaxSessExceeded    { value 2203; }
            enum tmnxTwampSrvPfxMaxSessExceeded { value 2204; }
            enum tmnxTwampRflInactivityTimeout  { value 2205; }
            enum tmnxOamPmThrRaise              { value 2300; }
            enum tmnxOamPmThrClear              { value 2301; }
            enum tmnxOamSathSvcTestCompleted    { value 2400; }
            enum tmnxOamSathSvcStrmCompleted    { value 2401; }
        }
        description "Events for oam module.";
    }

    typedef ospf-events {
        type enumeration {
            enum tmnxOspfVirtIfStateChange      { value 2001; }
            enum tmnxOspfVirtNbrStateChange     { value 2003; }
            enum tmnxOspfVirtIfConfigError      { value 2005; }
            enum tmnxOspfVirtIfAuthFailure      { value 2007; }
            enum tmnxOspfVirtIfRxBadPacket      { value 2009; }
            enum tmnxOspfAreaOriginateLsa       { value 2012; }
            enum tmnxOspfAreaMaxAgeLsa          { value 2013; }
            enum tmnxOspfLsdbOverflow           { value 2014; }
            enum tmnxOspfLsdbApproachingOverflow { value 2015; }
            enum tmnxOspfNssaTranslatorStatusChg { value 2017; }
            enum tmnxOspfRestartStatusChange    { value 2018; }
            enum tmnxOspfVirtNbrRestartHlprStsChg { value 2020; }
            enum tmnxOspfSpfRunsStopped         { value 2021; }
            enum tmnxOspfSpfRunsRestarted       { value 2022; }
            enum tmnxOspfOverloadEntered        { value 2023; }
            enum tmnxOspfOverloadExited         { value 2024; }
            enum tmnxOspfAsOriginateLsa         { value 2025; }
            enum tmnxOspfAsMaxAgeLsa            { value 2026; }
            enum tmnxOspfShamIfStateChange      { value 2031; }
            enum tmnxOspfShamNbrStateChange     { value 2032; }
            enum tmnxOspfShamIfConfigError      { value 2033; }
            enum tmnxOspfShamIfAuthFailure      { value 2034; }
            enum tmnxOspfShamIfRxBadPacket      { value 2035; }
            enum tmnxOspfShamNbrRestartHlprStsChg { value 2037; }
            enum tmnxOspfFailureDisabled        { value 2038; }
            enum tmnxOspfExportLimitReached     { value 2039; }
            enum tmnxOspfExportLimitWarning     { value 2040; }
            enum tmnxOspfRoutesExpLmtDropped    { value 2041; }
            enum tmnxOspfNgNbrStateChange       { value 2042; }
            enum tmnxOspfNgIfConfigError        { value 2043; }
            enum tmnxOspfNgIfAuthFailure        { value 2044; }
            enum tmnxOspfNgIfRxBadPacket        { value 2045; }
            enum tmnxOspfNgIfStateChange        { value 2047; }
            enum tmnxOspfNgNbrRestartHlprStsChg { value 2048; }
            enum tmnxOspfNgLinkOriginateLsa     { value 2049; }
            enum tmnxOspfNgLinkMaxAgeLsa        { value 2050; }
            enum tmnxOspfNgLdpSyncTimerStarted  { value 2051; }
            enum tmnxOspfNgLdpSyncExit          { value 2052; }
            enum tmnxOspfSrSidError             { value 2053; }
            enum tmnxOspfSrSidNotInLabelRange   { value 2054; }
            enum tmnxOspfOverloadWarning        { value 2055; }
            enum tmnxOspfRejectedAdjacencySid   { value 2056; }
            enum tmnxOspfAdjBfdSessionSetupFail { value 2057; }
            enum tmnxOspfSrgbBadLabelRange      { value 2058; }
            enum tmnxOspfRejectedAdjacencySet   { value 2059; }
            enum tmnxOspfSidStatsIndexAlloc     { value 2060; }
            enum tmnxOspfDynHostnameDuplicate   { value 2061; }
            enum tmnxOspfDynHostnameInconsistent { value 2062; }
            enum tmnxOspfFaOperParticipationDown { value 2063; }
            enum tmnxOspfNgNbrStrictBfdBlocked  { value 2064; }
            enum tmnxOspfVirtIfTxRetransmit     { status obsolete; }
            enum tmnxOspfShamIfTxRetransmit     { status obsolete; }
            enum tmnxOspfNgIfTxRetransmit       { status obsolete; }
        }
        description "Events for ospf module.";
    }

    typedef pcap-events {
        type enumeration {
            enum tmnxPcapFileError              { value 2001; }
            enum tmnxPcapBufferFull             { value 2002; }
            enum tmnxPcapBufferReadWriteFailure { value 2003; }
            enum tmnxPcapSoftwareFailure        { value 2004; }
            enum tmnxPcapReadWriteFailure       { status obsolete; }
        }
        description "Events for PCAP module.";
    }

    typedef pcep-events {
        type enumeration {
            enum tmnxPcepPccPeerStateChange     { value 2001; }
        }
        description "Events for pcep module.";
    }

    typedef pfcp-events {
        type enumeration {
            enum tmnxPfcpInvalidIe              { value 2001; }
        }
        description "Events for PFCP (Packet Forwarding Control Protocol).";
    }

    typedef pim-events {
        type enumeration {
            enum vRtrPimNgIfNeighborLoss        { value 2001; }
            enum vRtrPimNgIfNeighborUp          { value 2002; }
            enum vRtrPimNgInvalidJoinPrune      { value 2003; }
            enum vRtrPimNgInvalidRegister       { value 2004; }
            enum vRtrPimNgGrpInSSMRange         { value 2005; }
            enum vRtrPimNgBSRStateChange        { value 2006; }
            enum vRtrPimNgHelloDropped          { value 2007; }
            enum vRtrPimNgSGLimitExceeded       { value 2008; }
            enum vRtrPimNgReplicationLmtExceeded { value 2009; }
            enum vRtrPimNgMDTLimitExceeded      { value 2010; }
            enum vRtrPimNgMaxGrpsLimitExceeded  { value 2011; }
            enum vRtrPimNgDataMtReused          { value 2012; }
            enum vRtrPimNgMcacPlcyDropped       { value 2013; }
            enum vRtrPimNgInvalidIPmsiTunnel    { value 2014; }
            enum vRtrPimNgMaxGraftRetry         { value 2015; }
            enum vRtrPimNgBierInbInvSD          { value 2016; }
            enum vRtrPimNgBierInbInvBfrId       { value 2017; }
            enum vRtrPimNgUmhBMonFastFailPriToStb { value 2018; }
            enum vRtrPimNgUmhBMonFastFailStbToPri { value 2019; }
            enum vRtrPimNgInstMaxNbrReached     { value 2020; }
            enum vRtrPimNgIfMaxNbrReached       { value 2021; }
        }
        description "Events for pim module.";
    }

    typedef pim-snooping-events {
        type enumeration {
            enum tmnxPimSnpgIfNeighborLoss      { value 2001; }
            enum tmnxPimSnpgIfNeighborUp        { value 2002; }
            enum tmnxPimSnpgSGLimitExceeded     { value 2003; }
            enum tmnxPimSnpgSnoopModeChanged    { value 2004; }
            enum tmnxPimSnpgIfMaxNbrReached     { value 2005; }
            enum tmnxPimSnpgMaxNbrReached       { value 2006; }
        }
        description "Events for pim-snooping module.";
    }

    typedef port-events {
        type enumeration {
            enum sonetSDHAlarmSet               { value 2001; }
            enum sonetSDHAlarmClear             { value 2002; }
            enum sonetSDHChannelAlarmSet        { value 2003; }
            enum sonetSDHChannelAlarmClear      { value 2004; }
            enum SFPInserted                    { value 2005; }
            enum SFPRemoved                     { value 2006; }
            enum SFPStatusFailure               { value 2008; }
            enum portError                      { value 2009; }
            enum ds3AlarmSet                    { value 2013; }
            enum ds3AlarmClear                  { value 2014; }
            enum ds1AlarmSet                    { value 2015; }
            enum ds1AlarmClear                  { value 2016; }
            enum etherAlarmSet                  { value 2017; }
            enum etherAlarmClear                { value 2018; }
            enum ds1LoopbackStart               { value 2019; }
            enum ds1LoopbackStop                { value 2020; }
            enum ds3LoopbackStart               { value 2021; }
            enum ds3LoopbackStop                { value 2022; }
            enum sdhLoopbackStart               { value 2023; }
            enum sdhLoopbackStop                { value 2024; }
            enum etherLoopDetected              { value 2025; }
            enum etherLoopCleared               { value 2026; }
            enum etherSpeedNotCompatible        { value 2027; }
            enum etherDuplexNotCompatible       { value 2028; }
            enum etherIngressRateCfgNotCompatible { value 2029; }
            enum digitalDiagnosticMonitorFailed { value 2030; }
            enum SFPStatusDDMCorrupt            { value 2031; }
            enum SFPStatusReadError             { value 2032; }
            enum SFPStatusUnsupported           { value 2033; }
            enum dsxClockSyncStateChange        { value 2034; }
            enum tmnxPortUnsupportedFunction    { value 2036; }
            enum otuAlarms                      { value 2037; }
            enum tPortAccEgrQGrpHostMatchFailure { value 2039; }
            enum tPortEgrVPortHostMatchFailure  { value 2040; }
            enum digitalDiagnosticMonitorCleared { value 2041; }
            enum tmnxEqSonetClockSrcNotCompatible { value 2046; }
            enum tmnxEqSonetSfThreshNotCompatible { value 2047; }
            enum tmnxEqSonetFramingNotCompatible { value 2048; }
            enum tmnxResvCbsPoolThreshGreen     { value 2049; }
            enum tmnxResvCbsPoolThreshAmber     { value 2050; }
            enum tmnxResvCbsPoolThreshRed       { value 2051; }
            enum tmnxEqPortEtherCrcAlarm        { value 2052; }
            enum tmnxEqPortEtherCrcAlarmClear   { value 2053; }
            enum tmnxEqPortEtherInternalAlarm   { value 2054; }
            enum tmnxEqPortEtherInternalAlarmClr { value 2055; }
            enum tmnxEqCohOptPortAlarm          { value 2056; }
            enum tmnxEqPortEtherSymMonAlarm     { value 2057; }
            enum tmnxEqPortEtherSymMonAlarmClear { value 2058; }
            enum SFPStatusCulprit               { value 2059; }
            enum SFPStatusBlocked               { value 2060; }
            enum SFPStatusOperational           { value 2061; }
            enum tmnxRS232ControlLeadSignalChg  { value 2062; }
            enum tmnxRS232SquelchStatusChange   { value 2063; }
            enum tmnxRS232SquelchResetIssued    { value 2064; }
            enum tmnxCellularBearerCreated      { value 2065; }
            enum tmnxCellularBearerDeleted      { value 2066; }
            enum tmnxCellularBearerModified     { value 2067; }
            enum tmnxEqPortEtherEgressRateChange { value 2068; }
            enum tmnxCellularNoServiceReset     { value 2069; }
            enum tmnxCellularActiveSimCardChange { value 2070; }
            enum tmnxPortEtherLoopbackStarted   { value 2071; }
            enum tmnxPortEtherLoopbackStopped   { value 2072; }
            enum tmnxPortGnssStatusChange       { value 2073; }
            enum tmnxWlanNetworkConnected       { value 2074; }
            enum tmnxWlanNetworkDisconnected    { value 2075; }
            enum tmnxPortAUIReset               { value 2076; }
            enum tmnxCellPortCbsdRegistered     { value 2077; }
            enum tmnxCellPortCbsdUnregistered   { value 2078; }
            enum tmnxCellPortCbsdGranted        { value 2079; }
            enum tmnxCellPortCbsdAuthorized     { value 2080; }
            enum tmnxCellPortCbsdTransDown      { value 2081; }
            enum tmnxHwAggShpSchedOperColorGreen { value 2082; }
            enum tmnxHwAggShpSchedOperColorAmber { value 2083; }
            enum tmnxHwAggShpSchedOperColorRed  { value 2084; }
            enum tmnxCellularRssiAlarm          { value 2085; }
            enum tmnxCellularRssiAlarmClear     { value 2086; }
            enum SFPStatusInvalidFormFactor     { value 2087; }
            enum tmnxDS0ChanGrpLoopbackStarted  { value 2089; }
            enum tmnxDS0ChanGrpLoopbackStopped  { value 2090; }
            enum yellowDiffDelayExceeded        { status obsolete; }
            enum redDiffDelayExceeded           { status obsolete; }
            enum bndlBadEndPtDiscriminator      { status obsolete; }
            enum bundleMlfrMemberLoopback       { status obsolete; }
            enum wtrkAlarms                     { status obsolete; }
            enum tmnxPortEtherLoopbackStart     { status obsolete; }
            enum tmnxPortEtherLoopbackStop      { status obsolete; }
        }
        description "Events for port module.";
    }

    typedef pppoe-events {
        type enumeration {
            enum tmnxPppoeSessionFailure        { value 2001; }
            enum tmnxPppoeNcpFailure            { value 2002; }
            enum tmnxMlpppBundleIndicatorsChange { value 2003; }
            enum tmnxPppoeLacSteeringActive     { value 2004; }
            enum tmnxPppoeLacSteeringStopped    { value 2005; }
            enum tmnxPppoeLacSteeringFailed     { value 2006; }
            enum tmnxPppoeMaxSessionsOvrExceeded { value 2007; }
        }
        description "Events for pppoe module.";
    }

    typedef ptp-events {
        type enumeration {
            enum tmnxPtpCardNotSupported        { value 2001; }
            enum tmnxPtpCardNotSupportedClear   { value 2002; }
            enum tmnxPtpMasterClockChangedEvent { value 2003; }
            enum tmnxPtpClockRecoveryStateChange { value 2004; }
            enum tmnxPtpOutOfResources          { value 2005; }
            enum tmnxPtpOutOfResourcesClear     { value 2006; }
            enum tmnxPtpDynamicChange           { value 2007; }
            enum tmnxPtpPortNoTimestamping      { value 2008; }
            enum tmnxPtpPortPtsfUnusable        { value 2009; }
            enum tmnxPtpRequiresSystemReboot    { value 2010; }
            enum tmnxPtpRequiresSystemRebootClear { value 2011; }
            enum tmnxPtpTimeRecoveryStateChange { value 2012; }
            enum tmnxPtpPeerNoTxTimestamping    { value 2013; }
            enum tmnxPtpPeerNoTxTimestampingClear { value 2014; }
            enum tmnxPtpPeerNoRxTimestamping    { value 2015; }
            enum tmnxPtpPeerNoRxTimestampingClear { value 2016; }
        }
        description "Events for ptp module.";
    }

    typedef python-events {
        type enumeration {
            enum tmnxPythonInterpreterRestarted { value 2001; }
        }
        description "Events for the PYTHON module.";
    }

    typedef rip-events {
        type enumeration {
            enum ripPacketDiscarded             { value 2001; }
            enum vRtrRipAuthTypeMismatch        { value 2002; }
            enum vRtrRipAuthTypeFailure         { value 2003; }
            enum vRtrRipInstanceShuttingDown    { value 2004; }
            enum vRtrRipInstanceRestarted       { value 2005; }
            enum vRtrRipInstanceExpLmtReached   { value 2006; }
            enum vRtrRipInstanceExpLmtWarning   { value 2007; }
            enum vRtrRipInstanceRtsExpLmtDropped { value 2008; }
            enum vRtrRipPeerBfdDown             { value 2010; }
        }
        description "Events for rip module.";
    }

    typedef route-policy-events {
        type enumeration {
            enum trigPolicyPrevEval             { value 2001; }
        }
        description "Events for route-policy module.";
    }

    typedef rsvp-events {
        type enumeration {
            enum vRtrRsvpStateChange            { value 2001; }
            enum vRtrRsvpIfStateChange          { value 2002; }
            enum vRtrRsvpIfNbrStateUp           { value 2003; }
            enum vRtrRsvpIfNbrStateDown         { value 2004; }
            enum vRtrRsvpPEFailOverPriToStdBy   { value 2005; }
            enum vRtrRsvpPEFailOverStdByToPri   { value 2006; }
        }
        description "Events for rsvp module.";
    }

    typedef security-events {
        type enumeration {
            enum cli_user_login                 { value 2001; }
            enum cli_user_logout                { value 2002; }
            enum cli_user_login_failed          { value 2003; }
            enum cli_user_login_max_attempts    { value 2004; }
            enum ftp_user_login                 { value 2005; }
            enum ftp_user_logout                { value 2006; }
            enum ftp_user_login_failed          { value 2007; }
            enum ftp_user_login_max_attempts    { value 2008; }
            enum ssh_user_login                 { value 2009; }
            enum ssh_user_logout                { value 2010; }
            enum ssh_user_login_failed          { value 2011; }
            enum ssh_user_login_max_attempts    { value 2012; }
            enum radiusOperStatusChange         { value 2014; }
            enum user_disconnect                { value 2015; }
            enum radiusSystemIpAddrNotSet       { value 2016; }
            enum tacplusOperStatusChange        { value 2018; }
            enum mafEntryMatch                  { value 2019; }
            enum ftp_transfer_successful        { value 2020; }
            enum ftp_transfer_failed            { value 2021; }
            enum enable_admin                   { value 2022; }
            enum host_snmp_attempts             { value 2023; }
            enum SSH_server_preserve_key_fail   { value 2024; }
            enum tacplusInetSrvrOperStatusChange { value 2025; }
            enum radiusInetServerOperStatusChange { value 2026; }
            enum tmnxKeyChainAuthFailure        { value 2027; }
            enum tmnxCpmProtViolPort            { value 2028; }
            enum tmnxCpmProtViolPortAgg         { value 2029; }
            enum tmnxCpmProtViolIf              { value 2030; }
            enum tmnxCpmProtViolSap             { value 2031; }
            enum tmnxCpmProtViolMac             { value 2032; }
            enum tmnxCpmProtViolVdoSvcClient    { value 2033; }
            enum tmnxCpmProtViolVdoVrtrClient   { value 2034; }
            enum tmnxMD5AuthFailure             { value 2036; }
            enum tmnxCpmProtDefPolModified      { value 2037; }
            enum tmnxCpmProtViolSdpBind         { value 2039; }
            enum tmnxCpmProtExcdSdpBind         { value 2040; }
            enum tmnxCpmProtExcdSapEcm          { value 2041; }
            enum tmnxCpmProtExcdSdpBindEcm      { value 2042; }
            enum tmnxPkiFileReadFailed          { value 2043; }
            enum tmnxPkiCertVerificationFailed  { value 2044; }
            enum tmnxCAProfileStateChange       { value 2045; }
            enum tmnxCpmProtExcdSapIp           { value 2046; }
            enum tmnxDcpFpDynPoolUsageHiAlmRaise { value 2047; }
            enum tmnxDcpFpDynPoolUsageHiAlmClear { value 2048; }
            enum tmnxDcpCardFpEventOvrflwClr    { value 2049; }
            enum tmnxDcpCardSapEventOvrflwClr   { value 2050; }
            enum tmnxDcpCardVrtrIfEventOvrflwClr { value 2051; }
            enum sapDcpStaticExcd               { value 2052; }
            enum sapDcpDynamicExcd              { value 2053; }
            enum sapDcpStaticHoldDownStart      { value 2054; }
            enum sapDcpDynamicHoldDownStart     { value 2055; }
            enum sapDcpStaticHoldDownEnd        { value 2056; }
            enum sapDcpDynamicHoldDownEnd       { value 2057; }
            enum sapDcpStaticConform            { value 2058; }
            enum sapDcpDynamicConform           { value 2059; }
            enum sapDcpLocMonExcd               { value 2060; }
            enum sapDcpLocMonExcdDynResource    { value 2061; }
            enum sapDcpLocMonExcdAllDynAlloc    { value 2062; }
            enum sapDcpLocMonExcdAllDynFreed    { value 2063; }
            enum sapDcpDynamicEnforceAlloc      { value 2064; }
            enum sapDcpDynamicEnforceFreed      { value 2065; }
            enum vRtrIfDcpStaticExcd            { value 2066; }
            enum vRtrIfDcpDynamicExcd           { value 2067; }
            enum vRtrIfDcpStaticHoldDownStart   { value 2068; }
            enum vRtrIfDcpDynamicHoldDownStart  { value 2069; }
            enum vRtrIfDcpStaticHoldDownEnd     { value 2070; }
            enum vRtrIfDcpDynamicHoldDownEnd    { value 2071; }
            enum vRtrIfDcpStaticConform         { value 2072; }
            enum vRtrIfDcpDynamicConform        { value 2073; }
            enum vRtrIfDcpLocMonExcd            { value 2074; }
            enum vRtrIfDcpLocMonExcdDynResource { value 2075; }
            enum vRtrIfDcpLocMonExcdAllDynAlloc { value 2076; }
            enum vRtrIfDcpLocMonExcdAllDynFreed { value 2077; }
            enum vRtrIfDcpDynamicEnforceAlloc   { value 2078; }
            enum vRtrIfDcpDynamicEnforceFreed   { value 2079; }
            enum tmnxDcpCardFpEventOvrflw       { value 2080; }
            enum tmnxDcpCardSapEventOvrflw      { value 2081; }
            enum tmnxDcpCardVrtrIfEventOvrflw   { value 2082; }
            enum tmnxPkiCAProfActnStatusChg     { value 2083; }
            enum tmnxCpmProtViolSapOutProf      { value 2084; }
            enum tmnxCpmProtViolIfOutProf       { value 2085; }
            enum sysDNSSecFailedAuthentication  { value 2086; }
            enum tmnxCpmProtExcdSdpBindIp       { value 2087; }
            enum tmnxSecComputeCertChainFailure { value 2088; }
            enum tmnxCpmProtViolSdpBindOutProf  { value 2089; }
            enum tmnxSecNotifKeyChainExpired    { value 2090; }
            enum tmnxSysLicenseInvalid          { value 2091; }
            enum tmnxSysLicenseExpiresSoon      { value 2092; }
            enum tmnxPkiCAProfRevokeChkWarning  { value 2093; }
            enum tmnxCAProfUpDueToRevokeChkCrlOpt { value 2094; }
            enum tmnxPkiCertBeforeExpWarning    { value 2095; }
            enum tmnxPkiCertAfterExpWarning     { value 2096; }
            enum tmnxPkiCertExpWarningCleared   { value 2097; }
            enum tmnxPkiCRLBeforeExpWarning     { value 2098; }
            enum tmnxPkiCRLAfterExpWarning      { value 2099; }
            enum tmnxPkiCRLExpWarningCleared    { value 2100; }
            enum tmnxSecNotifFileReloaded       { value 2101; }
            enum tmnxSysLicenseValid            { value 2102; }
            enum tmnxSecPwdHistoryFileLoadFailed { value 2103; }
            enum tmnxSecPwdHistoryFileWriteFailed { value 2104; }
            enum tmnxPkiCAProfCrlUpdateStart    { value 2105; }
            enum tmnxPkiCAProfCrlUpdateSuccess  { value 2106; }
            enum tmnxPkiCAProfCrlUpdateUrlFail  { value 2107; }
            enum tmnxPkiCAProfCrlUpdAllUrlsFail { value 2108; }
            enum tmnxPkiFileWriteFailed         { value 2109; }
            enum tmnxPkiCAProfCrlUpdNoNxtUpdTime { value 2110; }
            enum tmnxUsrProfSessionLimitExceeded { value 2111; }
            enum tmnxCliGroupSessionLimitExceeded { value 2112; }
            enum tmnxPkiCAProfCrlUpdLargPreUpdTm { value 2113; }
            enum tmnxPkiCertNotYetValid         { value 2114; }
            enum tmnxPkiCRLNotYetValid          { value 2115; }
            enum tmnxAppPkiCertVerificationFailed { value 2116; }
            enum grpc_user_login                { value 2117; }
            enum grpc_user_logout               { value 2118; }
            enum grpc_user_login_failed         { value 2119; }
            enum grpc_user_login_max_attempts   { value 2120; }
            enum netconf_user_login             { value 2121; }
            enum netconf_user_logout            { value 2122; }
            enum netconf_user_login_failed      { value 2123; }
            enum netconf_user_login_max_attempts { value 2124; }
            enum tmnxSysLicenseActivated        { value 2125; }
            enum tmnxConfigModify               { value 2206; }
            enum tmnxConfigCreate               { value 2207; }
            enum tmnxConfigDelete               { value 2208; }
            enum tmnxStateChange                { value 2209; }
            enum radiusUserProfileInvalid       { value 2220; }
            enum tmnxSysStandbyLicensingError   { value 2221; }
            enum tmnxSysStandbyLicensingReady   { value 2222; }
            enum md_cli_io                      { value 2223; }
            enum md_cli_unauth_io               { value 2224; }
            enum tmnxSysAppLicenseInsufficient  { value 2225; }
            enum tmnxSysLicenseUpdateRequired   { value 2226; }
            enum netconf_auth                   { value 2227; }
            enum netconf_unauth                 { value 2228; }
            enum grpc_auth                      { value 2229; }
            enum grpc_unauth                    { value 2230; }
            enum tmnxCertKeyPairGen             { value 2231; }
            enum tmnxCertImport                 { value 2232; }
            enum tmnxCertExport                 { value 2233; }
            enum tmnxFileDeleted                { value 2234; }
            enum tmnxFileMoved                  { value 2235; }
            enum tmnxFileCopied                 { value 2236; }
            enum tmnxFileUnzip                  { value 2237; }
            enum tmnxPasswordHashingChanged     { value 2238; }
            enum tmnxUserPasswordChangedByAdmin { value 2239; }
            enum tmnxSSHSessionFailed           { value 2240; }
            enum tmnxSecSignedSwCpmBootEvent    { value 2241; }
            enum tSecSgndSwUefiVarsUpdtReqd     { value 2242; }
            enum tmnxPkiCertUpdUpdateStarted    { value 2245; }
            enum tmnxPkiCertUpdUpdateFinished   { value 2246; }
            enum tmnxPkiCertUpdUpdateFailed     { value 2247; }
            enum tmnxSystemPasswordChangedByAdmin { value 2248; }
            enum tmnxSysLicenseCleared          { value 2249; }
            enum tmnxSysLicensingStateOk        { value 2250; }
            enum tmnxPkiCertChainCompareCaNoMatch { value 2251; }
            enum ssh_auth_key_gen               { value 2252; }
            enum ssh_auth_key_synch_fail        { value 2253; }
        }
        description "Events for security module.";
    }

    typedef snmp-events {
        type enumeration {
            enum coldStart                      { value 2001; }
            enum warmStart                      { value 2002; }
            enum authenticationFailure          { value 2003; }
            enum linkDown                       { value 2004; }
            enum linkUp                         { value 2005; }
            enum risingAlarm                    { value 2101; }
            enum fallingAlarm                   { value 2102; }
            enum snmpdError                     { value 2201; }
        }
        description "Events for snmp module.";
    }

    typedef sr-mpls-events {
        type enumeration {
            enum tmnxSrMplsPfxSidFailure        { value 2001; }
        }
        description "Events for sr-mpls module.";
    }

    typedef srv6-events {
        type enumeration {
            enum vRtrSrv6FunctionExhaustion     { value 2001; }
            enum vRtrSrv6SvcSidIndex            { value 2002; }
            enum vRtrSrv6LocatorResExhaustion   { value 2003; }
        }
        description "Events for srv6 module.";
    }

    typedef sr-policy-events {
        type enumeration {
            enum vRtrSrPathIsCandPathOperChanged { value 2001; }
            enum vRtrSrPlcyPathActiveStateChanged { value 2002; }
        }
        description "Events for sr-policy module.";
    }

    typedef stp-events {
        type enumeration {
            enum topologyChangeSapMajorState    { value 2001; }
            enum newRootSap                     { value 2002; }
            enum topologyChangeVcpState         { value 2003; }
            enum newRootVcpState                { value 2004; }
            enum topologyChangeSapState         { value 2005; }
            enum receivedTCN                    { value 2006; }
            enum newRootBridge                  { value 2007; }
            enum unacknowledgedTCN              { value 2008; }
            enum higherPriorityBridge           { value 2009; }
            enum sapEncapPVST                   { value 2011; }
            enum sapEncapDot1d                  { value 2012; }
            enum tmnxSvcTopoChgSdpBindMajorState { value 2014; }
            enum tmnxSvcNewRootSdpBind          { value 2015; }
            enum tmnxSvcTopoChgSdpBindState     { value 2016; }
            enum tmnxSvcSdpBindRcvdTCN          { value 2017; }
            enum tmnxSvcSdpBindRcvdHigherBriPrio { value 2018; }
            enum tmnxSvcSdpBindEncapPVST        { value 2019; }
            enum tmnxSvcSdpBindEncapDot1d       { value 2020; }
            enum tmnxNewCistRegionalRootBridge  { value 2021; }
            enum tmnxNewMstiRegionalRootBridge  { value 2022; }
            enum tmnxStpRootGuardViolation      { value 2023; }
            enum tmnxStpMeshNotInMstRegion      { value 2024; }
            enum tmnxSapStpExcepCondStateChng   { value 2025; }
            enum tmnxSdpBndStpExcepCondStateChng { value 2026; }
            enum sapActiveProtocolChange        { value 2050; }
            enum tmnxSvcSdpActiveProtocolChange { value 2051; }
            enum vcpActiveProtocolChange        { value 2052; }
            enum topologyChangePipMajorState    { value 2053; }
            enum topologyChangePipState         { value 2054; }
            enum tmnxPipStpExcepCondStateChng   { value 2055; }
            enum pipActiveProtocolChange        { value 2056; }
        }
        description "Events for stp module.";
    }

    typedef svcmgr-events {
        type enumeration {
            enum svcTlsMacPinningViolation      { value 2011; }
            enum tmnxSubSlaacOverride           { value 2022; }
            enum svcEvpnMplsMacMoveExceedNonBlock { value 2068; }
            enum svcTlsVxInstReplicatorChgd     { value 2090; }
            enum svcArpHostOverride             { value 2091; }
            enum svcEvpnMHEsEviDFStateChgd      { value 2094; }
            enum svcEvpnMHEsIsidDFStateChgd     { value 2095; }
            enum svcEvpnRcvdProtSrcMac          { value 2096; }
            enum svcBgpEvpnBHDupMacAddrsDetected { value 2097; }
            enum svcEvpnEtreeBumLabelSysHiUsgSet { value 2099; }
            enum svcEvpnEtreeBumLabelSysHiUsgClr { value 2100; }
            enum svcVxlanEvpnMplsDestSysHiUsgSet { value 2101; }
            enum svcVxlanEvpnMplsDestSysHiUsgClr { value 2102; }
            enum svcStatusChanged               { value 2103; }
            enum svcTlsFdbTableFullAlarmRaised  { value 2104; }
            enum svcTlsFdbTableFullAlarmCleared { value 2105; }
            enum svcSysEvpnESDfPrefOperValChange { value 2106; }
            enum tmnxSvcSysFdbTableHighUsgSet   { value 2107; }
            enum iesIfStatusChanged             { value 2108; }
            enum tmnxEndPointTxActiveChanged    { value 2110; }
            enum tmnxSvcSysFdbTableHighUsgClr   { value 2112; }
            enum svcEvpnMHStandbyStatusChg      { value 2113; }
            enum svcEvpnVxVTepLclBiasAddFailSet { value 2114; }
            enum svcEvpnESVxVTepLclBiasAddFailSet { value 2115; }
            enum svcEvpnVxVTepLclBiasAddFailClr { value 2116; }
            enum svcEvpnESVxVTepLclBiasAddFailClr { value 2117; }
            enum svcEvpnRcvdPbbProtSrcMac       { value 2118; }
            enum svcTlsMrpAttrRegistrationFailed { value 2120; }
            enum svcTlsMrpAttrTblFullAlarmRaised { value 2125; }
            enum svcTlsMrpAttrTblFullAlarmCleared { value 2126; }
            enum svcEvpnMplsTEPEgrLblStateChgd  { value 2127; }
            enum svcEpipePbbOperStatusChanged   { value 2128; }
            enum svcTlsVxInstVTEPEgrVniStateChgd { value 2129; }
            enum svcEvpnVxInstESDstTEPStateChgd { value 2130; }
            enum svcSrv6InstTEPSidOperStateChgd { value 2131; }
            enum svcSrv6InstESDstTEPOperStateChgd { value 2132; }
            enum svcEvpnMplsESDestTEPStateChgd  { value 2133; }
            enum svcBgpEvpnTepStateChgd         { value 2134; }
            enum svcSrv6FunctionOutOfResources  { value 2135; }
            enum sapStatusChanged               { value 2203; }
            enum sapTlsMacAddrLimitAlarmRaised  { value 2204; }
            enum sapTlsMacAddrLimitAlarmCleared { value 2205; }
            enum hostConnectivityLost           { value 2206; }
            enum hostConnectivityRestored       { value 2207; }
            enum sapReceivedProtSrcMac          { value 2208; }
            enum sapTlsMacMoveExceeded          { value 2209; }
            enum sapPortStateChangeProcessed    { value 2210; }
            enum sapCemPacketDefectAlarm        { value 2211; }
            enum sapCemPacketDefectAlarmClear   { value 2212; }
            enum msapStateChanged               { value 2213; }
            enum msapCreationFailure            { value 2214; }
            enum sapTlsMacMoveExceedNonBlock    { value 2229; }
            enum sapEthLoopbackStarted          { value 2230; }
            enum sapEthLoopbackStopped          { value 2231; }
            enum sapTunnelEncapIpMtuTooSmall    { value 2243; }
            enum tmnxIpTunnelOperStateChange    { value 2244; }
            enum sapIfIgnorePortStateStart      { value 2245; }
            enum sapIfIgnorePortStateStop       { value 2246; }
            enum sapReceivedPbbProtSrcMac       { value 2247; }
            enum sdpStatusChanged               { value 2303; }
            enum sdpBindStatusChanged           { value 2306; }
            enum sdpKeepAliveStarted            { value 2307; }
            enum sdpKeepAliveStopped            { value 2308; }
            enum sdpKeepAliveProbeFailure       { value 2309; }
            enum sdpKeepAliveLateReply          { value 2310; }
            enum sdpTlsMacAddrLimitAlarmRaised  { value 2311; }
            enum sdpTlsMacAddrLimitAlarmCleared { value 2312; }
            enum sdpBindPwPeerStatusBitsChanged { value 2313; }
            enum sdpBindTlsMacMoveExceeded      { value 2314; }
            enum sdpBindPwPeerFaultAddrChanged  { value 2315; }
            enum sdpBindSdpStateChangeProcessed { value 2316; }
            enum sdpBandwidthOverbooked         { value 2317; }
            enum sdpBindInsufficientBandwidth   { value 2318; }
            enum dynamicSdpConfigChanged        { value 2319; }
            enum dynamicSdpBindConfigChanged    { value 2320; }
            enum dynamicSdpCreationFailed       { value 2321; }
            enum dynamicSdpBindCreationFailed   { value 2322; }
            enum sdpEgrIfsNetDomInconsCntChanged { value 2323; }
            enum sdpBindIpipeCeIpAddressChange  { value 2324; }
            enum sdpBindReceivedProtSrcMac      { value 2325; }
            enum sdpBindPwLocalStatusBitsChanged { value 2326; }
            enum sdpBindTlsMacMoveExceedNonBlock { value 2327; }
            enum sdpBindEthLoopbackStarted      { value 2328; }
            enum sdpBindEthLoopbackStopped      { value 2329; }
            enum sdpPbbActvPwWithNonActvCtrlPwChg { value 2330; }
            enum svcBgpEvpnDupMacAddrsDetected  { value 2331; }
            enum svcBgpEvpnDupMacAddrsCleared   { value 2332; }
            enum svcTlsVTEPHiUsageAlarmRaised   { value 2335; }
            enum svcTlsVTEPHiUsageAlarmCleared  { value 2336; }
            enum svcTlsVTEPEgrVniSysHiUsgAlarmSet { value 2337; }
            enum svcTlsVTEPEgrVniSysHiUsgAlarmClr { value 2338; }
            enum svcTlsVTEPEgrVniSvcHiUsgAlarmSet { value 2339; }
            enum svcTlsVTEPEgrVniSvcHiUsgAlarmClr { value 2340; }
            enum svcBindSysHiUsageAlarmRaised   { value 2341; }
            enum svcBindSysHiUsageAlarmCleared  { value 2342; }
            enum sdpControlPwActiveStateChg     { value 2345; }
            enum svcTlsProxyArpDupDetect        { value 2346; }
            enum svcTlsProxyArpDupClear         { value 2347; }
            enum svcTlsProxyNdDupDetect         { value 2348; }
            enum svcTlsProxyNdDupClear          { value 2349; }
            enum svcTlsEvpnTunnNHopHiUsgAlarmSet { value 2350; }
            enum svcTlsEvpnTunnNHopHiUsgAlarmClr { value 2351; }
            enum svcEvpnMplsTEPHiUsageRaised    { value 2352; }
            enum svcEvpnMplsTEPHiUsageCleared   { value 2353; }
            enum svcEvpnMplsTEPEgrBndSysHiUsgSet { value 2354; }
            enum svcEvpnMplsTEPEgrBndSysHiUsgClr { value 2355; }
            enum svcEvpnMplsTEPEgrBndSvcHiUsgSet { value 2356; }
            enum svcEvpnMplsTEPEgrBndSvcHiUsgClr { value 2357; }
            enum svcTlsProxyArpSysHiUsgSet      { value 2358; }
            enum svcTlsProxyArpSysHiUsgClr      { value 2359; }
            enum svcTlsProxyArpSvcHiUsgSet      { value 2360; }
            enum svcTlsProxyArpSvcHiUsgClr      { value 2361; }
            enum svcTlsProxyNdSysHiUsgSet       { value 2362; }
            enum svcTlsProxyNdSysHiUsgClr       { value 2363; }
            enum svcTlsProxyNdSvcHiUsgSet       { value 2364; }
            enum svcTlsProxyNdSvcHiUsgClr       { value 2365; }
            enum svcSiteMinDnTimerStateChg      { value 2366; }
            enum sdpBindReceivedPbbProtSrcMac   { value 2367; }
            enum svcTlsMfibTableFullAlarmRaised { value 2401; }
            enum svcTlsMfibTableFullAlarmCleared { value 2402; }
            enum tmnxSubscriberCreated          { value 2500; }
            enum tmnxSubscriberDeleted          { value 2501; }
            enum tmnxSubscriberRenamed          { value 2502; }
            enum tmnxSubAcctPlcyFailure         { value 2503; }
            enum tmnxSubMcsRelatedProblem       { value 2504; }
            enum tmnxSubAuthPlcyRadSerOperStatChg { value 2505; }
            enum tmnxSubAcctPlcyRadSerOperStatChg { value 2506; }
            enum svcEndPointMacLimitAlarmRaised { value 2507; }
            enum svcEndPointMacLimitAlarmCleared { value 2508; }
            enum tmnxSubRadSapDisconnectError   { value 2509; }
            enum tmnxSubRadSdpBndDisconnectError { value 2510; }
            enum tmnxSubRadSapCoAError          { value 2511; }
            enum tmnxSubRadSdpBndCoAError       { value 2512; }
            enum tmnxSubRadSapSubAuthError      { value 2513; }
            enum tmnxSubRadSdpBndSubAuthError   { value 2514; }
            enum svcFdbMimDestTblFullAlrm       { value 2515; }
            enum svcFdbMimDestTblFullAlrmCleared { value 2516; }
            enum svcPersistencyProblem          { value 2517; }
            enum svcArpHostPopulateErr          { value 2520; }
            enum svcEPMCEPConfigMismatch        { value 2522; }
            enum svcEPMCEPConfigMismatchResolved { value 2523; }
            enum svcEPMCEPPassiveModeActive     { value 2524; }
            enum svcEPMCEPPassiveModePassive    { value 2525; }
            enum sapHostBGPPeeringSetupFailed   { value 2526; }
            enum tmnxSubUserCategoryOutOfCredit { value 2527; }
            enum svcRestoreHostProblem          { value 2528; }
            enum tmnxSubUserCategoryRefreshCredit { value 2529; }
            enum tmnxSubUserCategoryError       { value 2530; }
            enum svcTlsSiteDesigFwdrChg         { value 2531; }
            enum sapTlsDataSapInstStatusChgd    { value 2532; }
            enum svcTlsGroupOperStatusChanged   { value 2533; }
            enum sapTunnelStateChange           { value 2535; }
            enum tmnxSubHostInconsistentAtmTdOvr { value 2536; }
            enum svcMSPwRtMisconfig             { value 2541; }
            enum svcOperGrpOperStatusChanged    { value 2542; }
            enum sapIpipeCeIpAddrChange         { value 2543; }
            enum svcMSPwRetryExpiredNotif       { value 2544; }
            enum svcVllSiteDesigFwdrChg         { value 2545; }
            enum tmnxSubSlaacSetupFailure       { value 2546; }
            enum tmnxIpTunnelOperRemIpChg       { value 2547; }
            enum tmnxSubHostLcktLimitReached    { value 2548; }
            enum tmnxSubHostLcktSapLimitReached { value 2549; }
            enum tmnxSubSysChassMemoryUsageHi   { value 2551; }
            enum tmnxSubVSubnetHostsDeleted     { value 2552; }
            enum sapHostRipListenerSetupFailed  { value 2553; }
            enum tmnxSubIpoeInvalidSessionKey   { value 2554; }
            enum tmnxSubIpoeInvalidCidRidChange { value 2555; }
            enum tmnxSubIpoeSessionLimitReached { value 2556; }
            enum tmnxSubIpoePersistenceRecovery { value 2557; }
            enum tmnxSubIpoeMigrHostDeleted     { value 2559; }
            enum tmnxSubMngdHostCreationFail    { value 2560; }
            enum tmnxSubMngdHostOverride        { value 2561; }
            enum tmnxSubHostInfoConflict        { value 2562; }
            enum tmnxSubPlBndFailed             { value 2563; }
            enum tmnxSubBrgCreated              { value 2564; }
            enum tmnxSubBrgDeleted              { value 2565; }
            enum tmnxSubBrgCvInitFailed         { value 2566; }
            enum tmnxSubBrgRadiusUpdateIpoeSeFail { value 2567; }
            enum tmnxSubBrgRadiusCoaError       { value 2568; }
            enum tmnxSubBrgRadiusAuthError      { value 2569; }
            enum tmnxSubBrgSessionLimitReached  { value 2570; }
            enum tmnxSubStatsResourceLimitReached { value 2571; }
            enum tmnxSubDhcpOverloadDetected    { value 2572; }
            enum aluIpTransportStateChanged     { value 2573; }
            enum tmnxSubBrgRadiusProxyAuthError { value 2574; }
            enum tmnxSubIpoeSessionBrgNotAuth   { value 2575; }
            enum tmnxSubRadiusCoaNatFwdFailed   { value 2576; }
            enum tmnxSubSVlanStatsReachedMaximum { value 2577; }
            enum svcTlsVxInstMacAdrLimitAlrmRsd { value 2600; }
            enum svcTlsVxInstMacAdrLimitAlrmClrd { value 2601; }
            enum tmnxSubCupsUpSapCreationFailed { value 2602; }
            enum tmnxSubCupsUpIfCreationFailed  { value 2603; }
            enum tmnxPfcpAssocPathMgmtStateChgd { value 2604; }
            enum tmnxSubInfoEgrAggRateLimitLowReq { value 2605; }
            enum tmnxSubIpoeWppRegistrationFailed { value 2606; }
            enum svcEvpnMplsTEPIpSysHiUsgSet    { value 2607; }
            enum svcEvpnMplsTEPIpSysHiUsgClr    { value 2608; }
            enum svcEvpnMHAutoEsiCreated        { value 2609; }
            enum svcEvpnMHAutoEsiConflict       { value 2610; }
            enum svcSrv6TEPEgrBndSysHiUsgSet    { value 2611; }
            enum svcSrv6TEPEgrBndSysHiUsgClr    { value 2612; }
            enum svcIfSubForwardingStatsDisNotify { value 2614; }
            enum svcIfSubForwardingStatsEnNotify { value 2615; }
            enum svcRoutedVplsEvpnGWDrStateChgd { value 2616; }
            enum svcSrv6TEPEgrBndSvcHiUsgSet    { value 2617; }
            enum svcSrv6TEPEgrBndSvcHiUsgClr    { value 2618; }
            enum tmnxSapMRtCpeChkStatusChange   { value 2619; }
            enum svcTlsVxlanReplicatorChgd      { status obsolete; }
            enum svcTlsDupVTEPEgrVNIDetected    { status obsolete; }
            enum svcTlsDupVTEPEgrVNICleared     { status obsolete; }
            enum sapAtmPppSessionFailure        { status obsolete; }
            enum sapAtmPppNcpFailure            { status obsolete; }
            enum svcSrv6FunctionExhaustion      { status obsolete; }
        }
        description "Events for svcmgr module.";
    }

    typedef system-events {
        type enumeration {
            enum stiDateAndTimeChanged          { value 2001; }
            enum ssiSaveConfigSucceeded         { value 2002; }
            enum ssiSaveConfigFailed            { value 2003; }
            enum sbiBootConfig                  { value 2004; }
            enum sbiBootSnmpd                   { value 2005; }
            enum tmnxConfigModify               { value 2006; }
            enum tmnxConfigCreate               { value 2007; }
            enum tmnxConfigDelete               { value 2008; }
            enum tmnxStateChange                { value 2009; }
            enum tmnxModuleMallocFailed         { value 2010; }
            enum tmnxTrapDropped                { value 2011; }
            enum ssiSyncConfigOK                { value 2012; }
            enum ssiSyncConfigFailed            { value 2013; }
            enum ssiSyncBootEnvOK               { value 2014; }
            enum ssiSyncBootEnvFailed           { value 2015; }
            enum socket_bind_failed             { value 2016; }
            enum socket_conn_accept_failed      { value 2017; }
            enum sntpTimeDiffExceedsThreshold   { value 2018; }
            enum tmnxSssiMismatch               { value 2022; }
            enum tmnxSnmpdStateChange           { value 2023; }
            enum tmnxRedStandbySyncing          { value 2024; }
            enum tmnxRedStandbyReady            { value 2025; }
            enum tmnxRedStandbySyncLost         { value 2026; }
            enum tmnxRedSwitchover              { value 2027; }
            enum tmnxRedCpmActive               { value 2028; }
            enum tmnxRedSingleCpm               { value 2029; }
            enum persistencyClosedAlarmRaised   { value 2030; }
            enum persistencyClosedAlarmCleared  { value 2031; }
            enum tmnxSntpOperChange             { value 2032; }
            enum tmnxFtpClientFailure           { value 2034; }
            enum persistencyEventReport         { value 2037; }
            enum sbiBootConfigFailFileError     { value 2038; }
            enum sbiBootConfigOKFileError       { value 2039; }
            enum persistenceRestoreProblem      { value 2041; }
            enum tmnxSysRollbackStarted         { value 2042; }
            enum tmnxSysRollbackStatusChange    { value 2043; }
            enum tmnxSysRollbackSaveStatusChange { value 2044; }
            enum tmnxSysRollbackFileDeleteStatus { value 2045; }
            enum ssiSyncRollbackOK              { value 2046; }
            enum ssiSyncRollbackFailed          { value 2047; }
            enum ssiSyncCertOK                  { value 2048; }
            enum ssiSyncCertFailed              { value 2049; }
            enum persistencyFileSysThresRaised  { value 2050; }
            enum persistencyFileSysThresCleared { value 2051; }
            enum tmnxSysExecStarted             { value 2052; }
            enum tmnxSysExecFinished            { value 2053; }
            enum tmnxSysRollbackSaveStarted     { value 2054; }
            enum tmnxSysRollbackDeleteStarted   { value 2055; }
            enum tmnxSysNvsysFileError          { value 2056; }
            enum tmnxConfigConflict             { value 2058; }
            enum tmnxSysBaseMacAddressNotSet    { value 2067; }
            enum tmnxSmLaunchStartFailed        { value 2068; }
            enum tmnxEhsHandlerInvoked          { value 2069; }
            enum tmnxEhsDroppedByMinDelay       { value 2070; }
            enum tmnxSysAppStats24HrsAvailable  { value 2071; }
            enum tmnxSysAppStatsWeekAvailable   { value 2072; }
            enum tmnxSysMgmtIfModeChangeStart   { value 2076; }
            enum tmnxSysMgmtIfModeChangeComplete { value 2077; }
            enum tmnxSysMgmtIfModeChangeFailure { value 2078; }
            enum tmnxSysMgmtIfLiIncorrectFormat { value 2079; }
            enum tmnxSysMgmtIfLiCfgNotEncrypted { value 2080; }
            enum stiDateAndTimeChanging         { value 2081; }
            enum tmnxSysSwFabFailRecStarted     { value 2082; }
            enum tmnxSysSwFabFailRecCompleted   { value 2083; }
            enum tmnxSysSwFabFailRecAborted     { value 2084; }
            enum tmnxSysSwFabFailRecDetected    { value 2085; }
            enum tMirrorLiXIfLicenseInvalid     { value 2086; }
            enum mdSaveCommitHistoryFailed      { value 2087; }
            enum sbiBootMdReadCommitHistoryFailed { value 2088; }
            enum tmnxSysDyingGasp               { value 2090; }
            enum tmnxSysHttpRdrOutOfSeqLimitExc { value 2091; }
            enum schedActionFailure             { value 2101; }
            enum smScriptAbort                  { value 2102; }
            enum smScriptResult                 { value 2103; }
            enum smScriptException              { value 2104; }
            enum ssiSaveIncrementConfigSucceeded { value 2110; }
            enum ssiSaveIncrementConfigFailed   { value 2111; }
            enum ssiSaveBackgroundConfigSucceeded { value 2112; }
            enum ssiSaveBackgroundConfigFailed  { value 2113; }
            enum tmnxLastSystemRebootAdmin      { value 2114; }
            enum mdCommitInProgress             { value 2120; }
            enum mdCommitSucceeded              { value 2121; }
            enum tmnxSysVsdServerAvailable      { status obsolete; }
            enum tmnxSysVsdServerUnavailable    { status obsolete; }
            enum tmnxSysXmppServerFunctional    { status obsolete; }
            enum tmnxSysXmppServerNotFunctional { status obsolete; }
        }
        description "Events for system module.";
    }

    typedef treesid-events {
        type enumeration {
            enum vRtrTreeSidCdtPathChanged      { value 2001; }
            enum vRtrTreeSidCdtPathActInsChanged { value 2002; }
            enum vRtrTreeSidInSidRegFailure     { value 2003; }
            enum vRtrTreeSidTreeIdAllocFailure  { value 2004; }
            enum vRtrTreeSidRepSegResExhaustion { value 2005; }
            enum vRtrTreeSidRepSegResExhstCleared { value 2006; }
            enum vRtrTreeSidLabelRangeExhaustion { value 2007; }
            enum vRtrTreeSidLblRangeExhstCleared { value 2008; }
            enum vRtrTreeSidFailOverPriToStdBy  { value 2009; }
            enum vRtrTreeSidFailOverStdByToPri  { value 2010; }
        }
        description "Events for tree-sid module.";
    }

    typedef user-events {
        type enumeration {
            enum cli_user_login                 { value 2001; }
            enum cli_user_logout                { value 2002; }
            enum cli_user_login_failed          { value 2003; }
            enum cli_user_login_max_attempts    { value 2004; }
            enum ftp_user_login                 { value 2005; }
            enum ftp_user_logout                { value 2006; }
            enum ftp_user_login_failed          { value 2007; }
            enum ftp_user_login_max_attempts    { value 2008; }
            enum cli_user_io                    { value 2009; }
            enum snmp_user_set                  { value 2010; }
            enum cli_config_io                  { value 2011; }
            enum cli_unauth_user_io             { value 2012; }
            enum cli_unauth_config_io           { value 2013; }
            enum grpc_user_login                { value 2014; }
            enum grpc_user_logout               { value 2015; }
            enum grpc_user_login_failed         { value 2016; }
            enum grpc_user_login_max_attempts   { value 2017; }
            enum netconf_user_login             { value 2018; }
            enum netconf_user_logout            { value 2019; }
            enum netconf_user_login_failed      { value 2020; }
            enum netconf_user_login_max_attempts { value 2021; }
        }
        description "Events for user module.";
    }

    typedef video-events {
        type enumeration {
            enum tmnxVdoDuplicateSsrcId         { value 2001; }
            enum tmnxVdoMdaSessionsLimitExceeded { value 2002; }
            enum tmnxVdoMdaSGLimitExceeded      { value 2003; }
            enum tmnxVdoMdaSessionsLimitCleared { value 2004; }
            enum tmnxVdoMdaSGLimitCleared       { value 2005; }
            enum tmnxVdoAdSpliceAbort           { value 2006; }
            enum tmnxVdoClientSessionsLmtExceeded { value 2007; }
            enum tmnxVdoClientSessionsLmtCleared { value 2008; }
            enum tmnxVdoGrpSrcAnlyzrErrState    { value 2009; }
            enum tmnxVdoGrpSrcAnlyzrStClear     { value 2010; }
            enum tmnxVdoMdaFccBwLimitExceeded   { value 2011; }
            enum tmnxVdoMdaFccBwLimitCleared    { value 2012; }
            enum tmnxVdoMdaRetBwLimitExceeded   { value 2013; }
            enum tmnxVdoMdaRetBwLimitCleared    { value 2014; }
            enum tmnxVdoMdaFccRetTotBwLmtExceeded { value 2015; }
            enum tmnxVdoMdaFccRetTotBwLmtCleared { value 2016; }
            enum tmnxVdoMdaFccSesLimitExceeded  { value 2017; }
            enum tmnxVdoMdaFccSesLimitCleared   { value 2018; }
            enum tmnxVdoMdaRetSesLimitExceeded  { value 2019; }
            enum tmnxVdoMdaRetSesLimitCleared   { value 2020; }
            enum tmnxVdoMdaFccRetTotSeLmtExceeded { value 2021; }
            enum tmnxVdoMdaFccRetTotSeLmtCleared { value 2022; }
            enum tmnxVdoVappSessionsLimitExceeded { value 2023; }
            enum tmnxVdoVappSGLimitExceeded     { value 2024; }
            enum tmnxVdoVappSessionsLimitCleared { value 2025; }
            enum tmnxVdoVappSGLimitCleared      { value 2026; }
            enum tmnxVdoVappFccBwLimitExceeded  { value 2027; }
            enum tmnxVdoVappFccBwLimitCleared   { value 2028; }
            enum tmnxVdoVappRetBwLimitExceeded  { value 2029; }
            enum tmnxVdoVappRetBwLimitCleared   { value 2030; }
            enum tmnxVdoVappFccRetTotBwLmtExceded { value 2031; }
            enum tmnxVdoVappFccRetTotBwLmtCleared { value 2032; }
            enum tmnxVdoVappFccSesLimitExceeded { value 2033; }
            enum tmnxVdoVappFccSesLimitCleared  { value 2034; }
            enum tmnxVdoVappRetSesLimitExceeded { value 2035; }
            enum tmnxVdoVappRetSesLimitCleared  { value 2036; }
            enum tmnxVdoVappFccRetTotSeLmtExceded { value 2037; }
            enum tmnxVdoVappFccRetTotSeLmtCleared { value 2038; }
        }
        description "Events for video module.";
    }

    typedef vrrp-events {
        type enumeration {
            enum vrrpTrapNewMaster              { value 2001; }
            enum vrrpTrapAuthFailure            { value 2002; }
            enum tmnxVrrpIPListMismatch         { value 2003; }
            enum tmnxVrrpIPListMismatchClear    { value 2004; }
            enum tmnxVrrpMultipleOwners         { value 2005; }
            enum tmnxVrrpBecameBackup           { value 2006; }
            enum vrrpPacketDiscarded            { value 2007; }
            enum tmnxVrrpBfdIntfSessStateChgd   { value 2008; }
            enum vrrpTrapProtoError             { value 2009; }
            enum tVrrpBecameBackup              { value 2010; }
            enum tVrrpTrapNewMaster             { value 2011; }
            enum tVrrpIPListMismatch            { value 2012; }
            enum tVrrpIPListMismatchClear       { value 2013; }
            enum tVrrpMultipleOwners            { value 2014; }
            enum tVrrpPacketDiscarded           { value 2015; }
            enum tVrrpRouterAdvNotActivated     { value 2016; }
            enum tVrrpRouterAdvNotActivatedClear { value 2017; }
            enum tVrrpOperDownInvalidMac        { value 2018; }
            enum tVrrpOperDownInvalidMacClear   { value 2019; }
            enum tmnxVrrpOperDownInvalidMac     { value 2020; }
            enum tmnxVrrpOperDownInvalidMacClear { value 2021; }
        }
        description "Events for vrrp module.";
    }

    typedef vrtr-events {
        type enumeration {
            enum tmnxVRtrMidRouteTCA            { value 2001; }
            enum tmnxVRtrHighRouteTCA           { value 2002; }
            enum tmnxVRtrHighRouteCleared       { value 2003; }
            enum tmnxVRtrMcastMidRouteTCA       { value 2005; }
            enum tmnxVRtrMcastMaxRoutesTCA      { value 2006; }
            enum tmnxVRtrMcastMaxRoutesCleared  { value 2007; }
            enum tmnxVRtrMaxArpEntriesTCA       { value 2008; }
            enum tmnxVRtrMaxArpEntriesCleared   { value 2009; }
            enum tmnxVRtrMaxRoutes              { value 2011; }
            enum tmnxVRtrBfdMaxSessionOnSlot    { value 2013; }
            enum tmnxVRtrBfdPortTypeNotSupported { value 2014; }
            enum tmnxVRtrIPv6MidRouteTCA        { value 2016; }
            enum tmnxVRtrIPv6HighRouteTCA       { value 2017; }
            enum tmnxVRtrIPv6HighRouteCleared   { value 2018; }
            enum tmnxVRtrStaticRouteCPEStatus   { value 2019; }
            enum tmnxVRtrManagedRouteAddFailed  { value 2022; }
            enum tmnxVRtrFibOccupancyThreshold  { value 2023; }
            enum tmnxVRtrInetAddressAttachFailed { value 2024; }
            enum tmnxVRtrSingleSfmOverloadStateCh { value 2025; }
            enum tmnxVRtrGrtExportLimitReached  { value 2026; }
            enum tmnxVRtrGrtRoutesExpLimitDropped { value 2027; }
            enum tmnxVRtrIfLdpSyncTimerStart    { value 2029; }
            enum tmnxVRtrIfLdpSyncTimerStop     { value 2030; }
            enum tmnxVRtrGrtV6ExportLimitReached { value 2032; }
            enum tmnxVRtrGrtV6RoutesExpLimDropped { value 2033; }
            enum tmnxVRtrStaticRouteStatusChanged { value 2034; }
            enum tmnxVRtrBfdSessExtDown         { value 2061; }
            enum tmnxVRtrBfdSessExtUp           { value 2062; }
            enum tmnxVRtrBfdSessExtDeleted      { value 2063; }
            enum tmnxVRtrBfdSessExtProtChange   { value 2064; }
            enum tmnxVRtrBfdExtNoCpmNpResources { value 2065; }
            enum tmnxVRtrDnsFault               { value 2066; }
            enum tmnxVRtrMacAcctLimitReached    { value 2067; }
            enum tmnxVRtrMacAcctLimitCleared    { value 2068; }
            enum tmnxVRtrNgBfdSessDown          { value 2069; }
            enum tmnxVRtrNgBfdSessUp            { value 2070; }
            enum tmnxVRtrNgBfdSessDeleted       { value 2071; }
            enum tmnxVRtrNgBfdSessProtChange    { value 2072; }
            enum tmnxVRtrNgBfdNoCpmNpResources  { value 2073; }
            enum tmnxVRtrNHRvplsARPHighUsage    { value 2074; }
            enum tmnxVRtrNHRvplsARPExhaust      { value 2075; }
            enum tmnxVRtrNHRvplsARPHighUsageClr { value 2076; }
            enum tmnxVRtrArpLmt                 { value 2077; }
            enum tmnxVRtrArpThresholdExceeded   { value 2078; }
            enum tmnxVRtrIpv6NbrLmt             { value 2079; }
            enum tmnxVRtrIpv6NbrThresholdExceeded { value 2080; }
            enum tmnxVRtrIfIgnorePortState      { value 2081; }
            enum tmnxVRtrPdnAddrMismatch        { value 2082; }
            enum tmnxVRtrPdnAddrMismatchCleared { value 2083; }
            enum tmnxVRtrLeakExportLimitReached { value 2084; }
            enum tmnxVRtrLeakExportLimitDropped { value 2085; }
            enum tmnxVRtrDhcpClientStatusChanged { value 2086; }
            enum tmnxVRtrDhcp6ClientStatusChanged { value 2087; }
            enum tmnxVRtrNeDiscovered           { value 2088; }
            enum tmnxVRtrNeRemoved              { value 2089; }
            enum tmnxVRtrNeModified             { value 2090; }
            enum vRtrIfDhcpClRtStatusChanged    { value 2091; }
            enum vRtrIfDhcpClStateDnsChanged    { value 2092; }
            enum vRtrAutoCfgRaRtStatusChanged   { value 2093; }
            enum vRtrIfDhcp6ClStateDnsChanged   { value 2094; }
            enum tipNbrAllocFailed              { value 2095; }
            enum vRtrIfEthLoopbackStarted       { value 2096; }
            enum vRtrIfEthLoopbackStopped       { value 2097; }
            enum tmnxVRtrBfdExtNoFreeTxIntrvlSlot { value 2098; }
            enum tmnxVRtrFibVPNOccupancyThreshold { value 2099; }
            enum tmnxVRtrBfdMultiHopFpMismatch  { value 2100; }
            enum vRtrBgpInstanceError           { value 2101; }
        }
        description "Events for vrtr module.";
    }

    typedef radius-events {
        type enumeration {
            enum tmnxRadSrvPlcySrvOperStateCh   { value 2001; }
            enum tmnxRadRouteDownloadFailed     { value 2002; }
            enum tmnxRadAcctOnOngoing           { value 2003; }
        }
        description "Events for radius module.";
    }

    typedef wpp-events {
        type enumeration {
            enum tmnxWppPortalStatChanged       { value 2001; }
            enum tmnxWppHostAuthenticationFailed { value 2002; }
            enum tmnxWppPortalUnreachable       { value 2003; }
            enum tmnxWppPortalGroupStatChanged  { value 2004; }
            enum tmnxWppPGHostAuthFailed        { value 2005; }
        }
        description "Events for wpp module.";
    }

    typedef wlan-gw-events {
        type enumeration {
            enum tmnxWlanGwResrcProblemDetected { value 2001; }
            enum tmnxWlanGwResrcProblemCause    { value 2002; }
            enum tmnxWlanGwTuQosProblem         { value 2003; }
            enum tmnxWlanGwGrpOperStateChanged  { value 2004; }
            enum tmnxWlanGwIomActive            { value 2005; }
            enum tmnxWlanGwMgwConnected         { value 2006; }
            enum tmnxWlanGwMgwRestarted         { value 2007; }
            enum tmnxWlanGwNumMgwHi             { value 2008; }
            enum tmnxWlanGwMgwStateChanged      { value 2009; }
            enum tmnxWlanGwQosRadiusGtpMismatch { value 2010; }
            enum tmnxWlanGwSubIfRedActiveChanged { value 2011; }
            enum tmnxWlanGwDsmGtpTunnelSetupFail { value 2012; }
            enum tmnxWlanGwSubIfPmStartD6cFailed { value 2013; }
            enum tmnxWlanGwSubIfPmNewPlReqFailed { value 2014; }
            enum tmnxWlanGwSubIfPmAddNewPlFailed { value 2015; }
            enum tmnxWlanGwSubIfPmCrIntObjFailed { value 2016; }
            enum tmnxWlanGwSubIfPmPoolTimeout   { value 2017; }
            enum tmnxWlanGwSubIfPmPoolUsageLow  { value 2018; }
            enum tmnxWlanGwSubIfPmLsQryRtryFailed { value 2019; }
            enum tmnxWlanGwGtpMessageDropped    { value 2020; }
            enum tmnxWlanGwSubIfPmPoolPartialUse { value 2021; }
            enum tmnxWlanGwBdCreated            { value 2022; }
            enum tmnxWlanGwBdDeleted            { value 2023; }
            enum tmnxWlanGwUeCreationFail       { value 2024; }
            enum tmnxWlanGwUeReplacement        { value 2025; }
            enum tmnxWlanGwGrpMemberUsageHigh   { value 2026; }
        }
        description "Events for wlan-gw module.";
    }

    typedef dot1x-events {
        type enumeration {
            enum alxDot1xHostAuthEvent          { value 2001; }
        }
        description "Events for the DOT1X module.";
    }

    typedef dynsvc-events {
        type enumeration {
            enum tmnxDynSvcSapFailed            { value 2001; }
        }
        description "Events for dynsvc module.";
    }

    typedef mpls-tp-events {
        type enumeration {
            enum vRtrMplsTpLspRevertMismatchAlarm { value 2001; }
            enum vRtrMplsTpLspRevertMismatchClear { value 2002; }
            enum vRtrMplsTpLspPtTypeMismatchAlarm { value 2003; }
            enum vRtrMplsTpLspPtTypeMismatchClear { value 2004; }
            enum vRtrMplsTpLspActivePathUp      { value 2005; }
            enum vRtrMplsTpLspActivePathChange  { value 2006; }
        }
        description "Events for mpls-tp module.";
    }

    typedef bfd-events {
        type enumeration {
            enum tmnxBfdOnLspSessDown           { value 2001; }
            enum tmnxBfdOnLspSessUp             { value 2002; }
            enum tmnxBfdOnLspSessDeleted        { value 2003; }
            enum tmnxBfdOnLspSessProtChange     { value 2004; }
            enum tmnxBfdOnLspSessNoCpmNpResources { value 2005; }
            enum tmnxBfdOnLspSessNoTailResources { value 2006; }
            enum tmnxBfdOnLspExtSessDown        { value 2007; }
            enum tmnxBfdOnLspExtSessUp          { value 2008; }
            enum tmnxBfdOnLspExtSessDeleted     { value 2009; }
            enum tmnxBfdOnLspExtSessProtChange  { value 2010; }
            enum tmnxBfdOnLspExtSessNoCpmNpResrcs { value 2011; }
        }
        description "Events for bfd module.";
    }

    typedef ripng-events {
        type enumeration {
            enum tmnxRipNgPacketDiscarded       { value 2001; }
            enum tmnxRipNgAuthTypeMismatch      { value 2002; }
            enum tmnxRipNgAuthFailure           { value 2003; }
            enum tmnxRipNgInstShuttingDown      { value 2004; }
            enum tmnxRipNgInstRestarted         { value 2005; }
            enum tmnxRipNgInstExpLmtReached     { value 2006; }
            enum tmnxRipNgInstExpLmtWarning     { value 2007; }
            enum tmnxRipNgInstRtsExpLmtDropped  { value 2008; }
            enum tmnxRipNgIfUcastAddrNotUsed    { value 2009; }
            enum tmnxRipNgPeerBfdDown           { value 2010; }
        }
        description "Events for RIPng module.";
    }

    typedef openflow-events {
        type enumeration {
            enum tmnxOFFlowEntryInsertFailed    { value 2001; }
        }
        description "Events for openflow module.";
    }

    typedef sflow-events {
        type enumeration {
            enum none                           { value 0; }
            enum tmnxSflowCpEntrySampling       { value 2001; }
            enum tmnxSflowPacketTxFailure       { value 2002; }
        }
        description "Events for sflow module.";
    }

    typedef rpki-events {
        type enumeration {
            enum tmnxRpkiNotifySession          { value 2001; }
            enum tmnxRpkiStaleTimerExpiry       { value 2002; }
        }
        description "Events for rpki module.";
    }

    typedef ldap-events {
        type enumeration {
            enum tmnxLdapOperStateChange        { value 2001; }
            enum tmnxLdapServerOperStateChange  { value 2002; }
        }
        description "Events for ldap module.";
    }

    typedef pppoe-clnt-events {
        type enumeration {
            enum tmnxPppoeClientSetupFailure    { value 2001; }
            enum tmnxPppoeClientEchoTimeout     { value 2004; }
            enum tmnxPppoeClientNcpFailure      { value 2005; }
        }
        description "Events for pppoe_clnt module.";
    }

    typedef adp-events {
        type enumeration {
            enum tmnxDiscoveryEndNotify         { value 2005; }
            enum tmnxDiscoveryCellularReq       { value 2050; }
        }
        description "Events for adp module.";
    }

    typedef satellite-events {
        type enumeration {
            enum tmnxSatelliteOperStateChange   { value 2001; }
            enum tmnxSatSyncIfTimRefSwitch      { value 2002; }
            enum tmnxSatSyncIfTimSystemQuality  { value 2003; }
            enum tmnxSatSyncIfTimRef1Quality    { value 2004; }
            enum tmnxSatSyncIfTimRef2Quality    { value 2005; }
            enum tmnxSatSyncIfTimHoldover       { value 2006; }
            enum tmnxSatSyncIfTimHoldoverClear  { value 2007; }
            enum tmnxSatSyncIfTimRef1Alarm      { value 2008; }
            enum tmnxSatSyncIfTimRef1AlarmClear { value 2009; }
            enum tmnxSatSyncIfTimRef2Alarm      { value 2010; }
            enum tmnxSatSyncIfTimRef2AlarmClear { value 2011; }
            enum tmnxSatLocalForwardStateChg    { value 2016; }
            enum tmnxSatLocalForwardSapStateChg { value 2017; }
        }
        description "Events for satellite module.";
    }

    typedef mgmt-core-events {
        type enumeration {
            enum none                           { value 0; }
            enum mdConfigChange                 { value 2001; }
            enum mdOcConfigChange               { value 2002; }
            enum mdBofConfigChange              { value 2003; }
            enum mdDebugConfigChange            { value 2004; }
            enum asyncOperationStatusChange     { value 2005; }
            enum syncOperationStatusChange      { value 2006; }
            enum mdAutomaticRollbackFailed      { value 2007; }
            enum mdRollbackFailed               { value 2008; }
        }
        description "Events for mgmt-core module.";
    }

    typedef dhcp-events {
        type enumeration {
            enum svcDHCPLseStateRestoreProblem  { value 2001; }
            enum sapDHCPLeaseEntriesExceeded    { value 2002; }
            enum sapDHCPLseStateOverride        { value 2003; }
            enum sapDHCPSuspiciousPcktRcvd      { value 2004; }
            enum sapDHCPLseStatePopulateErr     { value 2005; }
            enum sdpBindDHCPLeaseEntriesExceeded { value 2006; }
            enum sdpBindDHCPLseStateOverride    { value 2007; }
            enum sdpBindDHCPSuspiciousPcktRcvd  { value 2008; }
            enum sdpBindDHCPLseStatePopulateErr { value 2009; }
            enum tmnxVRtrDHCPSuspiciousPcktRcvd { value 2010; }
            enum sapStaticHostDynMacConflict    { value 2012; }
            enum sapDHCPProxyServerError        { value 2013; }
            enum tmnxVRtrDHCPIfLseStatesExceeded { value 2014; }
            enum sdpBindDHCPProxyServerError    { value 2016; }
            enum tmnxVRtrDHCP6RelayLseStExceeded { value 2020; }
            enum tmnxVRtrDHCP6ServerLseStExceeded { value 2021; }
            enum tmnxVRtrDHCP6LseStateOverride  { value 2022; }
            enum tmnxVRtrDHCP6RelayReplyStripUni { value 2023; }
            enum tmnxVRtrDHCP6IllegalClientAddr { value 2024; }
            enum tmnxVRtrDHCP6AssignedIllegSubnet { value 2025; }
            enum tmnxVRtrDHCP6ClientMacUnresolved { value 2026; }
            enum sapDHCPLseStateMobilityError   { value 2027; }
            enum sdpBindDHCPLseStateMobilityErr { value 2028; }
            enum svcDHCPMiscellaneousProblem    { value 2029; }
            enum sapStatHost6DynMacConflict     { value 2030; }
        }
        description "Events for dhcp module.";
    }

    typedef tls-events {
        type enumeration {
            enum tmnxTlsInitiateSession         { value 2001; }
            enum tmnxTlsTermination             { value 2002; }
            enum tmnxTlsFailure                 { value 2003; }
        }
        description "Events for tls module.";
    }

    typedef vrtr-name {
        type string {
            length "1..32";
        }
        default "Base";
        description
            "Specifies a virtual router instance as a string (unlike vrtr-id).
             'Base', 'management' or a service-id can be specified.";
    }

    typedef log-event-id {
        type uint32;
        description
            "Unique arbitrary identifier for indexing event type entries within
             an event generator application.";
    }

    typedef snmp-trap-group-name {
        type string {
            length "1..32";
            pattern "(([1-9]|[1-9][0-9]|100)|([^\\s0-9_])|([^\\s0-9_]\\P{C}*[^\\s])|([0-9]+[^\\s0-9])|([0-9]+[^0-9]\\P{C}*[^\\s]))" {
                error-message "must be numeric in range 1..100, or alphanumeric not starting with underscore and without trailing spaces";
            }
        }
        description "The value of snmp-trap-group name specifies an event stream log associated with snmp-trap-group";
    }

    typedef file-policy-name {
        type string {
            length "1..64";
            pattern "(([1-9]|[1-9][0-9])|([^\\s0-9_])|([^\\s0-9_]\\P{C}*[^\\s])|([0-9]+[^\\s0-9])|([0-9]+[^0-9]\\P{C}*[^\\s]))" {
                error-message "must be numeric in range 1..99, or alphanumeric not starting with underscore and without trailing spaces";
            }
        }
        description "The value of file-policy-name to be used when creating a log or accounting file";
    }

    typedef svc-vprn-snmp-trap-group-name {
        type string {
            length "1..17";
            pattern "(([1-9]|[1-9][0-9]|100)|([^\\s0-9_])|([^\\s0-9_]\\P{C}*[^\\s])|([0-9]+[^\\s0-9])|([0-9]+[^0-9]\\P{C}*[^\\s]))" {
                error-message "must be numeric in range 1..100, or alphanumeric not starting with underscore and without trailing spaces";
            }
        }
        description "The value of snmp-trap-group name specifies an event stream log associated with snmp-trap-group";
    }

    typedef log-name {
        type string {
            length "1..64";
            pattern "(([1-9]|[1-9][0-9]|10[01])|([^\\s0-9_])|([^\\s0-9_]\\P{C}*[^\\s])|([0-9]+[^\\s0-9])|([0-9]+[^0-9]\\P{C}*[^\\s]))" {
                error-message "must be numeric in range 1..101, or alphanumeric not starting with underscore and without trailing spaces";
            }
        }
        description "The value of log name specifies an event stream log.";
    }

    typedef log-syslog-name {
        type string {
            length "1..64";
            pattern "(([1-9]|10)|([^\\s0-9_])|([^\\s0-9_]\\P{C}*[^\\s])|([0-9]+[^\\s0-9])|([0-9]+[^0-9]\\P{C}*[^\\s]))" {
                error-message "must be numeric in range 1..10, or alphanumeric not starting with underscore and without trailing spaces";
            }
        }
        description "The value of log name specifies an event stream log.";
    }

    typedef log-vprn-syslog-name {
        type string {
            length "1..64";
            pattern "(([1-9]|[1-2][0-9]|30)|([^\\s0-9_])|([^\\s0-9_]\\P{C}*[^\\s])|([0-9]+[^\\s0-9])|([0-9]+[^0-9]\\P{C}*[^\\s]))" {
                error-message "must be numeric in range 1..30, or alphanumeric not starting with underscore and without trailing spaces";
            }
        }
        description "The value of log name specifies an event stream log.";
    }

    typedef li-log-name {
        type string {
            length "1..64";
            pattern "(([1-9]|[1-9][0-9]|100)|([^\\s0-9_])|([^\\s0-9_]\\P{C}*[^\\s])|([0-9]+[^\\s0-9])|([0-9]+[^0-9]\\P{C}*[^\\s]))" {
                error-message "must be numeric in range 1..100, or alphanumeric not starting with underscore and without trailing spaces";
            }
        }
        description "The value of log name specifies an event stream log.";
    }

    typedef log-filter-name {
        type string {
            length "1..64";
            pattern "(([1-9]|[1-9][0-9]|[1-9][0-9][0-9]|1[0-4][0-9][0-9]|1500)|([^\\s0-9_])|([^\\s0-9_]\\P{C}*[^\\s])|([0-9]+[^\\s0-9])|([0-9]+[^0-9]\\P{C}*[^\\s]))" {
                error-message "must be numeric in range 1..1500, or alphanumeric not starting with underscore and without trailing spaces";
            }
        }
        description "The value of log name specifies an event log filter.";
    }

    typedef log-filter-entry-name {
        type string {
            length "1..64";
            pattern "(([1-9]|[1-9][0-9]|[1-9][0-9][0-9])|([^\\s0-9_])|([^\\s0-9_]\\P{C}*[^\\s])|([0-9]+[^\\s0-9])|([0-9]+[^0-9]\\P{C}*[^\\s]))" {
                error-message "must be numeric in range 1..999, or alphanumeric not starting with underscore and without trailing spaces";
            }
        }
        description "The value of log name specifies an event log filter.";
    }

}
