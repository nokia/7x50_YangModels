module nokia-sr-openconfig-messages-deviations {

    namespace "urn:nokia.com:sros:ns:yang:sr:openconfig-messages-deviations";

    prefix "nokia-oc-messages-devs";

    import nokia-sros-yang-extensions     { prefix "sros-ext"; }
    import openconfig-messages            { prefix "oc-messages"; }

    sros-ext:sros-major-release "rel24";
    organization "Nokia";
    contact
        "Nokia SR OS Support
         Web: <http://www.nokia.com>";
    description
        "This module contains the list of deviations against the openconfig-messages
         module for the Nokia SR OS based routers.

         Copyright 2016 Nokia. All rights reserved. Reproduction of this document
         is authorized on the condition that the foregoing copyright notice is included.

         This nokia-sr-openconfig-messages-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2018-08-13";

    deviation /oc-messages:messages {
        deviate not-supported;
    }

}
