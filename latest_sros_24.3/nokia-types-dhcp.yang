module nokia-types-dhcp {

    yang-version "1.1";

    namespace "urn:nokia.com:sros:ns:yang:sr:types-dhcp";

    prefix "types-dhcp";

    import nokia-sros-yang-extensions     { prefix "sros-ext"; }

    sros-ext:sros-major-release "rel24";
    organization "Nokia";
    contact
        "Nokia SR OS Support
         Web: <http://www.nokia.com>";
    description
        "Common DHCP data types used in the SR OS management system.

         Copyright 2016 Nokia. All rights reserved. Reproduction of this document
         is authorized on the condition that the foregoing copyright notice is included.

         This nokia-types-dhcp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2019-03-27";

    typedef dhcp-server-client-type {
        type enumeration {
            enum dhcp                           { value 0; }
            enum ppp                            { value 1; }
            enum ipoe                           { value 2; }
            enum ipsec                          { value 3; }
        }
        description
            "Type of client of a DHCP server.

                dhcp  : CPE is a DHCP client
                ppp   : CPE is a PPP client (IPv4)
                ipoe  : CPE is an IPoE client (IPv6)
                ipsec : CPE is an IPSEC tunnel";
    }

    typedef dhcp-server-internal-client-type {
        type enumeration {
            enum ipoe-wan                       { value 1; }
            enum ipoe-slaac                     { value 2; }
            enum ppp                            { value 3; }
            enum ppp-slaac                      { value 4; }
            enum ipsec                          { value 5; }
        }
        description "Type of internal client";
    }

    typedef failover-control-type {
        type enumeration {
            enum local                          { value 1; }
            enum remote                         { value 2; }
            enum access-driven                  { value 3; }
        }
        description
            "DHCP server failover control type.

                local         : local system is in control
                remote        : remote system is in control
                access-driven : system is decided by access mechanism";
    }

    typedef dhcp6-duid-hardware-type {
        type union {
            type uint32;
            type enumeration {
                enum ethernet                       { value 1; }
                enum experimental-ethernet          { value 2; }
                enum amateur-radio                  { value 3; }
                enum proteon-pronet-token-ring      { value 4; }
                enum chaos                          { value 5; }
                enum ieee-802-network               { value 6; }
                enum arcnet                         { value 7; }
                enum hyperchannel                   { value 8; }
                enum lanstar                        { value 9; }
                enum autonet-short-address          { value 10; }
                enum localtalk                      { value 11; }
                enum localnet                       { value 12; }
                enum ultra-link                     { value 13; }
                enum smds                           { value 14; }
                enum frame-relay                    { value 15; }
                enum atm-jxb2                       { value 16; }
                enum hdlc                           { value 17; }
                enum fibre-channel                  { value 18; }
                enum atm-rfc2225                    { value 19; }
                enum serial-line                    { value 20; }
                enum atm-mike-burrows               { value 21; }
                enum mil-std-188-220                { value 22; }
                enum metricom                       { value 23; }
                enum ieee-1394                      { value 24; }
                enum mapos                          { value 25; }
                enum twinaxial                      { value 26; }
                enum eui-64                         { value 27; }
                enum hiparp                         { value 28; }
                enum ip-and-arp-over-iso-7816-3     { value 29; }
                enum arpsec                         { value 30; }
                enum ipsec-tunnel                   { value 31; }
                enum infiniband                     { value 32; }
                enum common-air-interface           { value 33; }
                enum wiegand-interface              { value 34; }
                enum pure-ip                        { value 35; }
                enum hw-exp1                        { value 36; }
                enum hfi                            { value 37; }
                enum hw-exp2                        { value 256; }
                enum aethernet                      { value 257; }
            }
        }
        description "Hardware type";
    }

}
