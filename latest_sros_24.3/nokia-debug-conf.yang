module nokia-debug-conf {

    yang-version "1.1";

    namespace "urn:nokia.com:sros:ns:yang:sr:debug-conf";

    prefix "debug-conf";

    import ietf-inet-types                { prefix "inet"; }
    import nokia-sros-yang-extensions     { prefix "sros-ext"; }
    import nokia-types-diameter           { prefix "types-diam"; }
    import nokia-types-igmp               { prefix "types-igmp"; }
    import nokia-types-igp                { prefix "types-igp"; }
    import nokia-types-isa                { prefix "types-isa"; }
    import nokia-types-isis               { prefix "types-isis"; }
    import nokia-types-l2tp               { prefix "types-l2tp"; }
    import nokia-types-radius             { prefix "types-radius"; }
    import nokia-types-router             { prefix "types-router"; }
    import nokia-types-security           { prefix "types-security"; }
    import nokia-types-services           { prefix "types-services"; }
    import nokia-types-sros               { prefix "types-sros"; }
    import nokia-types-subscriber-mgmt    { prefix "types-submgt"; }

    sros-ext:sros-major-release "rel24";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-debug-conf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-01-31";

    container debug {
        description "Configure application or protocol tracing";

        container aaa {
            description "Enter the aaa context";

            container diameter {
                description "Enter the diameter context";

                container application {
                    description "Enter the application context";

                    leaf failures {
                        type boolean;
                        default "false";
                        description "Debug Diameter application failures";
                    }

                    list policy {
                        key "name";
                        max-elements 32;
                        description "Enter the policy list instance";

                        leaf name {
                            type types-sros:named-item;
                            description "Diameter application policy name";
                        }

                        leaf failures {
                            type boolean;
                            default "true";
                            description "Debug Diameter application failures";
                        }

                        leaf messages {
                            type boolean;
                            default "false";
                            description "Debug Diameter application messages";
                        }

                    } // list policy

                } // container application

                list node {
                    key "origin-host";
                    max-elements 32;
                    description "Enter the node list instance";

                    leaf origin-host {
                        type types-diam:diam-fqdn;
                        description "Origin host of the Diameter node";
                    }

                    leaf failures {
                        type boolean;
                        default "true";
                        description "Debug Diameter node failures";
                    }

                    leaf relayed-messages {
                        type boolean;
                        default "false";
                        description "Debug relayed Diameter messages";
                    }

                    list peer {
                        key "index";
                        description "Enter the peer list instance";

                        leaf index {
                            type uint32 {
                                range "1..5";
                            }
                            description "Index of the peer in the Diameter node";
                        }

                        leaf failures {
                            type boolean;
                            default "true";
                            description "Debug Diameter peer failures";
                        }

                        leaf messages {
                            type boolean;
                            default "false";
                            description "Debug Diameter peer messages";
                        }

                    } // list peer

                } // list node

            } // container diameter

        } // container aaa

        container call-trace {
            description "Enter the call-trace context";

            container ipoe {
                description "Enter the ipoe context";

                list trace {
                    key "name";
                    max-elements 50;
                    description "Enter the trace list instance";

                    leaf name {
                        type string {
                            length "1..32";
                        }
                        description "Unique trace name";
                    }

                    leaf sap {
                        type types-sros:sap;
                        sros-ext:immutable;
                        description "SAP ID of the sessions to trace";
                    }

                    leaf mac {
                        type string {
                            length "1..17";
                        }
                        sros-ext:immutable;
                        description "MAC address of the sessions to trace";
                    }

                    leaf profile {
                        type types-sros:named-item;
                        sros-ext:immutable;
                        mandatory true;
                        description "Call trace profile applied for the trace";
                    }

                    leaf trace-existing-sessions {
                        type boolean;
                        sros-ext:immutable;
                        default "false";
                        description "Enable call trace for existing sessions";
                    }

                    leaf max-jobs {
                        type uint8 {
                            range "1..50";
                        }
                        sros-ext:immutable;
                        default "1";
                        description "Maximum number of trace jobs";
                    }

                    choice relay-agent-suboption {
                        case circuit-id {

                            leaf circuit-id {
                                type string {
                                    length "1..255";
                                }
                                sros-ext:immutable;
                                description "Circuit ID of the sessions to trace";
                            }

                        }
                        case remote-id {

                            leaf remote-id {
                                type string {
                                    length "1..255";
                                }
                                sros-ext:immutable;
                                description "Remote ID of the sessions to trace";
                            }

                        }
                    }
                } // list trace

            } // container ipoe

            container pppoe {
                description "Enter the pppoe context";

                list trace {
                    key "name";
                    max-elements 50;
                    description "Enter the trace list instance";

                    leaf name {
                        type string {
                            length "1..32";
                        }
                        description "Unique trace name";
                    }

                    leaf sap {
                        type types-sros:sap;
                        sros-ext:immutable;
                        description "SAP ID of the sessions to trace";
                    }

                    leaf mac {
                        type string {
                            length "1..17";
                        }
                        sros-ext:immutable;
                        description "MAC address of the sessions to trace";
                    }

                    leaf circuit-id {
                        type string {
                            length "1..255";
                        }
                        sros-ext:immutable;
                        description "Circuit ID of the sessions to trace";
                    }

                    leaf remote-id {
                        type string {
                            length "1..255";
                        }
                        sros-ext:immutable;
                        description "Remote ID of the sessions to trace";
                    }

                    leaf user-name {
                        type string {
                            length "1..253";
                            pattern "[^*]+\\*|\\*[^*]+|\\*[^*]+\\*|[^*]+" {
                                error-message "Only one wildcard at start and/or end is allowed.";
                            }
                        }
                        sros-ext:immutable;
                        description "PPPoE username of the sessions to trace";
                    }

                    leaf profile {
                        type types-sros:named-item;
                        sros-ext:immutable;
                        mandatory true;
                        description "Call trace profile applied for the trace";
                    }

                    leaf trace-existing-sessions {
                        type boolean;
                        sros-ext:immutable;
                        default "false";
                        description "Enable call trace for existing sessions";
                    }

                    leaf max-jobs {
                        type uint8 {
                            range "1..50";
                        }
                        sros-ext:immutable;
                        default "1";
                        description "Maximum number of trace jobs";
                    }

                } // list trace

            } // container pppoe

            container wlan-gw {
                description "Enter the wlan-gw context";

                list ue {
                    key "name";
                    max-elements 50;
                    description "Enter the ue list instance";

                    leaf name {
                        type string {
                            length "1..32";
                        }
                        description "Unique trace name";
                    }

                    leaf mac {
                        type types-sros:mac-address;
                        sros-ext:immutable;
                        mandatory true;
                        description "MAC address of the sessions to trace";
                    }

                    leaf profile {
                        type types-sros:named-item;
                        sros-ext:immutable;
                        mandatory true;
                        description "Call trace profile applied for the trace";
                    }

                } // list ue

            } // container wlan-gw

        } // container call-trace

        container certificate {
            description "Enter the certificate context";

            list auto-certificate-update {
                key "filename";
                max-elements 256;
                description "Add a list entry for auto-certificate-update";

                leaf filename {
                    type types-security:pki-file-name;
                    description "Certificate filename";
                }

            } // list auto-certificate-update

            list auto-crl-update {
                key "ca-profile-name";
                max-elements 128;
                description "Add a list entry for auto-crl-update";

                leaf ca-profile-name {
                    type types-sros:named-item;
                    description "Certificate Authority (CA) profile name";
                }

            } // list auto-crl-update

            list cmpv2 {
                key "ca-profile-name";
                max-elements 128;
                description "Add a list entry for cmpv2";

                leaf ca-profile-name {
                    type types-sros:named-item;
                    description "CA profile name";
                }

            } // list cmpv2

            list est {
                key "est-profile-name";
                max-elements 128;
                description "Add a list entry for est";

                leaf est-profile-name {
                    type types-sros:named-item;
                    description "EST profile name";
                }

            } // list est

            list ocsp {
                key "ca-profile-name";
                max-elements 128;
                description "Add a list entry for ocsp";

                leaf ca-profile-name {
                    type types-sros:named-item;
                    description "CA profile name";
                }

            } // list ocsp

        } // container certificate


        container ipsec {
            description "Enter the ipsec context";

            list tunnel {
                key "name";
                max-elements 16;
                description "Enter the tunnel list instance";

                leaf name {
                    type types-sros:named-item;
                    description "IPsec tunnel name";
                }

                leaf detail {
                    type boolean;
                    default "false";
                    description "Display detailed debug information";
                }

                leaf suppress-dpd-debug {
                    type boolean;
                    default "false";
                    description "Display debug output without DPD information";
                }

                leaf display-keys {
                    type boolean;
                    default "false";
                    description "Display keys in the debug output";
                }

            } // list tunnel

            container transport-mode {
                description "Enter the transport-mode context";

                list ip-tunnel {
                    key "name";
                    max-elements 16;
                    description "Enter the ip-tunnel list instance";

                    leaf name {
                        type types-sros:interface-name;
                        description "IPsec transport mode IP tunnel name";
                    }

                    leaf detail {
                        type boolean;
                        default "false";
                        description "Display detailed debug information";
                    }

                    leaf suppress-dpd-debug {
                        type boolean;
                        default "false";
                        description "Display debug output without DPD information";
                    }

                    leaf display-keys {
                        type boolean;
                        default "false";
                        description "Display keys in the debug output";
                    }

                } // list ip-tunnel

            } // container transport-mode

            list gateway {
                key "name";
                max-elements 16;
                description "Enter the gateway list instance";

                leaf name {
                    type types-sros:named-item;
                    description "IPsec gateway name";
                }

                list tunnel {
                    key "ip-address port";
                    max-elements 16;
                    description "Enter the tunnel list instance";

                    leaf ip-address {
                        type types-sros:ip-address;
                        description "Gateway tunnel remote IP address";
                    }

                    leaf port {
                        type types-sros:tcp-udp-port-non-zero;
                        description "Gateway tunnel remote port";
                    }

                    leaf detail {
                        type boolean;
                        default "false";
                        description "Display detailed debug information";
                    }

                    leaf suppress-dpd-debug {
                        type boolean;
                        default "false";
                        description "Display debug output without DPD information";
                    }

                    leaf display-keys {
                        type boolean;
                        default "false";
                        description "Display keys in the debug output";
                    }

                } // list tunnel

                list tunnel-nat {
                    key "ip-address port pre-nat-ip-address pre-nat-port";
                    max-elements 16;
                    description "Enter the tunnel-nat list instance";

                    leaf ip-address {
                        type types-sros:ipv4-unicast-address;
                        description "Gateway tunnel remote IP address";
                    }

                    leaf port {
                        type types-sros:tcp-udp-port-non-zero;
                        description "Gateway tunnel remote port";
                    }

                    leaf pre-nat-ip-address {
                        type types-sros:ipv4-unicast-address;
                        description "Gateway tunnel peer pre-NAT IP address";
                    }

                    leaf pre-nat-port {
                        type types-sros:tcp-udp-port-non-zero;
                        description "Gateway tunnel peer pre-NAT port";
                    }

                    leaf detail {
                        type boolean;
                        default "false";
                        description "Display detailed debug information";
                    }

                    leaf suppress-dpd-debug {
                        type boolean;
                        default "false";
                        description "Display debug output without DPD information";
                    }

                    leaf display-keys {
                        type boolean;
                        default "false";
                        description "Display keys in the debug output";
                    }

                } // list tunnel-nat

                list tunnel-subnet {
                    key "ip-prefix port";
                    max-elements 16;
                    description "Enter the tunnel-subnet list instance";

                    leaf ip-prefix {
                        type types-sros:ip-prefix;
                        description "Gateway tunnel remote IP prefix";
                    }

                    leaf port {
                        type union {
                            type enumeration {
                                enum any                            { value 0; }
                            }
                            type types-sros:tcp-udp-port-non-zero;
                        }
                        description "Gateway tunnel remote port";
                    }

                    leaf detail {
                        type boolean;
                        default "false";
                        description "Display detailed debug information";
                    }

                    leaf suppress-dpd-debug {
                        type boolean;
                        default "false";
                        description "Display debug output without DPD information";
                    }

                    leaf display-keys {
                        type boolean;
                        default "false";
                        description "Display keys in the debug output";
                    }

                } // list tunnel-subnet

            } // list gateway

            list client-db {
                key "name";
                max-elements 1000;
                description "Add a list entry for client-db";

                leaf name {
                    type types-sros:named-item;
                    description "IPsec client database name";
                }

            } // list client-db

            list certificate {
                key "filename";
                max-elements 200;
                description "Add a list entry for certificate";

                leaf filename {
                    type types-security:pki-file-name;
                    description "Imported IPsec certificate filename";
                }

            } // list certificate

        } // container ipsec

        container l2tp {
            description "Enter the l2tp context";

            leaf predictable-id-assignment {
                type boolean;
                default "false";
                description "Enable predictable tunnel and session ID assignment";
            }

        } // container l2tp

        list lag {
            key "lag-name";
            description "Enter the lag list instance";

            leaf lag-name {
                type types-sros:lag-interface;
                description "LAG name";
            }

            leaf state-machine {
                type boolean;
                default "false";
                description "Enable debugging for state-machine changes";
            }

            leaf lacp-packets {
                type boolean;
                default "false";
                description "Enable debugging for LACP packets";
            }

            leaf config {
                type boolean;
                default "false";
                description "Enable debugging for configuration changes";
            }

            leaf redundancy {
                type boolean;
                default "false";
                description "Enable debugging for redundancy";
            }

            leaf iom-updates {
                type boolean;
                default "false";
                description "Enable debugging for IOM updates";
            }

            leaf port-states {
                type boolean;
                default "false";
                description "Enable debugging for port-state changes";
            }

            leaf timers {
                type boolean;
                default "false";
                description "Enable debugging for timers";
            }

            leaf selection-logic {
                type boolean;
                default "false";
                description "Enable debugging for selection logic";
            }

            leaf multi-chassis {
                type boolean;
                default "false";
                description "Enable debugging for multi-chassis LAG";
            }

            leaf multi-chassis-packets {
                type boolean;
                default "false";
                description "Enable debugging for multi-chassis packets";
            }

            leaf bfd {
                type boolean;
                default "false";
                description "Enable debugging for BFD";
            }

            list port {
                key "port-id";
                description "Enter the port list instance";

                leaf port-id {
                    type types-sros:port;
                    description "Unique identifier for the port in the LAG";
                }

                leaf state-machine {
                    type boolean;
                    default "false";
                    description "Enable debugging for state-machine changes";
                }

                leaf lacp-packets {
                    type boolean;
                    default "false";
                    description "Enable debugging for LACP packets";
                }

                leaf config {
                    type boolean;
                    default "false";
                    description "Enable debugging for configuration changes";
                }

                leaf redundancy {
                    type boolean;
                    default "false";
                    description "Enable debugging for redundancy";
                }

                leaf port-states {
                    type boolean;
                    default "false";
                    description "Enable debugging for port-state changes";
                }

                leaf timers {
                    type boolean;
                    default "false";
                    description "Enable debugging for timers";
                }

                leaf selection-logic {
                    type boolean;
                    default "false";
                    description "Enable debugging for selection logic";
                }

                leaf multi-chassis {
                    type boolean;
                    default "false";
                    description "Enable debugging for multi-chassis LAG";
                }

                leaf bfd {
                    type boolean;
                    default "false";
                    description "Enable debugging for BFD";
                }

            } // list port

        } // list lag

        container nat {
            description "Enter the nat context";

            container large-scale {
                description "Enter the large-scale context";

                container nat44 {
                    description "Enter the nat44 context";

                    list subscriber {
                        key "inside-router ip-address";
                        max-elements 16;
                        description "Add a list entry for subscriber";

                        leaf inside-router {
                            type string;
                            description "Inside router instance name";
                        }

                        leaf ip-address {
                            type types-sros:ipv4-unicast-address;
                            description "Inside IPv4 address of the NAT44 subscriber";
                        }

                    } // list subscriber

                } // container nat44

                container dual-stack-lite {
                    description "Enter the dual-stack-lite context";

                    list subscriber {
                        key "inside-router b4-address";
                        max-elements 16;
                        description "Add a list entry for subscriber";

                        leaf inside-router {
                            type string;
                            description "Inside router instance name";
                        }

                        leaf b4-address {
                            type types-sros:ipv6-prefix;
                            description "IPv6 B4 address of the DS-Lite subscriber";
                        }

                    } // list subscriber

                } // container dual-stack-lite

                container nat64 {
                    description "Enter the nat64 context";

                    list subscriber {
                        key "inside-router ipv6-prefix";
                        max-elements 16;
                        description "Add a list entry for subscriber";

                        leaf inside-router {
                            type string;
                            description "Inside router instance name";
                        }

                        leaf ipv6-prefix {
                            type types-sros:ipv6-prefix;
                            description "NAT64 IPv6 prefix of the subscriber";
                        }

                    } // list subscriber

                } // container nat64

            } // container large-scale

            container l2-aware {
                description "Enter the l2-aware context";

                list subscriber {
                    key "subscriber-id";
                    max-elements 16;
                    description "Add a list entry for subscriber";

                    leaf subscriber-id {
                        type types-submgt:subscriber-id;
                        description "L2-aware subscriber ID";
                    }

                } // list subscriber

                container upnp {
                    description "Enter the upnp context";

                    list subscriber {
                        key "subscriber-id";
                        max-elements 10;
                        description "Enter the subscriber list instance";

                        leaf subscriber-id {
                            type types-submgt:subscriber-id;
                            description "L2-aware subscriber ID";
                        }

                        leaf events {
                            type boolean;
                            default "true";
                            description "Enable UPnP event debugging";
                        }

                        container packets {
                            presence "Enable the packets context";
                            description "Enable the packets context";

                            leaf detail {
                                type boolean;
                                default "false";
                                description "Include IP, UDP, and TCP headers in UPnP packet debug";
                            }

                        } // container packets

                    } // list subscriber

                } // container upnp

            } // container l2-aware

            container nat-import {
                description "Enter the nat-import context";

                list route {
                    key "ip-address inside-router";
                    max-elements 32;
                    description "Add a list entry for route";

                    leaf ip-address {
                        type union {
                            type types-sros:ipv4-unicast-address;
                            type enumeration {
                                enum any                            { value 0; }
                            }
                        }
                        description "IPv4 address of imported route, or any";
                    }

                    leaf inside-router {
                        type string;
                        description "Router name or VPRN service name, or any";
                    }

                } // list route

            } // container nat-import

            container pcp {
                description "Enter the pcp context";

                list router {
                    key "router-instance";
                    max-elements 8;
                    description "Enter the router list instance";

                    leaf router-instance {
                        type string;
                        description "Inside router instance name";
                    }

                    list server {
                        key "name";
                        max-elements 8;
                        description "Enter the server list instance";

                        leaf name {
                            type types-sros:named-item;
                            description "PCP server name";
                        }

                        container packets {
                            description "Enter the packets context";

                            leaf detail {
                                type boolean;
                                default "false";
                                description "Enable the detailed PCP packet debug output";
                            }

                            leaf direction {
                                type enumeration {
                                    enum ingress                        { value 0; }
                                    enum egress                         { value 1; }
                                    enum both                           { value 2; }
                                }
                                default "ingress";
                                description "Direction of the PCP packet debugging";
                            }

                        } // container packets

                    } // list server

                } // list router

            } // container pcp

        } // container nat

        list router {
            key "router-instance";
            description "Enter the router list instance";

            leaf router-instance {
                type string;
                description "Router name or VPRN service name";
            }

            container ip {
                description "Enter the ip context";

                container neighbor {
                    description "Enter the neighbor context";

                    list interface {
                        key "interface-name";
                        description "Enter the interface list instance";

                        leaf interface-name {
                            type types-sros:interface-name;
                            description "Interface name";
                        }

                        leaf address-family {
                            type enumeration {
                                enum ipv4                           { value 1; }
                                enum ipv6                           { value 2; }
                            }
                            description "Debug the specified address family";
                        }

                    } // list interface

                    container all-events {
                        presence "Enable the all-events context";
                        description "Enable the all-events context";

                        leaf address-family {
                            type enumeration {
                                enum ipv4                           { value 1; }
                                enum ipv6                           { value 2; }
                            }
                            description "Debug the specified address family";
                        }

                    } // container all-events

                } // container neighbor

                container icmp {
                    description "Enter the icmp context";

                    list interface {
                        key "interface-name";
                        description "Add a list entry for interface";

                        leaf interface-name {
                            type types-sros:interface-name;
                            description "Interface name";
                        }

                    } // list interface

                    container all-packets {
                        presence "Enable the all-packets context";
                        description "Enable the all-packets context";

                    } // container all-packets

                } // container icmp

                container icmp6 {
                    description "Enter the icmp6 context";

                    list interface {
                        key "interface-name";
                        description "Add a list entry for interface";

                        leaf interface-name {
                            type types-sros:interface-name;
                            description "Interface name";
                        }

                    } // list interface

                    container all-packets {
                        presence "Enable the all-packets context";
                        description "Enable the all-packets context";

                    } // container all-packets

                } // container icmp6

                container interface-events {
                    description "Enter the interface-events context";

                    list interface {
                        key "interface-name";
                        description "Add a list entry for interface";

                        leaf interface-name {
                            type types-sros:interface-name;
                            description "Interface name";
                        }

                    } // list interface

                    container all-events {
                        presence "Enable the all-events context";
                        description "Enable the all-events context";

                    } // container all-events

                } // container interface-events

                container packet {
                    description "Enter the packet context";

                    list interface {
                        key "interface-name";
                        description "Enter the interface list instance";

                        leaf interface-name {
                            type types-sros:interface-name;
                            description "Interface name";
                        }

                        leaf address-family {
                            type enumeration {
                                enum ipv4                           { value 1; }
                                enum ipv6                           { value 2; }
                            }
                            description "Debug the specified address family";
                        }

                        leaf headers {
                            type boolean;
                            default "false";
                            description "Display information associated with packet header only";
                        }

                        leaf protocol-id {
                            type int32 {
                                range "0..255";
                            }
                            description "IP protocol ID to trace";
                        }

                    } // list interface

                    container all-packets {
                        presence "Enable the all-packets context";
                        description "Enable the all-packets context";

                        leaf address-family {
                            type enumeration {
                                enum ipv4                           { value 1; }
                                enum ipv6                           { value 2; }
                            }
                            description "Debug the specified address family";
                        }

                        leaf headers {
                            type boolean;
                            default "false";
                            description "Display information associated with packet header only";
                        }

                        leaf protocol-id {
                            type int32 {
                                range "0..255";
                            }
                            description "IP protocol ID to trace";
                        }

                    } // container all-packets

                } // container packet

                container route-table {
                    presence "Enable the route-table context";
                    description "Enable the route-table context";

                    choice all-or-filter {
                        mandatory true;
                        case all {

                            leaf all {
                                type empty;
                                description "Allow trace for all route updates";
                            }

                        }
                        case filter {

                            container filter {
                                description "Enter the filter context";

                                container ipv4 {
                                    description "Enter the ipv4 context";

                                    list prefix {
                                        key "prefix";
                                        max-elements 1;
                                        description "Enter the prefix list instance";

                                        leaf prefix {
                                            type types-sros:ipv4-prefix;
                                            description "IPv4 prefix";
                                        }

                                        leaf longest-prefix-match {
                                            type boolean;
                                            default "false";
                                            description "Allow match for greatest prefix values";
                                        }

                                    } // list prefix

                                } // container ipv4

                                container ipv6 {
                                    description "Enter the ipv6 context";

                                    list prefix {
                                        key "prefix";
                                        max-elements 1;
                                        description "Enter the prefix list instance";

                                        leaf prefix {
                                            type types-sros:ipv6-prefix;
                                            description "IPv6 prefix";
                                        }

                                        leaf longest-prefix-match {
                                            type boolean;
                                            default "false";
                                            description "Allow match for greatest prefix values";
                                        }

                                    } // list prefix

                                } // container ipv6

                            } // container filter

                        }
                    }
                } // container route-table

                container tunnel-table {
                    when "../../router-instance = 'Base'" {
                        description "only allowed in the Base router";
                    }
                    presence "Enable the tunnel-table context";
                    description "Enable the tunnel-table context";

                    choice all-or-filter {
                        mandatory true;
                        case all {

                            leaf all {
                                type empty;
                                description "Allow trace for all tunnel updates";
                            }

                        }
                        case filter {

                            container filter {
                                description "Enter the filter context";

                                container ipv4 {
                                    description "Enter the ipv4 context";

                                    list prefix {
                                        key "prefix";
                                        max-elements 1;
                                        description "Enter the prefix list instance";

                                        leaf prefix {
                                            type types-sros:ipv4-prefix;
                                            description "IPv4 prefix";
                                        }

                                        leaf tunnel-type {
                                            type union {
                                                type types-router:tunnel-type;
                                                type enumeration {
                                                    enum all                            { value -1; }
                                                }
                                            }
                                            default "all";
                                            description "Tunnel type";
                                        }

                                        leaf longest-prefix-match {
                                            type boolean;
                                            default "false";
                                            description "Allow match for greatest prefix values";
                                        }

                                    } // list prefix

                                } // container ipv4

                                container ipv6 {
                                    description "Enter the ipv6 context";

                                    list prefix {
                                        key "prefix";
                                        max-elements 1;
                                        description "Enter the prefix list instance";

                                        leaf prefix {
                                            type types-sros:ipv6-prefix;
                                            description "IPv6 prefix";
                                        }

                                        leaf tunnel-type {
                                            type union {
                                                type types-router:tunnel-type;
                                                type enumeration {
                                                    enum all                            { value -1; }
                                                }
                                            }
                                            default "all";
                                            description "Tunnel type";
                                        }

                                        leaf longest-prefix-match {
                                            type boolean;
                                            default "false";
                                            description "Allow match for greatest prefix values";
                                        }

                                    } // list prefix

                                } // container ipv6

                                container id {
                                    description "Enter the id context";

                                    choice select {
                                        case sdp-id {

                                            leaf sdp-id {
                                                type types-services:sdp-id;
                                                description "SDP ID for tracing";
                                            }

                                        }
                                        case tunnel-id {

                                            leaf tunnel-id {
                                                type types-sros:tunnel-id;
                                                description "Tunnel ID for tracing";
                                            }

                                        }
                                    }
                                } // container id

                            } // container filter

                        }
                    }
                } // container tunnel-table

            } // container ip

            container dhcp {
                when "../router-instance != 'vpls-management' and ../router-instance != 'management'" {
                    description "dhcp debugging is not available for this router";
                }
                description "Enter the dhcp context";

                list mac {
                    key "address";
                    description "Enter the mac list instance";

                    leaf address {
                        type types-sros:mac-unicast-address-no-zero;
                        description "MAC address matching the client hardware address field";
                    }

                    leaf detail-level {
                        type enumeration {
                            enum high                           { value 1; }
                            enum medium                         { value 2; }
                            enum low                            { value 3; }
                        }
                        default "high";
                        description "Detail level of the DHCP debug output";
                    }

                    leaf mode {
                        type enumeration {
                            enum egress-ingress-and-dropped     { value 1; }
                            enum dropped-only                   { value 2; }
                            enum ingress-and-dropped            { value 3; }
                        }
                        default "egress-ingress-and-dropped";
                        description "DHCP packets present in the debug output";
                    }

                } // list mac

                list sap {
                    key "sap-id";
                    description "Enter the sap list instance";

                    leaf sap-id {
                        type types-sros:sap;
                        description "SAP ID";
                    }

                    leaf detail-level {
                        type enumeration {
                            enum high                           { value 1; }
                            enum medium                         { value 2; }
                            enum low                            { value 3; }
                        }
                        default "high";
                        description "Detail level of the DHCP debug output";
                    }

                    leaf mode {
                        type enumeration {
                            enum egress-ingress-and-dropped     { value 1; }
                            enum dropped-only                   { value 2; }
                            enum ingress-and-dropped            { value 3; }
                        }
                        default "egress-ingress-and-dropped";
                        description "DHCP packets present in the debug output";
                    }

                } // list sap

                list interface {
                    key "interface-name";
                    description "Enter the interface list instance";

                    leaf interface-name {
                        type types-sros:interface-name;
                        description "Interface name";
                    }

                    leaf detail-level {
                        type enumeration {
                            enum high                           { value 1; }
                            enum medium                         { value 2; }
                            enum low                            { value 3; }
                        }
                        default "high";
                        description "Detail level of the DHCP debug output";
                    }

                    leaf mode {
                        type enumeration {
                            enum egress-ingress-and-dropped     { value 1; }
                            enum dropped-only                   { value 2; }
                            enum ingress-and-dropped            { value 3; }
                        }
                        default "egress-ingress-and-dropped";
                        description "DHCP packets present in the debug output";
                    }

                } // list interface

                container all-packets {
                    presence "Enable the all-packets context";
                    description "Enable the all-packets context";

                    leaf detail-level {
                        type enumeration {
                            enum high                           { value 1; }
                            enum medium                         { value 2; }
                            enum low                            { value 3; }
                        }
                        default "high";
                        description "Detail level of the DHCP debug output";
                    }

                    leaf mode {
                        type enumeration {
                            enum egress-ingress-and-dropped     { value 1; }
                            enum dropped-only                   { value 2; }
                            enum ingress-and-dropped            { value 3; }
                        }
                        default "egress-ingress-and-dropped";
                        description "DHCP packets present in the debug output";
                    }

                } // container all-packets

            } // container dhcp

            container wpp {
                when "../router-instance != 'vpls-management' and ../router-instance != 'management'" {
                    description "wpp debugging is not available for this router";
                }
                description "Enter the wpp context";

                container packets {
                    presence "Enable the packets context";
                    description "Enable the packets context";

                    leaf detail-level {
                        type enumeration {
                            enum low                            { value 0; }
                            enum high                           { value 1; }
                        }
                        default "low";
                        description "Detail level of the WPP packet debug output";
                    }

                } // container packets

                list portal {
                    key "name";
                    description "Enter the portal list instance";

                    leaf name {
                        type types-sros:named-item;
                        description "WPP portal name";
                    }

                    container packets {
                        description "Enter the packets context";

                        leaf detail-level {
                            type enumeration {
                                enum low                            { value 0; }
                                enum high                           { value 1; }
                            }
                            default "low";
                            description "Detail level of the WPP packet debug output";
                        }

                    } // container packets

                } // list portal

            } // container wpp

            container l2tp {
                when "../router-instance != 'vpls-management' and ../router-instance != 'management'" {
                    description "l2tp debugging is not available for this router";
                }
                description "Enter the l2tp context";

                container events {
                    presence "Enable the events context";
                    description "Enable the events context";

                    choice all-or-selected-events {
                        mandatory true;
                        case all-events {

                            leaf all {
                                type empty;
                                description "Enable debugging for all events";
                            }

                        }
                        case selected-events {

                            leaf stop-control-connection-notification {
                                type boolean;
                                default "false";
                                description "Enable L2TP StopCCN event debugging";
                            }

                            leaf call-disconnect-notification {
                                type boolean;
                                default "false";
                                description "Enable L2TP CDN event debugging";
                            }

                            leaf finite-state-machine {
                                type boolean;
                                default "false";
                                description "Enable L2TP FSM event debugging";
                            }

                            container session-setup {
                                description "Enter the session-setup context";

                                leaf attempted-tunnels {
                                    type boolean;
                                    default "false";
                                    description "Enable debugging for attempted LNS tunnels";
                                }

                                leaf skipped-tunnels {
                                    type boolean;
                                    default "false";
                                    description "Enable debugging for skipped LNS tunnels";
                                }

                            } // container session-setup

                            container lac {
                                description "Enter the lac context";

                                leaf state-recovery {
                                    type boolean;
                                    default "false";
                                    description "Enable L2TP LAC state recovery event debugging";
                                }

                                leaf state-recovery-failed {
                                    type boolean;
                                    default "false";
                                    description "Enable L2TP LAC state recovery failed event debugging";
                                }

                            } // container lac

                            container lns {
                                description "Enter the lns context";

                                container ppp {
                                    presence "Enable the ppp context";
                                    description "Enable the ppp context";

                                    leaf terminate-only {
                                        type boolean;
                                        default "false";
                                        description "Debug events for ungracefully terminated sessions only";
                                    }

                                } // container ppp

                            } // container lns

                        }
                    }
                } // container events

                container packets {
                    presence "Enable the packets context";
                    description "Enable the packets context";

                    leaf detail-level {
                        type enumeration {
                            enum low                            { value 0; }
                            enum high                           { value 1; }
                        }
                        default "low";
                        description "Detail level of the L2TP packet debug output";
                    }

                    leaf direction {
                        type enumeration {
                            enum ingress                        { value 0; }
                            enum egress                         { value 1; }
                            enum both                           { value 2; }
                        }
                        default "both";
                        description "Direction of the L2TP packet debugging";
                    }

                    choice all-or-selected-packets {
                        mandatory true;
                        case all-packets {

                            leaf all {
                                type empty;
                                description "Enable debugging for all session packets";
                            }

                        }
                        case selected-packets {

                            leaf l2tp {
                                type boolean;
                                default "false";
                                description "Enable L2TP packet debugging";
                            }

                            container lns {
                                description "Enter the lns context";

                                leaf dhcp-client {
                                    type boolean;
                                    default "false";
                                    description "Enable DHCP client packet debugging";
                                }

                                container ppp {
                                    description "Enter the ppp context";

                                    choice all-or-selected-ppp-packets {
                                        case all-ppp-packets {

                                            leaf all {
                                                type empty;
                                                description "Enable PPP debugging for all PPP session packets";
                                            }

                                        }
                                        case selected-ppp-packets {

                                            leaf lcp {
                                                type boolean;
                                                default "false";
                                                description "Enable PPP debugging for LCP link establishment packets";
                                            }

                                            leaf pap {
                                                type boolean;
                                                default "false";
                                                description "Enable PPP debugging for PAP authentication packets";
                                            }

                                            leaf chap {
                                                type boolean;
                                                default "false";
                                                description "Enable PPP debugging for CHAP authentication packets";
                                            }

                                            leaf ipcp {
                                                type boolean;
                                                default "false";
                                                description "Enable PPP debugging for IPCP NCP packets";
                                            }

                                            leaf ipv6cp {
                                                type boolean;
                                                default "false";
                                                description "Enable PPP debugging for IPv6CP NCP packets";
                                            }

                                            leaf other {
                                                type boolean;
                                                default "false";
                                                description "Enable other PPP protocol packet debugging";
                                            }

                                        }
                                    }
                                } // container ppp

                            } // container lns

                        }
                    }
                } // container packets

                list tunnel {
                    key "connection-id";
                    max-elements 8;
                    description "Enter the tunnel list instance";

                    leaf connection-id {
                        type types-l2tp:connection-id;
                        description "Local control connection ID of the L2TP tunnel to debug";
                    }

                    container events {
                        presence "Enable the events context";
                        description "Enable the events context";

                        choice all-or-selected-events {
                            mandatory true;
                            case all-events {

                                leaf all {
                                    type empty;
                                    description "Enable debugging for all events";
                                }

                            }
                            case selected-events {

                                leaf stop-control-connection-notification {
                                    type boolean;
                                    default "false";
                                    description "Enable L2TP StopCCN event debugging";
                                }

                                leaf call-disconnect-notification {
                                    type boolean;
                                    default "false";
                                    description "Enable L2TP CDN event debugging";
                                }

                                leaf finite-state-machine {
                                    type boolean;
                                    default "false";
                                    description "Enable L2TP FSM event debugging";
                                }

                                container lac {
                                    description "Enter the lac context";

                                    leaf state-recovery {
                                        type boolean;
                                        default "false";
                                        description "Enable L2TP LAC state recovery event debugging";
                                    }

                                    leaf state-recovery-failed {
                                        type boolean;
                                        default "false";
                                        description "Enable L2TP LAC state recovery failed event debugging";
                                    }

                                } // container lac

                                container lns {
                                    description "Enter the lns context";

                                    container ppp {
                                        presence "Enable the ppp context";
                                        description "Enable the ppp context";

                                        leaf terminate-only {
                                            type boolean;
                                            default "false";
                                            description "Debug events for ungracefully terminated sessions only";
                                        }

                                    } // container ppp

                                } // container lns

                            }
                        }
                    } // container events

                    container packets {
                        presence "Enable the packets context";
                        description "Enable the packets context";

                        leaf detail-level {
                            type enumeration {
                                enum low                            { value 0; }
                                enum high                           { value 1; }
                            }
                            default "low";
                            description "Detail level of the L2TP packet debug output";
                        }

                        leaf direction {
                            type enumeration {
                                enum ingress                        { value 0; }
                                enum egress                         { value 1; }
                                enum both                           { value 2; }
                            }
                            default "both";
                            description "Direction of the L2TP packet debugging";
                        }

                        choice all-or-selected-packets {
                            mandatory true;
                            case all-packets {

                                leaf all {
                                    type empty;
                                    description "Enable debugging for all session packets";
                                }

                            }
                            case selected-packets {

                                leaf l2tp {
                                    type boolean;
                                    default "false";
                                    description "Enable L2TP packet debugging";
                                }

                                container lns {
                                    description "Enter the lns context";

                                    leaf dhcp-client {
                                        type boolean;
                                        default "false";
                                        description "Enable DHCP client packet debugging";
                                    }

                                    container ppp {
                                        description "Enter the ppp context";

                                        choice all-or-selected-ppp-packets {
                                            case all-ppp-packets {

                                                leaf all {
                                                    type empty;
                                                    description "Enable PPP debugging for all PPP session packets";
                                                }

                                            }
                                            case selected-ppp-packets {

                                                leaf lcp {
                                                    type boolean;
                                                    default "false";
                                                    description "Enable PPP debugging for LCP link establishment packets";
                                                }

                                                leaf pap {
                                                    type boolean;
                                                    default "false";
                                                    description "Enable PPP debugging for PAP authentication packets";
                                                }

                                                leaf chap {
                                                    type boolean;
                                                    default "false";
                                                    description "Enable PPP debugging for CHAP authentication packets";
                                                }

                                                leaf ipcp {
                                                    type boolean;
                                                    default "false";
                                                    description "Enable PPP debugging for IPCP NCP packets";
                                                }

                                                leaf ipv6cp {
                                                    type boolean;
                                                    default "false";
                                                    description "Enable PPP debugging for IPv6CP NCP packets";
                                                }

                                                leaf other {
                                                    type boolean;
                                                    default "false";
                                                    description "Enable other PPP protocol packet debugging";
                                                }

                                            }
                                        }
                                    } // container ppp

                                } // container lns

                            }
                        }
                    } // container packets

                } // list tunnel

                list udp-peer {
                    key "ip-address udp-port";
                    max-elements 8;
                    description "Enter the udp-peer list instance";

                    leaf ip-address {
                        type types-sros:ip-address;
                        description "IP address of the L2TP peer to debug";
                    }

                    leaf udp-port {
                        type inet:port-number;
                        description "UDP port of the L2TP peer to debug";
                    }

                    container events {
                        presence "Enable the events context";
                        description "Enable the events context";

                        choice all-or-selected-events {
                            mandatory true;
                            case all-events {

                                leaf all {
                                    type empty;
                                    description "Enable debugging for all events";
                                }

                            }
                            case selected-events {

                                leaf stop-control-connection-notification {
                                    type boolean;
                                    default "false";
                                    description "Enable L2TP StopCCN event debugging";
                                }

                                leaf call-disconnect-notification {
                                    type boolean;
                                    default "false";
                                    description "Enable L2TP CDN event debugging";
                                }

                                leaf finite-state-machine {
                                    type boolean;
                                    default "false";
                                    description "Enable L2TP FSM event debugging";
                                }

                                container lac {
                                    description "Enter the lac context";

                                    leaf state-recovery {
                                        type boolean;
                                        default "false";
                                        description "Enable L2TP LAC state recovery event debugging";
                                    }

                                    leaf state-recovery-failed {
                                        type boolean;
                                        default "false";
                                        description "Enable L2TP LAC state recovery failed event debugging";
                                    }

                                } // container lac

                                container lns {
                                    description "Enter the lns context";

                                    container ppp {
                                        presence "Enable the ppp context";
                                        description "Enable the ppp context";

                                        leaf terminate-only {
                                            type boolean;
                                            default "false";
                                            description "Debug events for ungracefully terminated sessions only";
                                        }

                                    } // container ppp

                                } // container lns

                            }
                        }
                    } // container events

                    container packets {
                        presence "Enable the packets context";
                        description "Enable the packets context";

                        leaf detail-level {
                            type enumeration {
                                enum low                            { value 0; }
                                enum high                           { value 1; }
                            }
                            default "low";
                            description "Detail level of the L2TP packet debug output";
                        }

                        leaf direction {
                            type enumeration {
                                enum ingress                        { value 0; }
                                enum egress                         { value 1; }
                                enum both                           { value 2; }
                            }
                            default "both";
                            description "Direction of the L2TP packet debugging";
                        }

                        choice all-or-selected-packets {
                            mandatory true;
                            case all-packets {

                                leaf all {
                                    type empty;
                                    description "Enable debugging for all session packets";
                                }

                            }
                            case selected-packets {

                                leaf l2tp {
                                    type boolean;
                                    default "false";
                                    description "Enable L2TP packet debugging";
                                }

                                container lns {
                                    description "Enter the lns context";

                                    leaf dhcp-client {
                                        type boolean;
                                        default "false";
                                        description "Enable DHCP client packet debugging";
                                    }

                                    container ppp {
                                        description "Enter the ppp context";

                                        choice all-or-selected-ppp-packets {
                                            case all-ppp-packets {

                                                leaf all {
                                                    type empty;
                                                    description "Enable PPP debugging for all PPP session packets";
                                                }

                                            }
                                            case selected-ppp-packets {

                                                leaf lcp {
                                                    type boolean;
                                                    default "false";
                                                    description "Enable PPP debugging for LCP link establishment packets";
                                                }

                                                leaf pap {
                                                    type boolean;
                                                    default "false";
                                                    description "Enable PPP debugging for PAP authentication packets";
                                                }

                                                leaf chap {
                                                    type boolean;
                                                    default "false";
                                                    description "Enable PPP debugging for CHAP authentication packets";
                                                }

                                                leaf ipcp {
                                                    type boolean;
                                                    default "false";
                                                    description "Enable PPP debugging for IPCP NCP packets";
                                                }

                                                leaf ipv6cp {
                                                    type boolean;
                                                    default "false";
                                                    description "Enable PPP debugging for IPv6CP NCP packets";
                                                }

                                                leaf other {
                                                    type boolean;
                                                    default "false";
                                                    description "Enable other PPP protocol packet debugging";
                                                }

                                            }
                                        }
                                    } // container ppp

                                } // container lns

                            }
                        }
                    } // container packets

                } // list udp-peer

                list ip-peer {
                    key "ip-address";
                    max-elements 8;
                    description "Enter the ip-peer list instance";

                    leaf ip-address {
                        type types-sros:ip-address;
                        description "IP address of the L2TP peer to debug";
                    }

                    container events {
                        presence "Enable the events context";
                        description "Enable the events context";

                        choice all-or-selected-events {
                            mandatory true;
                            case all-events {

                                leaf all {
                                    type empty;
                                    description "Enable debugging for all events";
                                }

                            }
                            case selected-events {

                                leaf stop-control-connection-notification {
                                    type boolean;
                                    default "false";
                                    description "Enable L2TP StopCCN event debugging";
                                }

                                leaf call-disconnect-notification {
                                    type boolean;
                                    default "false";
                                    description "Enable L2TP CDN event debugging";
                                }

                                leaf finite-state-machine {
                                    type boolean;
                                    default "false";
                                    description "Enable L2TP FSM event debugging";
                                }

                                container lac {
                                    description "Enter the lac context";

                                    leaf state-recovery {
                                        type boolean;
                                        default "false";
                                        description "Enable L2TP LAC state recovery event debugging";
                                    }

                                    leaf state-recovery-failed {
                                        type boolean;
                                        default "false";
                                        description "Enable L2TP LAC state recovery failed event debugging";
                                    }

                                } // container lac

                                container lns {
                                    description "Enter the lns context";

                                    container ppp {
                                        presence "Enable the ppp context";
                                        description "Enable the ppp context";

                                        leaf terminate-only {
                                            type boolean;
                                            default "false";
                                            description "Debug events for ungracefully terminated sessions only";
                                        }

                                    } // container ppp

                                } // container lns

                            }
                        }
                    } // container events

                    container packets {
                        presence "Enable the packets context";
                        description "Enable the packets context";

                        leaf detail-level {
                            type enumeration {
                                enum low                            { value 0; }
                                enum high                           { value 1; }
                            }
                            default "low";
                            description "Detail level of the L2TP packet debug output";
                        }

                        leaf direction {
                            type enumeration {
                                enum ingress                        { value 0; }
                                enum egress                         { value 1; }
                                enum both                           { value 2; }
                            }
                            default "both";
                            description "Direction of the L2TP packet debugging";
                        }

                        choice all-or-selected-packets {
                            mandatory true;
                            case all-packets {

                                leaf all {
                                    type empty;
                                    description "Enable debugging for all session packets";
                                }

                            }
                            case selected-packets {

                                leaf l2tp {
                                    type boolean;
                                    default "false";
                                    description "Enable L2TP packet debugging";
                                }

                                container lns {
                                    description "Enter the lns context";

                                    leaf dhcp-client {
                                        type boolean;
                                        default "false";
                                        description "Enable DHCP client packet debugging";
                                    }

                                    container ppp {
                                        description "Enter the ppp context";

                                        choice all-or-selected-ppp-packets {
                                            case all-ppp-packets {

                                                leaf all {
                                                    type empty;
                                                    description "Enable PPP debugging for all PPP session packets";
                                                }

                                            }
                                            case selected-ppp-packets {

                                                leaf lcp {
                                                    type boolean;
                                                    default "false";
                                                    description "Enable PPP debugging for LCP link establishment packets";
                                                }

                                                leaf pap {
                                                    type boolean;
                                                    default "false";
                                                    description "Enable PPP debugging for PAP authentication packets";
                                                }

                                                leaf chap {
                                                    type boolean;
                                                    default "false";
                                                    description "Enable PPP debugging for CHAP authentication packets";
                                                }

                                                leaf ipcp {
                                                    type boolean;
                                                    default "false";
                                                    description "Enable PPP debugging for IPCP NCP packets";
                                                }

                                                leaf ipv6cp {
                                                    type boolean;
                                                    default "false";
                                                    description "Enable PPP debugging for IPv6CP NCP packets";
                                                }

                                                leaf other {
                                                    type boolean;
                                                    default "false";
                                                    description "Enable other PPP protocol packet debugging";
                                                }

                                            }
                                        }
                                    } // container ppp

                                } // container lns

                            }
                        }
                    } // container packets

                } // list ip-peer

                list assignment-id {
                    key "assignment-id";
                    max-elements 8;
                    description "Enter the assignment-id list instance";

                    leaf assignment-id {
                        type string {
                            length "1..63";
                        }
                        description "Assignment ID of the L2TP tunnel to debug";
                    }

                    container events {
                        presence "Enable the events context";
                        description "Enable the events context";

                        choice all-or-selected-events {
                            mandatory true;
                            case all-events {

                                leaf all {
                                    type empty;
                                    description "Enable debugging for all events";
                                }

                            }
                            case selected-events {

                                leaf stop-control-connection-notification {
                                    type boolean;
                                    default "false";
                                    description "Enable L2TP StopCCN event debugging";
                                }

                                leaf call-disconnect-notification {
                                    type boolean;
                                    default "false";
                                    description "Enable L2TP CDN event debugging";
                                }

                                leaf finite-state-machine {
                                    type boolean;
                                    default "false";
                                    description "Enable L2TP FSM event debugging";
                                }

                                container lac {
                                    description "Enter the lac context";

                                    leaf state-recovery {
                                        type boolean;
                                        default "false";
                                        description "Enable L2TP LAC state recovery event debugging";
                                    }

                                    leaf state-recovery-failed {
                                        type boolean;
                                        default "false";
                                        description "Enable L2TP LAC state recovery failed event debugging";
                                    }

                                } // container lac

                                container lns {
                                    description "Enter the lns context";

                                    container ppp {
                                        presence "Enable the ppp context";
                                        description "Enable the ppp context";

                                        leaf terminate-only {
                                            type boolean;
                                            default "false";
                                            description "Debug events for ungracefully terminated sessions only";
                                        }

                                    } // container ppp

                                } // container lns

                            }
                        }
                    } // container events

                    container packets {
                        presence "Enable the packets context";
                        description "Enable the packets context";

                        leaf detail-level {
                            type enumeration {
                                enum low                            { value 0; }
                                enum high                           { value 1; }
                            }
                            default "low";
                            description "Detail level of the L2TP packet debug output";
                        }

                        leaf direction {
                            type enumeration {
                                enum ingress                        { value 0; }
                                enum egress                         { value 1; }
                                enum both                           { value 2; }
                            }
                            default "both";
                            description "Direction of the L2TP packet debugging";
                        }

                        choice all-or-selected-packets {
                            mandatory true;
                            case all-packets {

                                leaf all {
                                    type empty;
                                    description "Enable debugging for all session packets";
                                }

                            }
                            case selected-packets {

                                leaf l2tp {
                                    type boolean;
                                    default "false";
                                    description "Enable L2TP packet debugging";
                                }

                                container lns {
                                    description "Enter the lns context";

                                    leaf dhcp-client {
                                        type boolean;
                                        default "false";
                                        description "Enable DHCP client packet debugging";
                                    }

                                    container ppp {
                                        description "Enter the ppp context";

                                        choice all-or-selected-ppp-packets {
                                            case all-ppp-packets {

                                                leaf all {
                                                    type empty;
                                                    description "Enable PPP debugging for all PPP session packets";
                                                }

                                            }
                                            case selected-ppp-packets {

                                                leaf lcp {
                                                    type boolean;
                                                    default "false";
                                                    description "Enable PPP debugging for LCP link establishment packets";
                                                }

                                                leaf pap {
                                                    type boolean;
                                                    default "false";
                                                    description "Enable PPP debugging for PAP authentication packets";
                                                }

                                                leaf chap {
                                                    type boolean;
                                                    default "false";
                                                    description "Enable PPP debugging for CHAP authentication packets";
                                                }

                                                leaf ipcp {
                                                    type boolean;
                                                    default "false";
                                                    description "Enable PPP debugging for IPCP NCP packets";
                                                }

                                                leaf ipv6cp {
                                                    type boolean;
                                                    default "false";
                                                    description "Enable PPP debugging for IPv6CP NCP packets";
                                                }

                                                leaf other {
                                                    type boolean;
                                                    default "false";
                                                    description "Enable other PPP protocol packet debugging";
                                                }

                                            }
                                        }
                                    } // container ppp

                                } // container lns

                            }
                        }
                    } // container packets

                } // list assignment-id

                list group {
                    key "tunnel-group-name";
                    max-elements 8;
                    description "Enter the group list instance";

                    leaf tunnel-group-name {
                        type types-sros:named-item-64;
                        description "Tunnel group name of the L2TP tunnel to debug";
                    }

                    container events {
                        presence "Enable the events context";
                        description "Enable the events context";

                        choice all-or-selected-events {
                            mandatory true;
                            case all-events {

                                leaf all {
                                    type empty;
                                    description "Enable debugging for all events";
                                }

                            }
                            case selected-events {

                                leaf stop-control-connection-notification {
                                    type boolean;
                                    default "false";
                                    description "Enable L2TP StopCCN event debugging";
                                }

                                leaf call-disconnect-notification {
                                    type boolean;
                                    default "false";
                                    description "Enable L2TP CDN event debugging";
                                }

                                leaf finite-state-machine {
                                    type boolean;
                                    default "false";
                                    description "Enable L2TP FSM event debugging";
                                }

                                container session-setup {
                                    description "Enter the session-setup context";

                                    leaf attempted-tunnels {
                                        type boolean;
                                        default "false";
                                        description "Enable debugging for attempted LNS tunnels";
                                    }

                                    leaf skipped-tunnels {
                                        type boolean;
                                        default "false";
                                        description "Enable debugging for skipped LNS tunnels";
                                    }

                                } // container session-setup

                                container lac {
                                    description "Enter the lac context";

                                    leaf state-recovery {
                                        type boolean;
                                        default "false";
                                        description "Enable L2TP LAC state recovery event debugging";
                                    }

                                    leaf state-recovery-failed {
                                        type boolean;
                                        default "false";
                                        description "Enable L2TP LAC state recovery failed event debugging";
                                    }

                                } // container lac

                                container lns {
                                    description "Enter the lns context";

                                    container ppp {
                                        presence "Enable the ppp context";
                                        description "Enable the ppp context";

                                        leaf terminate-only {
                                            type boolean;
                                            default "false";
                                            description "Debug events for ungracefully terminated sessions only";
                                        }

                                    } // container ppp

                                } // container lns

                            }
                        }
                    } // container events

                    container packets {
                        presence "Enable the packets context";
                        description "Enable the packets context";

                        leaf detail-level {
                            type enumeration {
                                enum low                            { value 0; }
                                enum high                           { value 1; }
                            }
                            default "low";
                            description "Detail level of the L2TP packet debug output";
                        }

                        leaf direction {
                            type enumeration {
                                enum ingress                        { value 0; }
                                enum egress                         { value 1; }
                                enum both                           { value 2; }
                            }
                            default "both";
                            description "Direction of the L2TP packet debugging";
                        }

                        choice all-or-selected-packets {
                            mandatory true;
                            case all-packets {

                                leaf all {
                                    type empty;
                                    description "Enable debugging for all session packets";
                                }

                            }
                            case selected-packets {

                                leaf l2tp {
                                    type boolean;
                                    default "false";
                                    description "Enable L2TP packet debugging";
                                }

                                container lns {
                                    description "Enter the lns context";

                                    leaf dhcp-client {
                                        type boolean;
                                        default "false";
                                        description "Enable DHCP client packet debugging";
                                    }

                                    container ppp {
                                        description "Enter the ppp context";

                                        choice all-or-selected-ppp-packets {
                                            case all-ppp-packets {

                                                leaf all {
                                                    type empty;
                                                    description "Enable PPP debugging for all PPP session packets";
                                                }

                                            }
                                            case selected-ppp-packets {

                                                leaf lcp {
                                                    type boolean;
                                                    default "false";
                                                    description "Enable PPP debugging for LCP link establishment packets";
                                                }

                                                leaf pap {
                                                    type boolean;
                                                    default "false";
                                                    description "Enable PPP debugging for PAP authentication packets";
                                                }

                                                leaf chap {
                                                    type boolean;
                                                    default "false";
                                                    description "Enable PPP debugging for CHAP authentication packets";
                                                }

                                                leaf ipcp {
                                                    type boolean;
                                                    default "false";
                                                    description "Enable PPP debugging for IPCP NCP packets";
                                                }

                                                leaf ipv6cp {
                                                    type boolean;
                                                    default "false";
                                                    description "Enable PPP debugging for IPv6CP NCP packets";
                                                }

                                                leaf other {
                                                    type boolean;
                                                    default "false";
                                                    description "Enable other PPP protocol packet debugging";
                                                }

                                            }
                                        }
                                    } // container ppp

                                } // container lns

                            }
                        }
                    } // container packets

                } // list group

            } // container l2tp

            container radius {
                description "Enter the radius context";

                container servers {
                    when "../../router-instance != 'vpls-management'" {
                        description "Radius debugging is not available for the vpls-management router";
                    }
                    presence "Enable the servers context";
                    description "Enable the servers context";

                    leaf detail-level {
                        type enumeration {
                            enum low                            { value 1; }
                            enum medium                         { value 2; }
                            enum high                           { value 3; }
                        }
                        default "medium";
                        description "Detail level of the RADIUS debug output";
                    }

                    container packet-types {
                        description "Enter the packet-types context";

                        leaf authentication {
                            type boolean;
                            default "true";
                            description "Debug authentication packets";
                        }

                        leaf accounting {
                            type boolean;
                            default "true";
                            description "Debug accounting packets";
                        }

                        leaf coa {
                            type boolean;
                            default "true";
                            description "Debug CoA and DM packets";
                        }

                    } // container packet-types

                    list server-address {
                        key "address";
                        max-elements 10;
                        description "Add a list entry for server-address";

                        leaf address {
                            type types-sros:ip-address;
                            description "IP address of the RADIUS server";
                        }

                    } // list server-address

                    list attribute {
                        key "name";
                        max-elements 10;
                        description "Enter the attribute list instance";

                        leaf name {
                            type string;
                            description "Attribute filter name";
                        }

                        leaf transaction {
                            type boolean;
                            default "false";
                            description "Debug request and response transaction";
                        }

                        leaf type {
                            type types-radius:radius-attribute-type;
                            mandatory true;
                            description "RADIUS attribute type";
                        }

                        leaf extended-type {
                            must "../type = 241 or ../type = 242 or ../type = 243 or ../type = 244 or ../type = 245 or ../type = 246";
                            type types-radius:radius-attribute-extended-type;
                            description "RADIUS attribute extended type";
                        }

                        container vendor-specific {
                            description "Enter the vendor-specific context";

                            leaf vendor {
                                type types-radius:radius-vendor-id;
                                description "RADIUS vendor ID";
                            }

                            leaf vendor-type {
                                type uint32;
                                description "RADIUS vendor specific type";
                            }

                            container encoding {
                                description "Enter the encoding context";

                                leaf type-size {
                                    type uint32 {
                                        range "1..4";
                                    }
                                    default "1";
                                    description "Size of the vendor-type field";
                                }

                                leaf length-size {
                                    type uint32 {
                                        range "0..2";
                                    }
                                    default "1";
                                    description "Size of the vendor-length field";
                                }

                            } // container encoding

                        } // container vendor-specific

                        container value {
                            description "Enter the value context";

                            choice value-format {
                                description "Options for Radius attribute values";
                                case address {

                                    leaf address {
                                        type types-sros:ip-address;
                                        description "Attribute value specified as an IP address";
                                    }

                                }
                                case prefix {

                                    leaf prefix {
                                        type types-sros:ip-prefix;
                                        description "Attribute value specified as an IP prefix";
                                    }

                                }
                                case hex {

                                    leaf hex {
                                        type types-sros:hex-string {
                                            length "1..253";
                                        }
                                        description "Attribute value specified as a hexadecimal string";
                                    }

                                }
                                case integer {

                                    leaf integer {
                                        type uint32;
                                        description "Attribute value specified as an integer";
                                    }

                                }
                                case string {

                                    leaf string {
                                        type string {
                                            length "1..253";
                                        }
                                        description "Attribute value specified as a string";
                                    }

                                }
                            }
                        } // container value

                    } // list attribute

                } // container servers

                list proxy {
                    when "../../router-instance != 'management'" {
                        description "Radius debugging is not available for the vpls-management router";
                    }
                    key "name";
                    max-elements 8;
                    description "Enter the proxy list instance";

                    leaf name {
                        type types-sros:named-item;
                        description "RADIUS proxy server name";
                    }

                    leaf detail-level {
                        type enumeration {
                            enum low                            { value 1; }
                            enum high                           { value 2; }
                        }
                        default "low";
                        description "Detail level of the RADIUS proxy debug output";
                    }

                    leaf direction {
                        type enumeration {
                            enum ingress                        { value 1; }
                            enum egress                         { value 2; }
                            enum both                           { value 3; }
                        }
                        default "both";
                        description "Direction of the RADIUS proxy packet debugging";
                    }

                    leaf dropped-only {
                        type boolean;
                        default "false";
                        description "Show dropped packets only";
                    }

                    choice all-or-selected-packets {
                        mandatory true;
                        case all-packets {

                            leaf all-packet-types {
                                type empty;
                                description "Enable RADIUS proxy debugging for all packets";
                            }

                        }
                        case selected-packets {

                            container packet-types {
                                description "Enter the packet-types context";

                                leaf access-request {
                                    type boolean;
                                    default "false";
                                    description "Debug Access-Request packets";
                                }

                                leaf access-accept {
                                    type boolean;
                                    default "false";
                                    description "Debug Access-Accept packets";
                                }

                                leaf access-reject {
                                    type boolean;
                                    default "false";
                                    description "Debug Access-Reject packets";
                                }

                                leaf access-challenge {
                                    type boolean;
                                    default "false";
                                    description "Debug Access-Challenge packets";
                                }

                                leaf accounting-request {
                                    type boolean;
                                    default "false";
                                    description "Debug Accounting-Request packets";
                                }

                                leaf accounting-response {
                                    type boolean;
                                    default "false";
                                    description "Debug Accounting-Response packets";
                                }

                                leaf other {
                                    type boolean;
                                    default "false";
                                    description "Debug other packet types";
                                }

                            } // container packet-types

                        }
                    }
                    list client-address {
                        key "address";
                        max-elements 10;
                        description "Add a list entry for client-address";

                        leaf address {
                            type types-sros:ip-address;
                            description "IP address of the RADIUS client";
                        }

                    } // list client-address

                } // list proxy

            } // container radius

            container igmp {
                description "Enter the igmp context";

                leaf miscellaneous {
                    type boolean;
                    default "false";
                    description "Enable tracing of miscellaneous events";
                }

                container packet {
                    presence "Enable the packet context";
                    description "Enable the packet context";

                    leaf dropped {
                        type boolean;
                        default "true";
                        description "Enable tracing for dropped packets";
                    }

                    leaf ingress {
                        type boolean;
                        default "true";
                        description "Enable tracing for received packets";
                    }

                    leaf egress {
                        type boolean;
                        default "true";
                        description "Enable tracing for transmitted packets";
                    }

                    leaf type {
                        type types-igmp:trace-igmp-pkt-type;
                        default "all";
                        description "Packet type to trace";
                    }

                    choice origin {
                        default "all";
                        case interface-name {

                            leaf interface-name {
                                type types-sros:interface-name;
                                description "Interface name";
                            }

                        }
                        case interface-ip {

                            leaf interface-ip-address {
                                type types-sros:ipv4-address;
                                description "Source address of the packet to trace";
                            }

                        }
                        case group-interface {

                            leaf group-interface-name {
                                type types-sros:interface-name;
                                description "Interface name";
                            }

                        }
                        case host {

                            leaf host-ip-address {
                                type types-sros:ipv4-address;
                                description "Address of the host to trace";
                            }

                        }
                        case all {

                            leaf all-origins {
                                type empty;
                                description "Trace all origins";
                            }

                        }
                    }
                } // container packet

                container mcs {
                    presence "Enable the mcs context";
                    description "Enable the mcs context";

                    choice interface {
                        mandatory true;
                        case interface-name {

                            leaf interface-name {
                                type types-sros:interface-name;
                                description "Interface name";
                            }

                        }
                        case all {

                            leaf all-interfaces {
                                type empty;
                                description "Trace all interfaces";
                            }

                        }
                    }
                } // container mcs

                container interface {
                    presence "Enable the interface context";
                    description "Enable the interface context";

                    choice interface {
                        mandatory true;
                        case interface-name {

                            leaf interface-name {
                                type types-sros:interface-name;
                                description "Interface name";
                            }

                        }
                        case all {

                            leaf all-interfaces {
                                type empty;
                                description "Trace all interfaces";
                            }

                        }
                    }
                } // container interface

                container group-interface {
                    presence "Enable the group-interface context";
                    description "Enable the group-interface context";

                    choice group-interface {
                        mandatory true;
                        case interface-name {

                            leaf forwarding-service {
                                type types-services:service-name;
                                default "../../router-instance";
                                description "ID of the forwarding service to trace";
                            }

                            leaf group-interface-name {
                                type types-sros:interface-name;
                                description "Interface name";
                            }

                        }
                        case all {

                            leaf all-group-interfaces {
                                type empty;
                                description "Trace all interfaces";
                            }

                        }
                    }
                } // container group-interface

                container host {
                    presence "Enable the host context";
                    description "Enable the host context";

                    leaf ip-address {
                        type types-sros:ipv4-address;
                        description "IP address of the host to trace";
                    }

                    container group-interface {
                        description "Enter the group-interface context";

                        leaf forwarding-service {
                            type types-services:service-name;
                            default "../../router-instance";
                            description "ID of the forwarding service to trace";
                        }

                        leaf group-interface-name {
                            type types-sros:interface-name;
                            description "Interface name";
                        }

                    } // container group-interface

                } // container host

            } // container igmp

            container mld {
                description "Enter the mld context";

                leaf miscellaneous {
                    type boolean;
                    default "false";
                    description "Enable the tracing of miscellaneous events";
                }

                container packet {
                    presence "Enable the packet context";
                    description "Enable the packet context";

                    leaf dropped {
                        type boolean;
                        default "true";
                        description "Enable tracing for dropped packets";
                    }

                    leaf ingress {
                        type boolean;
                        default "true";
                        description "Enable tracing for received packets";
                    }

                    leaf egress {
                        type boolean;
                        default "true";
                        description "Enable tracing for transmitted packets";
                    }

                    leaf type {
                        type types-igmp:trace-mld-pkt-type;
                        default "all";
                        description "Packet type";
                    }

                    choice origin {
                        default "all";
                        case interface-name {

                            leaf interface-name {
                                type types-sros:interface-name;
                                description "Interface name";
                            }

                        }
                        case interface-ip {

                            leaf interface-ip-address {
                                type types-sros:ipv6-address;
                                description "Source address of the packet to trace";
                            }

                        }
                        case group-interface {

                            leaf group-interface-name {
                                type types-sros:interface-name;
                                description "Interface name";
                            }

                        }
                        case host {

                            leaf host-ip-address {
                                type types-sros:ipv6-address;
                                description "Address of the host to trace";
                            }

                        }
                        case all {

                            leaf all-origins {
                                type empty;
                                description "Allow trace for all origins";
                            }

                        }
                    }
                } // container packet

                container mcs {
                    presence "Enable the mcs context";
                    description "Enable the mcs context";

                    choice interface {
                        mandatory true;
                        case interface-name {

                            leaf interface-name {
                                type types-sros:interface-name;
                                description "Interface name";
                            }

                        }
                        case all {

                            leaf all-interfaces {
                                type empty;
                                description "Trace all interfaces";
                            }

                        }
                    }
                } // container mcs

                container interface {
                    presence "Enable the interface context";
                    description "Enable the interface context";

                    choice interface {
                        mandatory true;
                        case interface-name {

                            leaf interface-name {
                                type types-sros:interface-name;
                                description "Interface name";
                            }

                        }
                        case all {

                            leaf all-interfaces {
                                type empty;
                                description "Trace all interfaces";
                            }

                        }
                    }
                } // container interface

                container group-interface {
                    presence "Enable the group-interface context";
                    description "Enable the group-interface context";

                    choice group-interface {
                        mandatory true;
                        case interface-name {

                            leaf forwarding-service {
                                type types-services:service-name;
                                default "../../router-instance";
                                description "ID of the forwarding service to trace";
                            }

                            leaf group-interface-name {
                                type types-sros:interface-name;
                                description "Interface name";
                            }

                        }
                        case all {

                            leaf all-group-interfaces {
                                type empty;
                                description "Trace all interfaces";
                            }

                        }
                    }
                } // container group-interface

                container host {
                    presence "Enable the host context";
                    description "Enable the host context";

                    leaf ip-address {
                        type types-sros:ipv6-address;
                        description "IP address of the host to trace";
                    }

                    container group-interface {
                        description "Enter the group-interface context";

                        leaf forwarding-service {
                            type types-services:service-name;
                            default "../../router-instance";
                            description "ID of the forwarding service to trace";
                        }

                        leaf group-interface-name {
                            type types-sros:interface-name;
                            description "Interface name";
                        }

                    } // container group-interface

                } // container host

            } // container mld

            container pim {
                description "Enter the pim context";

                container events {
                    presence "Enable the events context";
                    description "Enable the events context";

                    choice all-or-selected-events {
                        default "all-events";
                        case all-events {

                            container all {
                                presence "Enable the all context";
                                description "Enable the all context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container all

                        }
                        case selected-events {

                            container adjacency {
                                presence "Enable the adjacency context";
                                description "Enable the adjacency context";

                            } // container adjacency

                            container assert {
                                presence "Enable the assert context";
                                description "Enable the assert context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container assert

                            container auto-rp {
                                presence "Enable the auto-rp context";
                                description "Enable the auto-rp context";

                            } // container auto-rp

                            container bgp {
                                presence "Enable the bgp context";
                                description "Enable the bgp context";

                                leaf group-address {
                                    type types-sros:ip-multicast-address;
                                    description "IP multicast group address used to trace events";
                                }

                                leaf source-address {
                                    type types-sros:ip-address;
                                    description "Source address used to trace events";
                                }

                                leaf peer-address {
                                    type types-sros:ip-address;
                                    description "BGP peer address used to trace events";
                                }

                            } // container bgp

                            container bier-inband {
                                presence "Enable the bier-inband context";
                                description "Enable the bier-inband context";

                                leaf detail {
                                    type boolean;
                                    default "false";
                                    description "Enable detail tracing";
                                }

                            } // container bier-inband

                            container bsr {
                                presence "Enable the bsr context";
                                description "Enable the bsr context";

                                leaf detail {
                                    type boolean;
                                    default "false";
                                    description "Enable detail tracing";
                                }

                            } // container bsr

                            container data {
                                presence "Enable the data context";
                                description "Enable the data context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container data

                            container db {
                                presence "Enable the db context";
                                description "Enable the db context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container db

                            container dynmldp {
                                presence "Enable the dynmldp context";
                                description "Enable the dynmldp context";

                                leaf detail {
                                    type boolean;
                                    default "false";
                                    description "Enable detail tracing";
                                }

                            } // container dynmldp

                            container extranet {
                                presence "Enable the extranet context";
                                description "Enable the extranet context";

                                leaf detail {
                                    type boolean;
                                    default "false";
                                    description "Enable detail tracing";
                                }

                            } // container extranet

                            container graft {
                                presence "Enable the graft context";
                                description "Enable the graft context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container graft

                            container interface {
                                presence "Enable the interface context";
                                description "Enable the interface context";

                                leaf interface-name {
                                    type types-sros:interface-name;
                                    description "Interface name";
                                }

                            } // container interface

                            container jp {
                                presence "Enable the jp context";
                                description "Enable the jp context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container jp

                            container mofrr {
                                presence "Enable the mofrr context";
                                description "Enable the mofrr context";

                            } // container mofrr

                            container mrib {
                                presence "Enable the mrib context";
                                description "Enable the mrib context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container mrib

                            container msg {
                                presence "Enable the msg context";
                                description "Enable the msg context";

                            } // container msg

                            container mvpn-rtcache {
                                presence "Enable the mvpn-rtcache context";
                                description "Enable the mvpn-rtcache context";

                                leaf group-address {
                                    type types-sros:ip-address;
                                    description "Group address used to trace events";
                                }

                                leaf peer-address {
                                    type types-sros:ip-address;
                                    description "Peer address used to trace events";
                                }

                            } // container mvpn-rtcache

                            container red {
                                presence "Enable the red context";
                                description "Enable the red context";

                                leaf detail {
                                    type boolean;
                                    default "false";
                                    description "Enable detail tracing";
                                }

                            } // container red

                            container register {
                                presence "Enable the register context";
                                description "Enable the register context";

                                leaf group-address {
                                    type types-sros:ip-multicast-address;
                                    description "IP multicast group address used to trace events";
                                }

                                leaf source-address {
                                    type types-sros:ip-address;
                                    description "Source address used to trace events";
                                }

                                leaf detail {
                                    type boolean;
                                    default "false";
                                    description "Enable detail tracing";
                                }

                            } // container register

                            container rpfv {
                                presence "Enable the rpfv context";
                                description "Enable the rpfv context";

                                leaf detail {
                                    type boolean;
                                    default "false";
                                    description "Enable detail tracing";
                                }

                            } // container rpfv

                            container rtm {
                                presence "Enable the rtm context";
                                description "Enable the rtm context";

                                leaf detail {
                                    type boolean;
                                    default "false";
                                    description "Enable detail tracing";
                                }

                            } // container rtm

                            container s-pmsi {
                                presence "Enable the s-pmsi context";
                                description "Enable the s-pmsi context";

                                leaf vpn-source-address {
                                    type types-sros:ip-address;
                                    description "VPN source address used to trace events";
                                }

                                leaf detail {
                                    type boolean;
                                    default "false";
                                    description "Enable detail tracing";
                                }

                            } // container s-pmsi

                            container tunnel-interface {
                                presence "Enable the tunnel-interface context";
                                description "Enable the tunnel-interface context";

                                leaf rsvp-p2mp {
                                    type types-sros:named-item;
                                    description "RSVP P2MP LSP name";
                                }

                                leaf ldp-p2mp-id {
                                    type uint32 {
                                        range "1..8192";
                                    }
                                    description "LDP P2MP ID";
                                }

                                leaf sender-address {
                                    type types-sros:ipv4-unicast-address;
                                    description "IP address of the sender";
                                }

                            } // container tunnel-interface

                        }
                    }
                } // container events

                container packet {
                    presence "Enable the packet context";
                    description "Enable the packet context";

                    leaf ipv4 {
                        type boolean;
                        default "true";
                        description "Enable tracing for PIM IPv4 packets";
                    }

                    leaf ipv6 {
                        type boolean;
                        default "true";
                        description "Enable tracing for PIM IPv6 packets";
                    }

                    leaf ingress {
                        type boolean;
                        default "true";
                        description "Enable tracing for received packets";
                    }

                    leaf egress {
                        type boolean;
                        default "true";
                        description "Enable tracing for transmitted packets";
                    }

                    choice all-or-selected-packets {
                        default "all-packets";
                        case all-packets {

                            leaf all-packet-types {
                                type empty;
                                description "Enable PIM debugging for all packets";
                            }

                            choice origin {
                                default "all";
                                case interface {

                                    leaf interface-name {
                                        type types-sros:interface-name;
                                        description "Interface name";
                                    }

                                }
                                case all {

                                    leaf all-origins {
                                        type empty;
                                        description "Enable trace for all origins";
                                    }

                                }
                            }
                        }
                        case selected-packets {

                            container packet-types {
                                description "Enter the packet-types context";

                                container hello {
                                    presence "Enable the hello context";
                                    description "Enable the hello context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container hello

                                container register {
                                    presence "Enable the register context";
                                    description "Enable the register context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container register

                                container register-stop {
                                    presence "Enable the register-stop context";
                                    description "Enable the register-stop context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container register-stop

                                container jp {
                                    presence "Enable the jp context";
                                    description "Enable the jp context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container jp

                                container bsr {
                                    presence "Enable the bsr context";
                                    description "Enable the bsr context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container bsr

                                container assert {
                                    presence "Enable the assert context";
                                    description "Enable the assert context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container assert

                                container crp {
                                    presence "Enable the crp context";
                                    description "Enable the crp context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container crp

                                container mdt-tlv {
                                    presence "Enable the mdt-tlv context";
                                    description "Enable the mdt-tlv context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container mdt-tlv

                                container auto-rp-announcement {
                                    presence "Enable the auto-rp-announcement context";
                                    description "Enable the auto-rp-announcement context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container auto-rp-announcement

                                container auto-rp-mapping {
                                    presence "Enable the auto-rp-mapping context";
                                    description "Enable the auto-rp-mapping context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container auto-rp-mapping

                                container graft {
                                    presence "Enable the graft context";
                                    description "Enable the graft context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container graft

                                container graft-ack {
                                    presence "Enable the graft-ack context";
                                    description "Enable the graft-ack context";

                                    choice origin {
                                        default "all";
                                        case interface {

                                            leaf interface-name {
                                                type types-sros:interface-name;
                                                description "Interface name";
                                            }

                                        }
                                        case all {

                                            leaf all-origins {
                                                type empty;
                                                description "Enable trace for all origins";
                                            }

                                        }
                                    }
                                } // container graft-ack

                            } // container packet-types

                        }
                    }
                } // container packet

            } // container pim

            container mtrace {
                description "Enter the mtrace context";

                container miscellaneous {
                    presence "Enable the miscellaneous context";
                    description "Enable the miscellaneous context";

                } // container miscellaneous

                container packet {
                    presence "Enable the packet context";
                    description "Enable the packet context";

                    choice all-or-selected-packets {
                        default "all-packets";
                        case all-packets {

                            leaf all-packet-types {
                                type empty;
                                description "Enable debugging for all packets";
                            }

                        }
                        case selected-packets {

                            container packet-types {
                                description "Enter the packet-types context";

                                leaf query {
                                    type boolean;
                                    default "false";
                                    description "Debug query packets";
                                }

                                leaf request {
                                    type boolean;
                                    default "false";
                                    description "Debug request packets";
                                }

                                leaf response {
                                    type boolean;
                                    default "false";
                                    description "Debug response packets";
                                }

                            } // container packet-types

                        }
                    }
                } // container packet

            } // container mtrace

            container mtrace2 {
                description "Enter the mtrace2 context";

                container miscellaneous {
                    presence "Enable the miscellaneous context";
                    description "Enable the miscellaneous context";

                } // container miscellaneous

                container packet {
                    presence "Enable the packet context";
                    description "Enable the packet context";

                    choice all-or-selected-packets {
                        default "all-packets";
                        case all-packets {

                            leaf all-packet-types {
                                type empty;
                                description "Enable debugging for all packets";
                            }

                        }
                        case selected-packets {

                            container packet-types {
                                description "Enter the packet-types context";

                                leaf query {
                                    type boolean;
                                    default "false";
                                    description "Debug query packets";
                                }

                                leaf request {
                                    type boolean;
                                    default "false";
                                    description "Debug request packets";
                                }

                                leaf response {
                                    type boolean;
                                    default "false";
                                    description "Debug response packets";
                                }

                            } // container packet-types

                        }
                    }
                } // container packet

            } // container mtrace2

            container msdp {
                description "Enter the msdp context";

                container packet {
                    presence "Enable the packet context";
                    description "Enable the packet context";

                    choice all-or-selected-packets {
                        default "all-packets";
                        case all-packets {

                            leaf all-packet-types {
                                type empty;
                                description "Enable MSDP debugging for all packets";
                            }

                        }
                        case selected-packets {

                            container packet-types {
                                description "Enter the packet-types context";

                                container keep-alive {
                                    presence "Enable the keep-alive context";
                                    description "Enable the keep-alive context";

                                    leaf peer-address {
                                        type types-sros:ip-address;
                                        description "Peer address used to trace packets";
                                    }

                                } // container keep-alive

                                container source-active {
                                    presence "Enable the source-active context";
                                    description "Enable the source-active context";

                                    leaf peer-address {
                                        type types-sros:ip-address;
                                        description "Peer address used to trace packets";
                                    }

                                } // container source-active

                                container sa-request {
                                    presence "Enable the sa-request context";
                                    description "Enable the sa-request context";

                                    leaf peer-address {
                                        type types-sros:ip-address;
                                        description "Peer address used to trace packets";
                                    }

                                } // container sa-request

                                container sa-response {
                                    presence "Enable the sa-response context";
                                    description "Enable the sa-response context";

                                    leaf peer-address {
                                        type types-sros:ip-address;
                                        description "Peer address used to trace packets";
                                    }

                                } // container sa-response

                            } // container packet-types

                        }
                    }
                } // container packet

                container pim {
                    presence "Enable the pim context";
                    description "Enable the pim context";

                    leaf group-address {
                        type types-sros:ipv4-multicast-address;
                        description "IP multicast group address used to trace events";
                    }

                } // container pim

                container rtm {
                    presence "Enable the rtm context";
                    description "Enable the rtm context";

                    leaf rp-address {
                        type types-sros:ipv4-address;
                        description "IP multicast RP address used to trace events";
                    }

                } // container rtm

                container sa-db {
                    presence "Enable the sa-db context";
                    description "Enable the sa-db context";

                    leaf group-address {
                        type types-sros:ipv4-multicast-address;
                        description "IP multicast group address used to trace events";
                    }

                    leaf source-address {
                        type types-sros:ipv4-address;
                        description "Source address used to trace events";
                    }

                    leaf rp-address {
                        type types-sros:ipv4-address;
                        description "IP multicast RP address used to trace events";
                    }

                } // container sa-db

            } // container msdp

            container vrrp {
                when "../router-instance != 'vpls-management' and ../router-instance != 'management'" {
                    description "vrrp debugging is not available for this router";
                }
                description "Enter the vrrp context";

                container events {
                    description "Enter the events context";

                    list interface {
                        key "interface-name";
                        description "Enter the interface list instance";

                        leaf interface-name {
                            type types-sros:interface-name;
                            description "Interface name";
                        }

                        container ipv4 {
                            description "Enter the ipv4 context";

                            list vrid {
                                key "virtual-router-id";
                                max-elements 4;
                                description "Add a list entry for vrid";

                                leaf virtual-router-id {
                                    type int32 {
                                        range "1..255";
                                    }
                                    description "Virtual router ID to debug";
                                }

                            } // list vrid

                        } // container ipv4

                        container ipv6 {
                            description "Enter the ipv6 context";

                            list vrid {
                                key "virtual-router-id";
                                max-elements 4;
                                description "Add a list entry for vrid";

                                leaf virtual-router-id {
                                    type int32 {
                                        range "1..255";
                                    }
                                    description "Virtual router ID to debug";
                                }

                            } // list vrid

                        } // container ipv6

                        container all-vrids {
                            presence "Enable the all-vrids context";
                            description "Enable the all-vrids context";

                        } // container all-vrids

                    } // list interface

                    container all-events {
                        presence "Enable the all-events context";
                        description "Enable the all-events context";

                    } // container all-events

                } // container events

                container packet {
                    description "Enter the packet context";

                    list interface {
                        key "interface-name";
                        description "Enter the interface list instance";

                        leaf interface-name {
                            type types-sros:interface-name;
                            description "Interface name";
                        }

                        container ipv4 {
                            description "Enter the ipv4 context";

                            list vrid {
                                key "virtual-router-id";
                                max-elements 4;
                                description "Add a list entry for vrid";

                                leaf virtual-router-id {
                                    type int32 {
                                        range "1..255";
                                    }
                                    description "Virtual router ID to debug";
                                }

                            } // list vrid

                        } // container ipv4

                        container ipv6 {
                            description "Enter the ipv6 context";

                            list vrid {
                                key "virtual-router-id";
                                max-elements 4;
                                description "Add a list entry for vrid";

                                leaf virtual-router-id {
                                    type int32 {
                                        range "1..255";
                                    }
                                    description "Virtual router ID to debug";
                                }

                            } // list vrid

                        } // container ipv6

                        container all-vrids {
                            presence "Enable the all-vrids context";
                            description "Enable the all-vrids context";

                        } // container all-vrids

                    } // list interface

                    container all-packets {
                        presence "Enable the all-packets context";
                        description "Enable the all-packets context";

                    } // container all-packets

                } // container packet

            } // container vrrp

            container bier {
                description "Enter the bier context";

                container db {
                    presence "Enable the db context";
                    description "Enable the db context";

                } // container db

                container fib {
                    presence "Enable the fib context";
                    description "Enable the fib context";

                } // container fib

                container management {
                    presence "Enable the management context";
                    description "Enable the management context";

                } // container management

                container red {
                    presence "Enable the red context";
                    description "Enable the red context";

                } // container red

                container rtm {
                    presence "Enable the rtm context";
                    description "Enable the rtm context";

                } // container rtm

                container template {
                    presence "Enable the template context";
                    description "Enable the template context";

                } // container template

                container tunnel {
                    presence "Enable the tunnel context";
                    description "Enable the tunnel context";

                } // container tunnel

            } // container bier


            container ldp {
                when "../router-instance = 'Base'" {
                    description "LDP protocol is only supported in router Base";
                }
                description "Enter the ldp context";

                list peer {
                    key "ip-address";
                    description "Enter the peer list instance";

                    leaf ip-address {
                        type types-sros:ip-address;
                        description "Peer IP address";
                    }

                    container event {
                        description "Enter the event context";

                        container bindings {
                            presence "Enable the bindings context";
                            description "Enable the bindings context";

                        } // container bindings

                        container messages {
                            presence "Enable the messages context";
                            description "Enable the messages context";

                        } // container messages

                    } // container event

                    container packet {
                        description "Enter the packet context";

                        container init {
                            presence "Enable the init context";
                            description "Enable the init context";

                            leaf detail {
                                type boolean;
                                default "false";
                                description "Display detailed information";
                            }

                        } // container init

                        container keepalive {
                            presence "Enable the keepalive context";
                            description "Enable the keepalive context";

                        } // container keepalive

                        container label {
                            presence "Enable the label context";
                            description "Enable the label context";

                            leaf detail {
                                type boolean;
                                default "false";
                                description "Display detailed information";
                            }

                        } // container label

                        container hello {
                            presence "Enable the hello context";
                            description "Enable the hello context";

                            leaf detail {
                                type boolean;
                                default "false";
                                description "Display detailed information";
                            }

                        } // container hello

                    } // container packet

                } // list peer

                list interface {
                    key "interface-name";
                    description "Enter the interface list instance";

                    leaf interface-name {
                        type types-sros:interface-name;
                        description "Interface name";
                    }

                    container ipv4 {
                        presence "Enable the ipv4 context";
                        description "Enable the ipv4 context";

                        container event {
                            description "Enter the event context";

                            container messages {
                                presence "Enable the messages context";
                                description "Enable the messages context";

                            } // container messages

                        } // container event

                        container packet {
                            description "Enter the packet context";

                            container hello {
                                presence "Enable the hello context";
                                description "Enable the hello context";

                                leaf detail {
                                    type boolean;
                                    default "false";
                                    description "Display detailed information";
                                }

                            } // container hello

                        } // container packet

                    } // container ipv4

                    container ipv6 {
                        presence "Enable the ipv6 context";
                        description "Enable the ipv6 context";

                        container event {
                            description "Enter the event context";

                            container messages {
                                presence "Enable the messages context";
                                description "Enable the messages context";

                            } // container messages

                        } // container event

                        container packet {
                            description "Enter the packet context";

                            container hello {
                                presence "Enable the hello context";
                                description "Enable the hello context";

                                leaf detail {
                                    type boolean;
                                    default "false";
                                    description "Display detailed information";
                                }

                            } // container hello

                        } // container packet

                    } // container ipv6

                } // list interface

            } // container ldp

        } // list router

        container service {
            description "Enter the service context";

            list ies {
                key "service-name";
                description "Enter the ies list instance";

                leaf service-name {
                    type types-services:service-name;
                    description "Administrative service name";
                }

                container ppp {
                    description "Enter the ppp context";

                    list circuit-id {
                        key "id";
                        max-elements 8;
                        description "Add a list entry for circuit-id";

                        leaf id {
                            type string {
                                length "1..255";
                            }
                            description "Circuit ID of the PPPoE session to debug";
                        }

                    } // list circuit-id

                    container events {
                        presence "Enable the events context";
                        description "Enable the events context";

                        choice all-or-selected-events {
                            mandatory true;
                            case all-events {

                                leaf all {
                                    type empty;
                                    description "Enable PPP debugging for all events";
                                }

                            }
                            case selected-events {

                                container dhcp-client {
                                    presence "Enable the dhcp-client context";
                                    description "Enable the dhcp-client context";

                                    leaf terminate-only {
                                        type boolean;
                                        default "false";
                                        description "Debug events for ungraceful terminated sessions only";
                                    }

                                } // container dhcp-client

                                container l2tp {
                                    presence "Enable the l2tp context";
                                    description "Enable the l2tp context";

                                    leaf terminate-only {
                                        type boolean;
                                        default "false";
                                        description "Debug events for ungraceful terminated sessions only";
                                    }

                                } // container l2tp

                                container local-address-assignment {
                                    presence "Enable the local-address-assignment context";
                                    description "Enable the local-address-assignment context";

                                    leaf terminate-only {
                                        type boolean;
                                        default "false";
                                        description "Debug events for ungraceful terminated sessions only";
                                    }

                                } // container local-address-assignment

                                container ppp {
                                    presence "Enable the ppp context";
                                    description "Enable the ppp context";

                                    leaf terminate-only {
                                        type boolean;
                                        default "false";
                                        description "Debug events for ungraceful terminated sessions only";
                                    }

                                } // container ppp

                            }
                        }
                    } // container events

                    list mac {
                        key "address";
                        max-elements 8;
                        description "Add a list entry for mac";

                        leaf address {
                            type types-sros:mac-address;
                            description "MAC address of the PPPoE session to debug";
                        }

                    } // list mac

                    container packets {
                        presence "Enable the packets context";
                        description "Enable the packets context";

                        leaf detail-level {
                            type enumeration {
                                enum low                            { value 0; }
                                enum medium                         { value 1; }
                                enum high                           { value 2; }
                            }
                            default "high";
                            description "Detail level of the PPP packet debug output";
                        }

                        leaf mode {
                            type enumeration {
                                enum dropped-only                   { value 1; }
                                enum ingress-and-dropped            { value 2; }
                                enum egress-ingress-and-dropped     { value 3; }
                            }
                            default "dropped-only";
                            description "PPP packets present in the debug output";
                        }

                        choice all-or-selected-packets {
                            mandatory true;
                            case all-packets {

                                leaf all {
                                    type empty;
                                    description "Enable PPP debugging for all packets";
                                }

                            }
                            case selected-packets {

                                leaf dhcp-client {
                                    type boolean;
                                    default "false";
                                    description "Enable DHCP client packet debugging";
                                }

                                container discovery {
                                    description "Enter the discovery context";

                                    choice all-or-selected-discovery-packets {
                                        case all-discovery-packets {

                                            leaf all {
                                                type empty;
                                                description "Enable PPP debugging for all discovery packets";
                                            }

                                        }
                                        case selected-discovery-packets {

                                            leaf padi {
                                                type boolean;
                                                default "false";
                                                description "Enable PPP debugging for PADI discovery packets";
                                            }

                                            leaf pado {
                                                type boolean;
                                                default "false";
                                                description "Enable PPP debugging for PADO discovery packets";
                                            }

                                            leaf padr {
                                                type boolean;
                                                default "false";
                                                description "Enable PPP debugging for PADR discovery packets";
                                            }

                                            leaf pads {
                                                type boolean;
                                                default "false";
                                                description "Enable PPP debugging for PADS discovery packets";
                                            }

                                            leaf padt {
                                                type boolean;
                                                default "false";
                                                description "Enable PPP debugging for PADT discovery packets";
                                            }

                                        }
                                    }
                                } // container discovery

                                container ppp-session {
                                    description "Enter the ppp-session context";

                                    choice all-or-selected-ppp-session-packets {
                                        case all-ppp-session-packets {

                                            leaf all {
                                                type empty;
                                                description "Enable PPP debugging for all PPP session packets";
                                            }

                                        }
                                        case selected-ppp-session-packets {

                                            leaf lcp {
                                                type boolean;
                                                default "false";
                                                description "Enable PPP debugging for LCP link establishment packets";
                                            }

                                            leaf pap {
                                                type boolean;
                                                default "false";
                                                description "Enable PPP debugging for PAP authentication packets";
                                            }

                                            leaf chap {
                                                type boolean;
                                                default "false";
                                                description "Enable PPP debugging for CHAP authentication packets";
                                            }

                                            leaf ipcp {
                                                type boolean;
                                                default "false";
                                                description "Enable PPP debugging for IPCP NCP packets";
                                            }

                                            leaf ipv6cp {
                                                type boolean;
                                                default "false";
                                                description "Enable PPP debugging for IPv6CP NCP packets";
                                            }

                                        }
                                    }
                                } // container ppp-session

                            }
                        }
                    } // container packets

                    list remote-id {
                        key "id";
                        max-elements 8;
                        description "Add a list entry for remote-id";

                        leaf id {
                            type string {
                                length "1..255";
                            }
                            description "Remote ID of the PPPoE session to debug";
                        }

                    } // list remote-id

                    list user-name {
                        key "name";
                        max-elements 8;
                        description "Add a list entry for user-name";

                        leaf name {
                            type string {
                                length "1..255";
                            }
                            description "Username of the PPPoE session to debug";
                        }

                    } // list user-name

                    list sap {
                        key "sap-id";
                        max-elements 8;
                        description "Add a list entry for sap";

                        leaf sap-id {
                            type types-sros:sap;
                            description "SAP ID of the PPPoE session to debug";
                        }

                    } // list sap

                } // container ppp

            } // list ies

            list vpls {
                key "service-name";
                description "Enter the vpls list instance";

                leaf service-name {
                    type types-services:service-name;
                    description "Administrative service name";
                }

                container ppp {
                    description "Enter the ppp context";

                    list circuit-id {
                        key "id";
                        max-elements 8;
                        description "Add a list entry for circuit-id";

                        leaf id {
                            type string {
                                length "1..255";
                            }
                            description "Circuit ID of the PPPoE session to debug";
                        }

                    } // list circuit-id

                    container events {
                        presence "Enable the events context";
                        description "Enable the events context";

                        choice all-or-selected-events {
                            mandatory true;
                            case all-events {

                                leaf all {
                                    type empty;
                                    description "Enable PPP debugging for all events";
                                }

                            }
                            case selected-events {

                                container dhcp-client {
                                    presence "Enable the dhcp-client context";
                                    description "Enable the dhcp-client context";

                                    leaf terminate-only {
                                        type boolean;
                                        default "false";
                                        description "Debug events for ungraceful terminated sessions only";
                                    }

                                } // container dhcp-client

                                container l2tp {
                                    presence "Enable the l2tp context";
                                    description "Enable the l2tp context";

                                    leaf terminate-only {
                                        type boolean;
                                        default "false";
                                        description "Debug events for ungraceful terminated sessions only";
                                    }

                                } // container l2tp

                                container local-address-assignment {
                                    presence "Enable the local-address-assignment context";
                                    description "Enable the local-address-assignment context";

                                    leaf terminate-only {
                                        type boolean;
                                        default "false";
                                        description "Debug events for ungraceful terminated sessions only";
                                    }

                                } // container local-address-assignment

                                container ppp {
                                    presence "Enable the ppp context";
                                    description "Enable the ppp context";

                                    leaf terminate-only {
                                        type boolean;
                                        default "false";
                                        description "Debug events for ungraceful terminated sessions only";
                                    }

                                } // container ppp

                            }
                        }
                    } // container events

                    list mac {
                        key "address";
                        max-elements 8;
                        description "Add a list entry for mac";

                        leaf address {
                            type types-sros:mac-address;
                            description "MAC address of the PPPoE session to debug";
                        }

                    } // list mac

                    container packets {
                        presence "Enable the packets context";
                        description "Enable the packets context";

                        leaf detail-level {
                            type enumeration {
                                enum low                            { value 0; }
                                enum medium                         { value 1; }
                                enum high                           { value 2; }
                            }
                            default "high";
                            description "Detail level of the PPP packet debug output";
                        }

                        leaf mode {
                            type enumeration {
                                enum dropped-only                   { value 1; }
                                enum ingress-and-dropped            { value 2; }
                                enum egress-ingress-and-dropped     { value 3; }
                            }
                            default "dropped-only";
                            description "PPP packets present in the debug output";
                        }

                        choice all-or-selected-packets {
                            mandatory true;
                            case all-packets {

                                leaf all {
                                    type empty;
                                    description "Enable PPP debugging for all packets";
                                }

                            }
                            case selected-packets {

                                leaf dhcp-client {
                                    type boolean;
                                    default "false";
                                    description "Enable DHCP client packet debugging";
                                }

                                container discovery {
                                    description "Enter the discovery context";

                                    choice all-or-selected-discovery-packets {
                                        case all-discovery-packets {

                                            leaf all {
                                                type empty;
                                                description "Enable PPP debugging for all discovery packets";
                                            }

                                        }
                                        case selected-discovery-packets {

                                            leaf padi {
                                                type boolean;
                                                default "false";
                                                description "Enable PPP debugging for PADI discovery packets";
                                            }

                                            leaf pado {
                                                type boolean;
                                                default "false";
                                                description "Enable PPP debugging for PADO discovery packets";
                                            }

                                            leaf padr {
                                                type boolean;
                                                default "false";
                                                description "Enable PPP debugging for PADR discovery packets";
                                            }

                                            leaf pads {
                                                type boolean;
                                                default "false";
                                                description "Enable PPP debugging for PADS discovery packets";
                                            }

                                            leaf padt {
                                                type boolean;
                                                default "false";
                                                description "Enable PPP debugging for PADT discovery packets";
                                            }

                                        }
                                    }
                                } // container discovery

                                container ppp-session {
                                    description "Enter the ppp-session context";

                                    choice all-or-selected-ppp-session-packets {
                                        case all-ppp-session-packets {

                                            leaf all {
                                                type empty;
                                                description "Enable PPP debugging for all PPP session packets";
                                            }

                                        }
                                        case selected-ppp-session-packets {

                                            leaf lcp {
                                                type boolean;
                                                default "false";
                                                description "Enable PPP debugging for LCP link establishment packets";
                                            }

                                            leaf pap {
                                                type boolean;
                                                default "false";
                                                description "Enable PPP debugging for PAP authentication packets";
                                            }

                                            leaf chap {
                                                type boolean;
                                                default "false";
                                                description "Enable PPP debugging for CHAP authentication packets";
                                            }

                                            leaf ipcp {
                                                type boolean;
                                                default "false";
                                                description "Enable PPP debugging for IPCP NCP packets";
                                            }

                                            leaf ipv6cp {
                                                type boolean;
                                                default "false";
                                                description "Enable PPP debugging for IPv6CP NCP packets";
                                            }

                                        }
                                    }
                                } // container ppp-session

                            }
                        }
                    } // container packets

                    list remote-id {
                        key "id";
                        max-elements 8;
                        description "Add a list entry for remote-id";

                        leaf id {
                            type string {
                                length "1..255";
                            }
                            description "Remote ID of the PPPoE session to debug";
                        }

                    } // list remote-id

                    list user-name {
                        key "name";
                        max-elements 8;
                        description "Add a list entry for user-name";

                        leaf name {
                            type string {
                                length "1..255";
                            }
                            description "Username of the PPPoE session to debug";
                        }

                    } // list user-name

                    list sap {
                        key "sap-id";
                        max-elements 8;
                        description "Add a list entry for sap";

                        leaf sap-id {
                            type types-sros:sap;
                            description "SAP ID of the PPPoE session to debug";
                        }

                    } // list sap

                } // container ppp

                container igmp-snooping {
                    description "Enter the igmp-snooping context";

                    container packet {
                        presence "Enable the packet context";
                        description "Enable the packet context";

                        leaf detail {
                            type types-igmp:trace-igmp-mld-pkt-detail;
                            default "medium";
                            description "Detail level of the debug output";
                        }

                        leaf dropped {
                            type boolean;
                            default "true";
                            description "Enable tracing for dropped packets";
                        }

                        leaf ingress {
                            type boolean;
                            default "true";
                            description "Enable tracing for received packets";
                        }

                        leaf egress {
                            type boolean;
                            default "true";
                            description "Enable tracing for transmitted packets";
                        }

                        leaf evpn-mpls {
                            type boolean;
                            default "false";
                            description "Allow debugging for EVPN-MPLS destinations";
                        }

                        list mac {
                            key "mac-address";
                            max-elements 8;
                            description "Add a list entry for mac";

                            leaf mac-address {
                                type types-sros:mac-address;
                                description "MAC address";
                            }

                        } // list mac

                        list sap {
                            key "sap-id";
                            max-elements 8;
                            description "Add a list entry for sap";

                            leaf sap-id {
                                type types-sros:sap;
                                description "SAP ID";
                            }

                        } // list sap

                        list sdp-bind {
                            key "sdp-bind-id";
                            max-elements 8;
                            description "Add a list entry for sdp-bind";

                            leaf sdp-bind-id {
                                type types-services:sdp-bind-id;
                                description "SDP bind ID";
                            }

                        } // list sdp-bind

                        list evpn-vxlan {
                            key "ip-address vni";
                            max-elements 8;
                            description "Add a list entry for evpn-vxlan";

                            leaf ip-address {
                                type types-sros:ip-unicast-address;
                                description "IP address of the VXLAN Tunnel Endpoint";
                            }

                            leaf vni {
                                type types-services:vxlan-vni;
                                description "VXLAN Network Identifier of the VXLAN binding";
                            }

                        } // list evpn-vxlan

                    } // container packet

                } // container igmp-snooping

                container mld-snooping {
                    description "Enter the mld-snooping context";

                    container packet {
                        presence "Enable the packet context";
                        description "Enable the packet context";

                        leaf detail {
                            type types-igmp:trace-igmp-mld-pkt-detail;
                            default "medium";
                            description "Detail level of the debug output";
                        }

                        leaf dropped {
                            type boolean;
                            default "true";
                            description "Enable tracing for dropped packets";
                        }

                        leaf ingress {
                            type boolean;
                            default "true";
                            description "Enable tracing for received packets";
                        }

                        leaf egress {
                            type boolean;
                            default "true";
                            description "Enable tracing for transmitted packets";
                        }

                        leaf evpn-mpls {
                            type boolean;
                            default "false";
                            description "Allow debugging for EVPN-MPLS destinations";
                        }

                        list mac {
                            key "mac-address";
                            max-elements 8;
                            description "Add a list entry for mac";

                            leaf mac-address {
                                type types-sros:mac-address;
                                description "MAC address";
                            }

                        } // list mac

                        list sap {
                            key "sap-id";
                            max-elements 8;
                            description "Add a list entry for sap";

                            leaf sap-id {
                                type types-sros:sap;
                                description "SAP ID";
                            }

                        } // list sap

                        list sdp-bind {
                            key "sdp-bind-id";
                            max-elements 8;
                            description "Add a list entry for sdp-bind";

                            leaf sdp-bind-id {
                                type types-services:sdp-bind-id;
                                description "SDP bind ID";
                            }

                        } // list sdp-bind

                        list evpn-vxlan {
                            key "ip-address vni";
                            max-elements 8;
                            description "Add a list entry for evpn-vxlan";

                            leaf ip-address {
                                type types-sros:ip-unicast-address;
                                description "IP address of the VXLAN Tunnel Endpoint";
                            }

                            leaf vni {
                                type types-services:vxlan-vni;
                                description "VXLAN Network Identifier of the VXLAN binding";
                            }

                        } // list evpn-vxlan

                    } // container packet

                } // container mld-snooping

                container pim-snooping {
                    description "Enter the pim-snooping context";

                    container events {
                        presence "Enable the events context";
                        description "Enable the events context";

                        choice all-or-selected-events {
                            default "all-events";
                            case all-events {

                                container all {
                                    presence "Enable the all context";
                                    description "Enable the all context";

                                    leaf group-address {
                                        type types-sros:ip-multicast-address;
                                        description "IP multicast group address used to trace events";
                                    }

                                    leaf source-address {
                                        type types-sros:ip-address;
                                        description "Source address used to trace events";
                                    }

                                    leaf detail {
                                        type boolean;
                                        default "false";
                                        description "Enable detail tracing";
                                    }

                                } // container all

                            }
                            case selected-events {

                                container adjacency {
                                    presence "Enable the adjacency context";
                                    description "Enable the adjacency context";

                                } // container adjacency

                                container db {
                                    presence "Enable the db context";
                                    description "Enable the db context";

                                    leaf group-address {
                                        type types-sros:ip-multicast-address;
                                        description "IP multicast group address used to trace events";
                                    }

                                    leaf source-address {
                                        type types-sros:ip-address;
                                        description "Source address used to trace events";
                                    }

                                    leaf detail {
                                        type boolean;
                                        default "false";
                                        description "Enable detail tracing";
                                    }

                                } // container db

                                container port {
                                    presence "Enable the port context";
                                    description "Enable the port context";

                                    leaf detail {
                                        type boolean;
                                        default "false";
                                        description "Enable detail tracing";
                                    }

                                    choice origin {
                                        mandatory true;
                                        case sap {

                                            leaf sap-id {
                                                type types-sros:sap;
                                                description "SAP ID";
                                            }

                                        }
                                        case sdp {

                                            leaf sdp-bind-id {
                                                type types-services:sdp-bind-id;
                                                description "SDP bind ID";
                                            }

                                        }
                                        case evpn-mpls {

                                            leaf evpn-mpls {
                                                type empty;
                                                description "Enable tracing for EVPN-MPLS ports";
                                            }

                                        }
                                        case vxlan {
                                            description "Tunnel Endpoint";

                                            leaf vtep {
                                                type types-sros:ip-unicast-address;
                                                description "IP address of the tunnel endpoint";
                                            }

                                            leaf vni {
                                                type types-services:vxlan-vni;
                                                description "VXLAN Network Identifier of the VXLAN binding";
                                            }

                                        }
                                    }
                                } // container port

                                container jp {
                                    presence "Enable the jp context";
                                    description "Enable the jp context";

                                    leaf group-address {
                                        type types-sros:ip-multicast-address;
                                        description "IP multicast group address used to trace events";
                                    }

                                    leaf source-address {
                                        type types-sros:ip-address;
                                        description "Source address used to trace events";
                                    }

                                    leaf detail {
                                        type boolean;
                                        default "false";
                                        description "Enable detail tracing";
                                    }

                                } // container jp

                                container red {
                                    presence "Enable the red context";
                                    description "Enable the red context";

                                    leaf detail {
                                        type boolean;
                                        default "false";
                                        description "Enable detail tracing";
                                    }

                                } // container red

                                container mcs {
                                    presence "Enable the mcs context";
                                    description "Enable the mcs context";

                                    leaf detail {
                                        type boolean;
                                        default "false";
                                        description "Enable detail tracing";
                                    }

                                } // container mcs

                            }
                        }
                    } // container events

                    container packet {
                        presence "Enable the packet context";
                        description "Enable the packet context";

                        choice origin {
                            default "all";
                            case port {

                                container port {
                                    presence "Enable the port context";
                                    description "Enable the port context";

                                    choice origin {
                                        mandatory true;
                                        case sap {

                                            leaf sap-id {
                                                type types-sros:sap;
                                                description "SAP ID";
                                            }

                                        }
                                        case sdp {

                                            leaf sdp-bind-id {
                                                type types-services:sdp-bind-id;
                                                description "SDP bind ID";
                                            }

                                        }
                                        case evpn-mpls {

                                            leaf evpn-mpls {
                                                type empty;
                                                description "Enable tracing for EVPN-MPLS ports";
                                            }

                                        }
                                        case vxlan {
                                            description "Tunnel Endpoint";

                                            leaf vtep {
                                                type types-sros:ip-unicast-address;
                                                description "IP address of the tunnel endpoint";
                                            }

                                            leaf vni {
                                                type types-services:vxlan-vni;
                                                description "VXLAN Network Identifier of the VXLAN binding";
                                            }

                                        }
                                    }
                                } // container port

                            }
                            case all {

                                leaf all-origins {
                                    type empty;
                                    description "Allow tracing on all ports";
                                }

                            }
                        }
                        choice all-or-selected-packets {
                            default "all-packets";
                            case all-packets {

                                leaf all-packet-types {
                                    type empty;
                                    description "Enable PIM debugging for all packets";
                                }

                            }
                            case selected-packets {

                                container packet-types {
                                    description "Enter the packet-types context";

                                    leaf hello {
                                        type boolean;
                                        default "false";
                                        description "Debug Hello packets";
                                    }

                                    leaf jp {
                                        type boolean;
                                        default "false";
                                        description "Debug join and prune packets";
                                    }

                                } // container packet-types

                            }
                        }
                    } // container packet

                } // container pim-snooping

                container spb {
                    presence "Enable the spb context";
                    description "Enable the spb context";

                    container events {
                        presence "Enable the events context";
                        description "Enable the events context";

                        leaf l2db {
                            type boolean;
                            default "false";
                            description "Trace SPB L2DB events";
                        }

                        container adjacency {
                            presence "Enable the adjacency context";
                            description "Enable the adjacency context";

                            choice option {
                                case sap {

                                    leaf sap {
                                        type types-sros:sap;
                                        description "SAP ID";
                                    }

                                }
                                case sdp {

                                    leaf sdp-bind-id {
                                        type types-services:sdp-bind-id;
                                        description "SAP bind ID";
                                    }

                                }
                                case nbr {

                                    leaf system-id {
                                        type types-igp:system-id;
                                        description "System ID";
                                    }

                                }
                            }
                        } // container adjacency

                        container lsdb {
                            presence "Enable the lsdb context";
                            description "Enable the lsdb context";

                            leaf hostname {
                                type types-isis:system-or-lsp-id;
                                description "Host name";
                            }

                        } // container lsdb

                        container spf {
                            presence "Enable the spf context";
                            description "Enable the spf context";

                            leaf system-id {
                                type types-igp:system-id;
                                description "System ID";
                            }

                        } // container spf

                    } // container events

                    container interface {
                        presence "Enable the interface context";
                        description "Enable the interface context";

                        choice origin {
                            case sap {

                                leaf sap {
                                    type types-sros:sap;
                                    description "SAP ID";
                                }

                            }
                            case sdp {

                                leaf sdp-bind-id {
                                    type types-services:sdp-bind-id;
                                    description "SDP bind ID";
                                }

                            }
                        }
                    } // container interface

                    container packet {
                        presence "Enable the packet context";
                        description "Enable the packet context";

                        leaf type {
                            type enumeration {
                                enum none                           { value 0; }
                                enum ptop-hello                     { value 1; }
                                enum l1-hello                       { value 2; }
                                enum l1-psnp                        { value 3; }
                                enum l1-csnp                        { value 4; }
                                enum l1-lsp                         { value 5; }
                            }
                            default "none";
                            description "Packet type";
                        }

                        leaf detail {
                            type boolean;
                            default "false";
                            description "Enable detailed tracing";
                        }

                        choice origin {
                            case sap {

                                leaf sap {
                                    type types-sros:sap;
                                    description "SAP ID";
                                }

                            }
                            case sdp {

                                leaf sdp-bind-id {
                                    type types-services:sdp-bind-id;
                                    description "SDP bind ID";
                                }

                            }
                        }
                    } // container packet

                } // container spb

                container stp {
                    description "Enter the stp context";

                    container events {
                        presence "Enable the events context";
                        description "Enable the events context";

                        choice all-or-selected-events {
                            default "all-events";
                            case all-events {

                                leaf all-events {
                                    type empty;
                                    description "Trace all STP events";
                                }

                            }
                            case selected-events {

                                container event-types {
                                    description "Enter the event-types context";

                                    leaf bpdu {
                                        type boolean;
                                        default "false";
                                        description "Trace received and transmitted BPDUs";
                                    }

                                    leaf core-connectivity {
                                        type boolean;
                                        default "false";
                                        description "Trace STO core connectivity events";
                                    }

                                    leaf exception {
                                        type boolean;
                                        default "false";
                                        description "Trace STP exception events";
                                    }

                                    leaf fsm-state-changes {
                                        type boolean;
                                        default "false";
                                        description "Trace STP FSM state change events";
                                    }

                                    leaf fsm-timers {
                                        type boolean;
                                        default "false";
                                        description "Trace STP FSM timer events";
                                    }

                                    leaf port-role {
                                        type boolean;
                                        default "false";
                                        description "Trace STP port role events";
                                    }

                                    leaf port-state {
                                        type boolean;
                                        default "false";
                                        description "Trace STP port state events";
                                    }

                                } // container event-types

                            }
                        }
                    } // container events

                    list sap {
                        key "sap-id";
                        max-elements 256;
                        description "Add a list entry for sap";

                        leaf sap-id {
                            type types-sros:sap;
                            description "SAP ID";
                        }

                    } // list sap

                    list sdp-bind {
                        key "sdp-bind-id";
                        max-elements 256;
                        description "Add a list entry for sdp-bind";

                        leaf sdp-bind-id {
                            type types-services:sdp-bind-id;
                            description "SDP bind ID";
                        }

                    } // list sdp-bind

                } // container stp

                container mrp {
                    description "Enter the mrp context";

                    container events {
                        presence "Enable the events context";
                        description "Enable the events context";

                        choice all-or-selected-events {
                            default "all-events";
                            case all-events {

                                leaf all-events {
                                    type empty;
                                    description "Trace all MRP events";
                                }

                            }
                            case selected-events {

                                container event-types {
                                    description "Enter the event-types context";

                                    leaf mrpdu {
                                        type boolean;
                                        default "false";
                                        description "Trace received and transmitted PDUs";
                                    }

                                    leaf applicant-sm {
                                        type boolean;
                                        default "false";
                                        description "Trace the applicant state machine";
                                    }

                                    leaf registrant-sm {
                                        type boolean;
                                        default "false";
                                        description "Trace registrant state machine changes";
                                    }

                                    leaf periodic-sm {
                                        type boolean;
                                        default "false";
                                        description "Trace periodic state machine changes";
                                    }

                                    leaf leave-all-sm {
                                        type boolean;
                                        default "false";
                                        description "Trace leave all state machine changes";
                                    }

                                } // container event-types

                            }
                        }
                    } // container events

                    list mmrp-mac {
                        key "mac";
                        max-elements 256;
                        description "Add a list entry for mmrp-mac";

                        leaf mac {
                            type types-sros:mac-address;
                            description "MAC address to trace";
                        }

                    } // list mmrp-mac

                    list mvrp-vlan {
                        key "vlan";
                        max-elements 256;
                        description "Add a list entry for mvrp-vlan";

                        leaf vlan {
                            type int32 {
                                range "0..4094";
                            }
                            description "VLAN ID to trace";
                        }

                    } // list mvrp-vlan

                    list sap {
                        key "sap-id";
                        max-elements 256;
                        description "Add a list entry for sap";

                        leaf sap-id {
                            type types-sros:sap;
                            description "SAP ID to trace";
                        }

                    } // list sap

                    list sdp-bind {
                        key "sdp-bind-id";
                        max-elements 256;
                        description "Add a list entry for sdp-bind";

                        leaf sdp-bind-id {
                            type types-services:sdp-bind-id;
                            description "SDP ID to trace";
                        }

                    } // list sdp-bind

                } // container mrp

                container proxy-arp {
                    description "Enter the proxy-arp context";

                    choice source {
                        case mac {

                            container mac {
                                description "Enter the mac context";

                                list address {
                                    key "address";
                                    max-elements 256;
                                    description "Add a list entry for address";

                                    leaf address {
                                        type types-sros:mac-address;
                                        description "MAC address of the proxy ARP session to debug";
                                    }

                                } // list address

                            } // container mac

                        }
                        case ip {

                            container ip {
                                description "Enter the ip context";

                                list address {
                                    key "ipv4-address";
                                    max-elements 256;
                                    description "Add a list entry for address";

                                    leaf ipv4-address {
                                        type types-sros:ipv4-unicast-address;
                                        description "IPv4 address of the proxy ARP session to debug";
                                    }

                                } // list address

                            } // container ip

                        }
                        case all {

                            leaf all {
                                type empty;
                                description "Debug the proxy ARP function for all addresses";
                            }

                        }
                    }
                } // container proxy-arp

                container proxy-nd {
                    description "Enter the proxy-nd context";

                    choice source {
                        case mac {

                            container mac {
                                description "Enter the mac context";

                                list address {
                                    key "address";
                                    max-elements 256;
                                    description "Add a list entry for address";

                                    leaf address {
                                        type types-sros:mac-address;
                                        description "MAC address of the proxy ND session to debug";
                                    }

                                } // list address

                            } // container mac

                        }
                        case ip {

                            container ip {
                                description "Enter the ip context";

                                list address {
                                    key "ipv6-address";
                                    max-elements 256;
                                    description "Add a list entry for address";

                                    leaf ipv6-address {
                                        type types-sros:ipv6-address;
                                        description "IPv6 address of the proxy ND session to debug";
                                    }

                                } // list address

                            } // container ip

                        }
                        case all {

                            leaf all {
                                type empty;
                                description "Debug the proxy ND function for all addresses";
                            }

                        }
                    }
                } // container proxy-nd

            } // list vpls

            list vprn {
                key "service-name";
                description "Enter the vprn list instance";

                leaf service-name {
                    type types-services:service-name;
                    description "Administrative service name";
                }

                container ppp {
                    description "Enter the ppp context";

                    list circuit-id {
                        key "id";
                        max-elements 8;
                        description "Add a list entry for circuit-id";

                        leaf id {
                            type string {
                                length "1..255";
                            }
                            description "Circuit ID of the PPPoE session to debug";
                        }

                    } // list circuit-id

                    container events {
                        presence "Enable the events context";
                        description "Enable the events context";

                        choice all-or-selected-events {
                            mandatory true;
                            case all-events {

                                leaf all {
                                    type empty;
                                    description "Enable PPP debugging for all events";
                                }

                            }
                            case selected-events {

                                container dhcp-client {
                                    presence "Enable the dhcp-client context";
                                    description "Enable the dhcp-client context";

                                    leaf terminate-only {
                                        type boolean;
                                        default "false";
                                        description "Debug events for ungraceful terminated sessions only";
                                    }

                                } // container dhcp-client

                                container l2tp {
                                    presence "Enable the l2tp context";
                                    description "Enable the l2tp context";

                                    leaf terminate-only {
                                        type boolean;
                                        default "false";
                                        description "Debug events for ungraceful terminated sessions only";
                                    }

                                } // container l2tp

                                container local-address-assignment {
                                    presence "Enable the local-address-assignment context";
                                    description "Enable the local-address-assignment context";

                                    leaf terminate-only {
                                        type boolean;
                                        default "false";
                                        description "Debug events for ungraceful terminated sessions only";
                                    }

                                } // container local-address-assignment

                                container ppp {
                                    presence "Enable the ppp context";
                                    description "Enable the ppp context";

                                    leaf terminate-only {
                                        type boolean;
                                        default "false";
                                        description "Debug events for ungraceful terminated sessions only";
                                    }

                                } // container ppp

                            }
                        }
                    } // container events

                    list mac {
                        key "address";
                        max-elements 8;
                        description "Add a list entry for mac";

                        leaf address {
                            type types-sros:mac-address;
                            description "MAC address of the PPPoE session to debug";
                        }

                    } // list mac

                    container packets {
                        presence "Enable the packets context";
                        description "Enable the packets context";

                        leaf detail-level {
                            type enumeration {
                                enum low                            { value 0; }
                                enum medium                         { value 1; }
                                enum high                           { value 2; }
                            }
                            default "high";
                            description "Detail level of the PPP packet debug output";
                        }

                        leaf mode {
                            type enumeration {
                                enum dropped-only                   { value 1; }
                                enum ingress-and-dropped            { value 2; }
                                enum egress-ingress-and-dropped     { value 3; }
                            }
                            default "dropped-only";
                            description "PPP packets present in the debug output";
                        }

                        choice all-or-selected-packets {
                            mandatory true;
                            case all-packets {

                                leaf all {
                                    type empty;
                                    description "Enable PPP debugging for all packets";
                                }

                            }
                            case selected-packets {

                                leaf dhcp-client {
                                    type boolean;
                                    default "false";
                                    description "Enable DHCP client packet debugging";
                                }

                                container discovery {
                                    description "Enter the discovery context";

                                    choice all-or-selected-discovery-packets {
                                        case all-discovery-packets {

                                            leaf all {
                                                type empty;
                                                description "Enable PPP debugging for all discovery packets";
                                            }

                                        }
                                        case selected-discovery-packets {

                                            leaf padi {
                                                type boolean;
                                                default "false";
                                                description "Enable PPP debugging for PADI discovery packets";
                                            }

                                            leaf pado {
                                                type boolean;
                                                default "false";
                                                description "Enable PPP debugging for PADO discovery packets";
                                            }

                                            leaf padr {
                                                type boolean;
                                                default "false";
                                                description "Enable PPP debugging for PADR discovery packets";
                                            }

                                            leaf pads {
                                                type boolean;
                                                default "false";
                                                description "Enable PPP debugging for PADS discovery packets";
                                            }

                                            leaf padt {
                                                type boolean;
                                                default "false";
                                                description "Enable PPP debugging for PADT discovery packets";
                                            }

                                        }
                                    }
                                } // container discovery

                                container ppp-session {
                                    description "Enter the ppp-session context";

                                    choice all-or-selected-ppp-session-packets {
                                        case all-ppp-session-packets {

                                            leaf all {
                                                type empty;
                                                description "Enable PPP debugging for all PPP session packets";
                                            }

                                        }
                                        case selected-ppp-session-packets {

                                            leaf lcp {
                                                type boolean;
                                                default "false";
                                                description "Enable PPP debugging for LCP link establishment packets";
                                            }

                                            leaf pap {
                                                type boolean;
                                                default "false";
                                                description "Enable PPP debugging for PAP authentication packets";
                                            }

                                            leaf chap {
                                                type boolean;
                                                default "false";
                                                description "Enable PPP debugging for CHAP authentication packets";
                                            }

                                            leaf ipcp {
                                                type boolean;
                                                default "false";
                                                description "Enable PPP debugging for IPCP NCP packets";
                                            }

                                            leaf ipv6cp {
                                                type boolean;
                                                default "false";
                                                description "Enable PPP debugging for IPv6CP NCP packets";
                                            }

                                        }
                                    }
                                } // container ppp-session

                            }
                        }
                    } // container packets

                    list remote-id {
                        key "id";
                        max-elements 8;
                        description "Add a list entry for remote-id";

                        leaf id {
                            type string {
                                length "1..255";
                            }
                            description "Remote ID of the PPPoE session to debug";
                        }

                    } // list remote-id

                    list user-name {
                        key "name";
                        max-elements 8;
                        description "Add a list entry for user-name";

                        leaf name {
                            type string {
                                length "1..255";
                            }
                            description "Username of the PPPoE session to debug";
                        }

                    } // list user-name

                    list sap {
                        key "sap-id";
                        max-elements 8;
                        description "Add a list entry for sap";

                        leaf sap-id {
                            type types-sros:sap;
                            description "SAP ID of the PPPoE session to debug";
                        }

                    } // list sap

                } // container ppp

            } // list vprn

        } // container service

        container subscriber-mgmt {
            description "Enter the subscriber-mgmt context";

            container gtp {
                description "Enter the gtp context";

                leaf events {
                    type boolean;
                    default "false";
                    description "Enable GTP event debugging";
                }

                container packets {
                    presence "Enable the packets context";
                    description "Enable the packets context";

                    leaf mode {
                        type enumeration {
                            enum all                            { value 1; }
                            enum dropped                        { value 2; }
                        }
                        default "dropped";
                        description "GTP packets to include in the debug output";
                    }

                    leaf detail-level {
                        type enumeration {
                            enum high                           { value 1; }
                            enum low                            { value 2; }
                        }
                        default "low";
                        description "Detail level of the GTP packet debug output";
                    }

                } // container packets

                list imsi {
                    key "imsi-instance";
                    max-elements 8;
                    description "Add a list entry for imsi";

                    leaf imsi-instance {
                        type string {
                            length "0..15";
                            pattern "[0-9]+";
                        }
                        description "IMSI of GTP sessions to debug";
                    }

                } // list imsi

                list peer {
                    key "address router";
                    max-elements 8;
                    description "Enter the peer list instance";

                    leaf address {
                        type types-sros:ip-unicast-address;
                        description "Remote IP address of the GTP peer";
                    }

                    leaf router {
                        type string;
                        description "Router instance where GTP peer packets are expected";
                    }

                    leaf udp-port {
                        type types-sros:tcp-udp-port;
                        default "2123";
                        description "UDP source (Rx packets) / destination (Tx packets) port";
                    }

                } // list peer

            } // container gtp

        } // container subscriber-mgmt

        container system {
            description "Enter the system context";

            container management-interface {
                description "Enter the management-interface context";

                leaf netconf {
                    type enumeration {
                        enum error                          { value 1; }
                        enum warning                        { value 2; }
                        enum info                           { value 3; }
                    }
                    description "Debugging verbosity for NETCONF";
                }

                container remote-management {
                    description "Enter the remote-management context";

                    leaf service {
                        type boolean;
                        default "false";
                        description "Enable service level debug";
                    }

                    container manager {
                        description "Enter the manager context";

                        choice managers {
                            case all {

                                leaf all {
                                    type empty;
                                    description "Enable debug of all managers";
                                }

                            }
                            case specific-managers {

                                list manager-name {
                                    key "name";
                                    description "Add a list entry for manager-name";

                                    leaf name {
                                        type types-sros:named-item-64;
                                        description "Manager name";
                                    }

                                } // list manager-name

                            }
                        }
                    } // container manager

                } // container remote-management

            } // container management-interface

            container grpc {
                description "Enter the grpc context";

                leaf-list type {
                    type enumeration {
                        enum gnmi-capabilities              { value 1; }
                        enum gnmi-get                       { value 2; }
                        enum gnmi-set                       { value 3; }
                        enum gnmi-subscribe                 { value 4; }
                        enum rib-api-modify                 { value 5; }
                        enum rib-api-getversion             { value 6; }
                        enum gnoi-cert-mgmt-rpcs            { value 7; }
                        enum gnoi-file-rpcs                 { value 8; }
                        enum gnoi-system-rpcs               { value 9; }
                    }
                    max-elements 10;
                    description "RPCs or service types to debug";
                }

                container client {
                    description "Enter the client context";

                    choice address {
                        case ip-address {

                            leaf ip-address {
                                type types-sros:ip-address;
                                description "IP address for debugging";
                            }

                        }
                        case all {

                            leaf all {
                                type empty;
                                description "Set debugging for all clients";
                            }

                        }
                    }
                } // container client

            } // container grpc

            container grpc-tunnel {
                description "Enter the grpc-tunnel context";

                container tunnel {
                    description "Enter the tunnel context";

                    choice tunnel {
                        case name {

                            leaf name {
                                type types-sros:named-item;
                                description "Name of the tunnel to restrict the debug output";
                            }

                        }
                        case all {

                            leaf all {
                                type empty;
                                description "Set debug output for all tunnels";
                            }

                        }
                    }
                } // container tunnel

            } // container grpc-tunnel

            container http-connections {
                presence "Enable the http-connections context";
                description "Enable the http-connections context";

                leaf client-ip-prefix {
                    type union {
                        type types-sros:ip-prefix;
                        type enumeration {
                            enum any                            { value -1; }
                        }
                    }
                    default "any";
                    description "HTTP client IP prefix";
                }

            } // container http-connections

        } // container system


        container wlan-gw {
            description "Enter the wlan-gw context";

            list group {
                key "id";
                max-elements 1;
                description "Enter the group list instance";

                leaf id {
                    type types-isa:wlan-gw-group-id;
                    description "WLAN-GW group ID in the system";
                }

                container learn-ap-mac {
                    presence "Enable the learn-ap-mac context";
                    description "Enable the learn-ap-mac context";

                    leaf tunnel-remote-address {
                        type types-sros:ip-address;
                        mandatory true;
                        description "IP address of the remote tunnel endpoint";
                    }

                } // container learn-ap-mac

                list statistic {
                    key "type name";
                    description "Enter the statistic list instance";

                    leaf type {
                        type enumeration {
                            enum packet-error {
                                value 0;
                                description "Packet related error";
                            }
                            enum host-error {
                                value 1;
                                description "Host related error";
                            }
                            enum bd-error {
                                value 2;
                                description "Bridge domain related error";
                            }
                            enum forwarding {
                                value 3;
                                description "Number of forwarded packets";
                            }
                            enum reassembly {
                                value 4;
                                description "Reassembly related statistic";
                            }
                            enum aa {
                                value 5;
                                description "AA related statistic";
                            }
                            enum radius {
                                value 6;
                                description "RADIUS related statistic";
                            }
                            enum arp {
                                value 7;
                                description "ARP related statistic";
                            }
                            enum dhcp4 {
                                value 8;
                                description "DHCP related statistic";
                            }
                            enum dhcp6 {
                                value 9;
                                description "DHCPv6 related statistic";
                            }
                            enum icmp4 {
                                value 10;
                                description "ICMP related statistic";
                            }
                            enum icmp6 {
                                value 11;
                                description "ICMPv6 related statistic";
                            }
                        }
                        description "Type of statistic to trace";
                    }

                    leaf name {
                        type types-sros:named-item-64;
                        description "Name of the statistic to trace";
                    }

                    leaf capture-packet {
                        type boolean;
                        default "false";
                        description "Set a single packet capture trigger for the statistic";
                    }

                } // list statistic

                container ue {
                    presence "Enable the ue context";
                    description "Enable the ue context";

                    leaf bridge-domain {
                        type uint32 {
                            range "1..4294967295";
                        }
                        description "Bridge domain of the UEs to debug";
                    }

                    leaf mac-address {
                        type types-sros:mac-address;
                        description "MAC address of the UE to debug";
                    }

                    container protocols {
                        presence "Enable the protocols context";
                        description "Enable the protocols context";

                        leaf arp {
                            type boolean;
                            default "false";
                            description "Enable debugging for the ARP protocol";
                        }

                        leaf dhcp4 {
                            type boolean;
                            default "false";
                            description "Enable debugging for the DHCP protocol";
                        }

                        leaf dhcp6 {
                            type boolean;
                            default "false";
                            description "Enable debugging for the DHCPv6 protocol";
                        }

                        leaf icmp4 {
                            type boolean;
                            default "false";
                            description "Enable debugging for the ICMP protocol";
                        }

                        leaf icmp6 {
                            type boolean;
                            default "false";
                            description "Enable debugging for the ICMPv6 protocol";
                        }

                        leaf radius {
                            type boolean;
                            default "false";
                            description "Enable debugging for the RADIUS protocol";
                        }

                    } // container protocols

                } // container ue

            } // list group

        } // container wlan-gw

    } // container debug

}
