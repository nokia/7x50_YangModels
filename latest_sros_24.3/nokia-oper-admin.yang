module nokia-oper-admin {

    yang-version "1.1";

    namespace "urn:nokia.com:sros:ns:yang:sr:oper-admin";

    prefix "oper-admin";

    import ietf-yang-types                { prefix "yang"; }
    import nokia-sros-yang-extensions     { prefix "sros-ext"; }
    import nokia-state                    { prefix "state"; }
    import nokia-types-operation          { prefix "types-operation"; }
    import nokia-types-security           { prefix "types-security"; }
    import nokia-types-sros               { prefix "types-sros"; }

    sros-ext:sros-major-release "rel24";
    organization "Nokia";
    contact
        "Nokia SR OS Support
         Web: <http://www.nokia.com>";
    description
        "Nokia YANG Data model for admin actions on SR OS based routers.

         Copyright 2016 Nokia. All rights reserved. Reproduction of this document
         is authorized on the condition that the foregoing copyright notice is included.

         This nokia-oper-admin YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2016-01-01";

    typedef configuration-region {
        type enumeration {
            enum configure                      { value 0; }
            enum li                             { value 1; }
        }
        default "configure";
        description "The configuration region specify region which is used";
    }

    typedef cli-path-type {
        type string;
        description "Path type used for path infrastructure";
    }

    container admin {
        config false;
        description "Enter the administrative context for system operations";

        action disconnect {
            description "Disconnect a user session";

            input {

                leaf op-table-bypass {
                    type types-operation:operation-op-table-bypass;
                    description "Avoid operation ID allocation";
                }

                leaf address {
                    type types-sros:ip-address;
                    description "IP address of the session to disconnect";
                }

                leaf session-id {
                    type uint32 {
                        range "1..4294967295";
                    }
                    description "ID of the session to disconnect";
                }

                leaf session-type {
                    type enumeration {
                        enum console                        { value 1; }
                        enum bluetooth                      { value 2; }
                        enum telnet                         { value 3; }
                        enum ssh                            { value 4; }
                        enum ftp                            { value 5; }
                        enum netconf                        { value 6; }
                        enum grpc                           { value 7; }
                        enum cron-ehs                       { value 8; }
                    }
                    description "Type of session to disconnect";
                }

                leaf username {
                    type types-sros:named-item;
                    description "Username to disconnect";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action disconnect

        action reboot {
            description "Reboot CPM or force an upgrade of system boot ROMs";

            input {

                leaf now {
                    type empty;
                    description "Reboot immediately without prompts or confirmation";
                }

                leaf card {
                    type enumeration {
                        enum active                         { value 1; }
                        enum standby                        { value 2; }
                        enum upgrade                        { value 3; }
                    }
                    description "Card to reboot";
                }

                leaf hold {
                    type empty;
                    description "Hold a rebooted standby CPM from coming back online";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action reboot

        action tech-support {
            description "Save technical support information to a file";

            input {

                leaf url {
                    type types-sros:url;
                    description "URL to save technical support information";
                }

            }
            output {

                leaf operation-id {
                    type types-operation:operation-id;
                    description "ID assigned to the operation.";
                }

                leaf start-time {
                    type types-operation:operation-timestamp;
                    description "Time when the operation started its execution.";
                }

                leaf results-path {
                    type types-operation:operation-path;
                    description "Path to the results of the operation formatted as xpath.";
                }

                leaf status {
                    type types-operation:operation-status;
                    description "Status of the operation";
                }

                leaf-list error-message {
                    type types-operation:operation-message;
                    description "Error messages reported during execution of the operation.";
                }

                leaf-list warning-message {
                    type types-operation:operation-message;
                    description "Warning messages reported during execution of the operation.";
                }

                leaf-list info-message {
                    type types-operation:operation-message;
                    description "Info messages reported during execution of the operation.";
                }

                leaf end-time {
                    type types-operation:operation-timestamp;
                    description "Time when the operation ended its execution.";
                }

            }
        } // action tech-support

        container application-assurance {
            description "Enter the application-assurance context";

            action upgrade {
                description "Upgrade to a new isa-aa.tim file";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action upgrade

            list group {
                key "aa-group-id";
                description "Enter the group list instance";

                leaf aa-group-id {
                    type leafref {
                        path "/state:state/state:application-assurance/state:group/state:aa-group-id";
                    }
                    description "AA group ID";
                }

                list url-list {
                    key "url-list-name";
                    description "Enter the url-list list instance";

                    leaf url-list-name {
                        type leafref {
                            path "/state:state/state:application-assurance/state:group[state:aa-group-id=current()/../../aa-group-id]/state:url-list/state:url-list-name";
                        }
                        description "AA URL list name";
                    }

                    action upgrade {
                        description "Upgrade the referenced URL list";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action upgrade

                } // list url-list

            } // list group

        } // container application-assurance

        container clear {
            description "Enter the clear context";

            container security {
                description "Enter the security context";

                action lockout {
                    description "Reset the lockout timer";

                    input {

                        choice lockout-options {
                            mandatory true;
                            case user-name {

                                leaf user {
                                    type types-sros:named-item;
                                    description "User to be cleared of lockout";
                                }

                            }
                            case all {

                                leaf all {
                                    type empty;
                                    description "Clear lockout of all users";
                                }

                            }
                        }
                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lockout

                action password-history {
                    description "Clear the password history";

                    input {

                        choice password-history-options {
                            mandatory true;
                            case user-name {

                                leaf user {
                                    type types-sros:named-item;
                                    description "User to be cleared of password history information";
                                }

                            }
                            case all {

                                leaf all {
                                    type empty;
                                    description "Clear password history of all users";
                                }

                            }
                        }
                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action password-history

            } // container security

        } // container clear

        container nat {
            description "Enter the nat context";

            action save-deterministic-script {
                description "Save script that computes deterministic NAT map entries";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action save-deterministic-script

        } // container nat

        container redundancy {
            description "Enter the redundancy context";

            action force-switchover {
                description "Force a switchover to the standby CPM";

                input {

                    leaf now {
                        type empty;
                        description "Force the switchover to the standby CPM immediately";
                    }

                    leaf ignore-status {
                        type empty;
                        description "Switch to the standby CPM regardless of its status";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action force-switchover

            action synchronize {
                description "Synchronize the standby CPM";

                input {

                    choice synchronize {
                        mandatory true;
                        case boot-environment {

                            leaf boot-environment {
                                type empty;
                                description "Synchronize all files required for the boot process";
                            }

                        }
                        case configuration {

                            leaf configuration {
                                type empty;
                                description "Synchronize the configuration files";
                            }

                        }
                        case certificate {

                            leaf certificate {
                                type empty;
                                description "Synchronize imported certificate, key, and CRL files";
                            }

                        }
                    }
                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action synchronize

        } // container redundancy

        container satellite {
            description "Perform administrative operations for satellites";

            list ethernet-satellite {
                key "satellite-id";
                description "Enter the ethernet-satellite list instance";

                leaf satellite-id {
                    type leafref {
                        path "/state:state/state:satellite/state:ethernet-satellite/state:satellite-id";
                    }
                    description "Satellite ID";
                }

                action reboot {
                    description "Initiate an administrative reboot of the chassis";

                    input {

                        leaf now {
                            type empty;
                            description "Reboot immediately without prompts or confirmation";
                        }

                        leaf upgrade {
                            type empty;
                            description "Initiate a firmware image update during the reboot";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action reboot

                action synchronize {
                    description "Synchronize the chassis to the boot image";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action synchronize

                action tech-support {
                    description "Save satellite technical support information";

                    input {

                        leaf url {
                            type types-sros:url;
                            mandatory true;
                            description "URL to save technical support information";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action tech-support

            } // list ethernet-satellite


        } // container satellite

        container set {
            description "Enter the set context";

            action time {
                description "System date and time";

                input {

                    leaf system-time {
                        type yang:date-and-time;
                        mandatory true;
                        description "System date and time";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action time

        } // container set

        container system {
            description "Enter the system context";

            container security {
                description "Enter the security context";

                container hash-control {
                    description "Enter the hash-control context";

                    action custom-hash {
                        description "Custom encryption";

                        input {

                            leaf algorithm {
                                type enumeration {
                                    enum 3des {
                                        value 0;
                                        description "DES-EDE3-ECB with PKCS #5 padding";
                                    }
                                    enum aes128 {
                                        value 1;
                                        description "AES-128-ECB with PKCS #7 padding";
                                    }
                                    enum aes192 {
                                        value 2;
                                        description "AES-192-ECB with PKCS #7 padding";
                                    }
                                    enum aes256 {
                                        value 3;
                                        description "AES-256-ECB with PKCS #7 padding";
                                    }
                                }
                                mandatory true;
                                description "Algorithm for custom encryption";
                            }

                            leaf key {
                                type string {
                                    length "1..71";
                                }
                                mandatory true;
                                description "Key for encryption algorithm";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action custom-hash

                    action remove-custom-hash {
                        description "Remove the custom encryption";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action remove-custom-hash

                } // container hash-control

                container secure-boot {
                    description "Enter the secure-boot context";

                    action activate {
                        description "Activate secure boot on a CPM";

                        input {

                            leaf card {
                                type leafref {
                                    path "/state:state/state:cpm/state:cpm-slot";
                                }
                                mandatory true;
                                description "CPM slot where secure boot is activated or modified";
                            }

                            leaf confirmation-code {
                                type types-sros:string-not-all-spaces {
                                    length "1..32";
                                }
                                description "Confirmation code";
                            }

                            leaf now {
                                type empty;
                                description "Perform the action immediately";
                            }

                            leaf serial-number {
                                type types-sros:string-not-all-spaces {
                                    length "1..32";
                                }
                                description "CPM card serial number which secure-boot activates";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate

                    action revoke-key {
                        description "Revoke secure boot keys";

                        input {

                            leaf card {
                                type leafref {
                                    path "/state:state/state:cpm/state:cpm-slot";
                                }
                                mandatory true;
                                description "CPM slot where secure boot is activated or modified";
                            }

                            leaf confirmation-code {
                                type types-sros:string-not-all-spaces {
                                    length "1..32";
                                }
                                description "Confirmation code";
                            }

                            leaf now {
                                type empty;
                                description "Perform the action immediately";
                            }

                            leaf serial-number {
                                type types-sros:string-not-all-spaces {
                                    length "1..32";
                                }
                                description "CPM card serial number which secure-boot activates";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action revoke-key

                    action update-key {
                        description "Update secure boot keys";

                        input {

                            leaf card {
                                type leafref {
                                    path "/state:state/state:cpm/state:cpm-slot";
                                }
                                mandatory true;
                                description "CPM slot where secure boot is activated or modified";
                            }

                            leaf confirmation-code {
                                type types-sros:string-not-all-spaces {
                                    length "1..32";
                                }
                                description "Confirmation code";
                            }

                            leaf now {
                                type empty;
                                description "Perform the action immediately";
                            }

                            leaf serial-number {
                                type types-sros:string-not-all-spaces {
                                    length "1..32";
                                }
                                description "CPM card serial number which secure-boot activates";
                            }

                            leaf software-image {
                                type types-sros:cflash-and-url;
                                mandatory true;
                                description "Location of the target software image";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action update-key

                    action validate {
                        description "Validate software signature for the specified image";

                        input {

                            leaf software-image {
                                type types-sros:cflash-and-url;
                                mandatory true;
                                description "Location of the target software image";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action validate

                } // container secure-boot

                action system-password {
                    description "Change a local system password";

                    input {

                        leaf admin-password {
                            type empty;
                            mandatory true;
                            description "Administrative password";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action system-password

                container pki {
                    description "Perform PKI related operations";

                    action clear-ocsp-cache {
                        description "Clear the current OCSP response cache";

                        input {

                            leaf entry-id {
                                type uint32 {
                                    range "1..2000";
                                }
                                description "Local OCSP response cache entry ID to clear";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action clear-ocsp-cache

                    container cmpv2 {
                        description "Perform CMPv2 operations";

                        action cert-request {
                            description "Request an additional certificate";

                            input {

                                leaf ca-profile {
                                    type leafref {
                                        path "/state:state/state:system/state:security/state:pki/state:ca-profile/state:ca-profile-name";
                                    }
                                    mandatory true;
                                    description "PKI CA profile name";
                                }

                                leaf current-key {
                                    type types-security:pki-file-name;
                                    mandatory true;
                                    description "Imported key file used to create the request";
                                }

                                leaf current-certificate {
                                    type types-security:pki-file-name;
                                    mandatory true;
                                    description "Existing imported certificate file to create request";
                                }

                                leaf new-key {
                                    type types-security:pki-file-name;
                                    mandatory true;
                                    description "New imported key file to create certificate request";
                                }

                                leaf hash-algorithm {
                                    type types-security:hash-algorithm;
                                    description "Hash algorithm used for the certificate signature";
                                }

                                leaf subject-dn {
                                    type string {
                                        length "1..256";
                                    }
                                    description "Subject of the requesting certificate";
                                }

                                leaf domain-name {
                                    type string {
                                        length "1..512";
                                    }
                                    description "FQDNs for the Subject Alternative Name";
                                }

                                leaf ip-address {
                                    type types-sros:ip-address;
                                    description "IP address for the Subject Alternative Name";
                                }

                                leaf save-as {
                                    type types-sros:cflash-url;
                                    mandatory true;
                                    description "Full path to save the result certificate";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    container request-parameters {
                                        description "Enter the request-parameters context";

                                        leaf ca-profile {
                                            type string {
                                                length "1..32";
                                            }
                                            description "The pki ca-profile name";
                                        }

                                        leaf save-as {
                                            type types-sros:cflash-url;
                                            description "Path to result certificate file";
                                        }

                                        leaf current-key {
                                            type types-security:pki-file-name;
                                        }

                                        leaf current-certificate {
                                            type types-security:pki-file-name;
                                        }

                                        leaf new-key {
                                            type types-security:pki-file-name;
                                        }

                                        leaf hash-algorithm {
                                            type types-security:hash-algorithm;
                                            description "Hash algorithm used for the certificate signature";
                                        }

                                        leaf subject-dn {
                                            type string {
                                                length "1..256";
                                            }
                                            description "Subject of the requesting certificate";
                                        }

                                        leaf domain-name {
                                            type string {
                                                length "1..512";
                                            }
                                            description "FQDNs for the Subject Alternative Name";
                                        }

                                        leaf ip-address {
                                            type types-sros:ip-address;
                                            description "IP address for the Subject Alternative Name";
                                        }

                                    } // container request-parameters

                                    leaf last-ca-response-time {
                                        type yang:date-and-time;
                                        description "Time when CA last response";
                                    }

                                    leaf transaction-status {
                                        type types-security:cmpv2-transaction-status;
                                        description "CMPv2 transaction status";
                                    }

                                    leaf transaction-status-code {
                                        type types-security:cmpv2-transaction-status-code;
                                        description "CMPv2 transaction status code";
                                    }

                                    leaf transaction-status-string {
                                        type string {
                                            length "1..255";
                                        }
                                        description "CMPv2 transaction extra status info";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action cert-request

                        action clear-request {
                            description "Clear pending CMPv2 requests";

                            input {

                                leaf ca-profile {
                                    type leafref {
                                        path "/state:state/state:system/state:security/state:pki/state:ca-profile/state:ca-profile-name";
                                    }
                                    mandatory true;
                                    description "PKI CA profile name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action clear-request

                        action initial-registration {
                            description "Request initial certificate using the CMPv2 protocol";

                            input {

                                leaf ca-profile {
                                    type leafref {
                                        path "/state:state/state:system/state:security/state:pki/state:ca-profile/state:ca-profile-name";
                                    }
                                    mandatory true;
                                    description "PKI CA profile name";
                                }

                                leaf key-to-certify {
                                    type types-security:pki-file-name;
                                    mandatory true;
                                    description "Name of the key file used to create initial request";
                                }

                                choice protection-algorithm {
                                    mandatory true;
                                    case password {

                                        leaf password {
                                            type string {
                                                length "1..64";
                                            }
                                            description "Password for message protection";
                                        }

                                        leaf reference {
                                            type string {
                                                length "1..64";
                                            }
                                            description "Password reference number";
                                        }

                                    }
                                    case signature {

                                        leaf certificate {
                                            type types-security:pki-file-name;
                                            description "Filename of the certificate for the protection key";
                                        }

                                        leaf send-chain {
                                            type empty;
                                            description "Send a certificate chain";
                                        }

                                        leaf with-ca {
                                            type leafref {
                                                path "/state:state/state:system/state:security/state:pki/state:ca-profile/state:ca-profile-name";
                                            }
                                            description "Name of CA profile with certificate in the send chain";
                                        }

                                        leaf protection-key {
                                            type types-security:pki-file-name;
                                            description "Key file used to generate message protection signature";
                                        }

                                        leaf hash-algorithm {
                                            type types-security:hash-algorithm;
                                            description "Hash algorithm used for the certificate signature";
                                        }

                                    }
                                }
                                leaf subject-dn {
                                    type string {
                                        length "1..256";
                                    }
                                    description "Subject of the requesting certificate";
                                }

                                leaf domain-name {
                                    type string {
                                        length "1..512";
                                    }
                                    description "FQDNs for the Subject Alternative Name";
                                }

                                leaf ip-address {
                                    type types-sros:ip-address;
                                    description "IP address for the Subject Alternative Name";
                                }

                                leaf save-as {
                                    type types-sros:cflash-url;
                                    mandatory true;
                                    description "Full path to save the result certificate";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    container request-parameters {
                                        description "Enter the request-parameters context";

                                        leaf ca-profile {
                                            type string {
                                                length "1..32";
                                            }
                                            description "The pki ca-profile name";
                                        }

                                        leaf save-as {
                                            type types-sros:cflash-url;
                                            description "Path to result certificate file";
                                        }

                                        leaf key-to-certify {
                                            type types-security:pki-file-name;
                                        }

                                        choice protection-algorithm {
                                            case password {

                                                leaf reference {
                                                    type string {
                                                        length "1..64";
                                                    }
                                                }

                                            }
                                            case signature {

                                                leaf certificate {
                                                    type types-security:pki-file-name;
                                                }

                                                leaf send-chain {
                                                    type empty;
                                                }

                                                leaf with-ca {
                                                    type string {
                                                        length "1..32";
                                                    }
                                                }

                                                leaf protection-key {
                                                    type types-security:pki-file-name;
                                                }

                                                leaf hash-algorithm {
                                                    type types-security:hash-algorithm;
                                                    description "Hash algorithm used for the certificate signature";
                                                }

                                            }
                                        }
                                        leaf subject-dn {
                                            type string {
                                                length "1..256";
                                            }
                                            description "Subject of the requesting certificate";
                                        }

                                        leaf domain-name {
                                            type string {
                                                length "1..512";
                                            }
                                            description "FQDNs for the Subject Alternative Name";
                                        }

                                        leaf ip-address {
                                            type types-sros:ip-address;
                                            description "IP address for the Subject Alternative Name";
                                        }

                                    } // container request-parameters

                                    leaf ca-profile {
                                        type string {
                                            length "1..32";
                                        }
                                        description "The pki ca-profile name";
                                    }

                                    leaf save-as {
                                        type types-sros:cflash-url;
                                        description "Path to result certificate file";
                                    }

                                    leaf last-ca-response-time {
                                        type yang:date-and-time;
                                        description "Time when CA last response";
                                    }

                                    leaf transaction-status {
                                        type types-security:cmpv2-transaction-status;
                                        description "CMPv2 transaction status";
                                    }

                                    leaf transaction-status-code {
                                        type types-security:cmpv2-transaction-status-code;
                                        description "CMPv2 transaction status code";
                                    }

                                    leaf transaction-status-string {
                                        type string {
                                            length "1..255";
                                        }
                                        description "CMPv2 transaction extra status info";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action initial-registration

                        action key-update {
                            description "Request new certificate to update existing certificate";

                            input {

                                leaf ca-profile {
                                    type leafref {
                                        path "/state:state/state:system/state:security/state:pki/state:ca-profile/state:ca-profile-name";
                                    }
                                    mandatory true;
                                    description "PKI CA profile name";
                                }

                                leaf new-key {
                                    type types-security:pki-file-name;
                                    mandatory true;
                                    description "Name of new imported key file used for the key update";
                                }

                                leaf old-key {
                                    type types-security:pki-file-name;
                                    mandatory true;
                                    description "Name of the old key file to be replaced";
                                }

                                leaf old-certificate {
                                    type types-security:pki-file-name;
                                    mandatory true;
                                    description "Name of the old certificate file to be replaced";
                                }

                                leaf hash-algorithm {
                                    type types-security:hash-algorithm;
                                    description "Hash algorithm used for the certificate signature";
                                }

                                leaf save-as {
                                    type types-sros:cflash-url;
                                    mandatory true;
                                    description "Full path to save the result certificate file";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    container request-parameters {
                                        description "Enter the request-parameters context";

                                        leaf ca-profile {
                                            type string {
                                                length "1..32";
                                            }
                                            description "The pki ca-profile name";
                                        }

                                        leaf save-as {
                                            type types-sros:cflash-url;
                                            description "Path to result certificate file";
                                        }

                                        leaf new-key {
                                            type types-security:pki-file-name;
                                        }

                                        leaf old-key {
                                            type types-security:pki-file-name;
                                        }

                                        leaf old-certificate {
                                            type types-security:pki-file-name;
                                        }

                                        leaf hash-algorithm {
                                            type types-security:hash-algorithm;
                                            description "Hash algorithm used for the certificate signature";
                                        }

                                    } // container request-parameters

                                    leaf last-ca-response-time {
                                        type yang:date-and-time;
                                        description "Time when CA last response";
                                    }

                                    leaf transaction-status {
                                        type types-security:cmpv2-transaction-status;
                                        description "CMPv2 transaction status";
                                    }

                                    leaf transaction-status-code {
                                        type types-security:cmpv2-transaction-status-code;
                                        description "CMPv2 transaction status code";
                                    }

                                    leaf transaction-status-string {
                                        type string {
                                            length "1..255";
                                        }
                                        description "CMPv2 transaction extra status info";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action key-update

                        action poll {
                            description "Poll the CMPv2 server for pending request status";

                            input {

                                leaf ca-profile {
                                    type leafref {
                                        path "/state:state/state:system/state:security/state:pki/state:ca-profile/state:ca-profile-name";
                                    }
                                    mandatory true;
                                    description "PKI CA profile name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf request-type {
                                        type types-security:cmpv2-request-type;
                                        description "CMPv2 request type";
                                    }

                                    leaf ca-profile {
                                        type string {
                                            length "1..32";
                                        }
                                        description "The pki ca-profile name";
                                    }

                                    leaf save-as {
                                        type types-sros:cflash-url;
                                        description "Path to result certificate file";
                                    }

                                    leaf last-ca-response-time {
                                        type yang:date-and-time;
                                        description "Time when CA last response";
                                    }

                                    leaf transaction-status {
                                        type types-security:cmpv2-transaction-status;
                                        description "CMPv2 transaction status";
                                    }

                                    leaf transaction-status-code {
                                        type types-security:cmpv2-transaction-status-code;
                                        description "CMPv2 transaction status code";
                                    }

                                    leaf transaction-status-string {
                                        type string {
                                            length "1..255";
                                        }
                                        description "CMPv2 transaction extra status info";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action poll

                    } // container cmpv2

                    action convert-file {
                        description "Convert imported file between secure and legacy format";

                        input {

                            leaf input-file {
                                type types-security:pki-file-name;
                                mandatory true;
                                description "Name of the file to be converted";
                            }

                            leaf output-file {
                                type types-security:pki-file-name;
                                mandatory true;
                                description "Output filename";
                            }

                            leaf format {
                                type types-security:cert-file-convert-format;
                                mandatory true;
                                description "File format to convert to";
                            }

                            leaf force {
                                type empty;
                                description "Force the conversion";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action convert-file

                    action crl-update {
                        description "Trigger the CRL update for the CA profile";

                        input {

                            leaf ca-profile {
                                type leafref {
                                    path "/state:state/state:system/state:security/state:pki/state:ca-profile/state:ca-profile-name";
                                }
                                mandatory true;
                                description "PKI CA profile name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action crl-update

                    container est {
                        description "Perform Enrollment over Secure Transport operations";

                        action ca-certificates {
                            description "Download CA certificates from the EST server";

                            input {

                                leaf est-profile {
                                    type string {
                                        length "1..32";
                                    }
                                    mandatory true;
                                    description "PKI EST profile name";
                                }

                                leaf output-url {
                                    type types-sros:cflash-url;
                                    mandatory true;
                                    description "Path to the result file";
                                }

                                leaf force {
                                    type empty;
                                    description "Force an overwrite of the result file";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action ca-certificates

                        action enroll {
                            description "Enroll a new certificate with CA with the EST protocol";

                            input {

                                leaf est-profile {
                                    type string {
                                        length "1..32";
                                    }
                                    mandatory true;
                                    description "PKI EST profile name";
                                }

                                leaf key {
                                    type types-sros:cflash-url;
                                    mandatory true;
                                    description "Name of the imported the key file to enroll";
                                }

                                leaf hash-algorithm {
                                    type types-security:hash-algorithm;
                                    description "Hash algorithm used for the certificate signature";
                                }

                                leaf subject-dn {
                                    type string {
                                        length "1..256";
                                    }
                                    description "Subject of the requesting certificate";
                                }

                                leaf domain-name {
                                    type string {
                                        length "1..512";
                                    }
                                    description "FQDNs for the Subject Alternative Name";
                                }

                                leaf ip-address {
                                    type types-sros:ip-address;
                                    description "IP address for the Subject Alternative Name";
                                }

                                leaf output-file {
                                    type types-security:pki-file-name;
                                    mandatory true;
                                    description "Name of the result file";
                                }

                                leaf force {
                                    type empty;
                                    description "Force an overwrite of the result file";
                                }

                                leaf validate-certificate-chain {
                                    type empty;
                                    description "Validate result certificate chain before importing";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action enroll

                        action renew {
                            description "Renew a CA certificate using the EST protocol";

                            input {

                                leaf est-profile {
                                    type string {
                                        length "1..32";
                                    }
                                    mandatory true;
                                    description "PKI EST profile name";
                                }

                                leaf certificate {
                                    type types-sros:cflash-url;
                                    mandatory true;
                                    description "Name of the imported certificate file to renew";
                                }

                                leaf key {
                                    type types-sros:cflash-url;
                                    mandatory true;
                                    description "Imported key file of the certificate to renew";
                                }

                                leaf hash-algorithm {
                                    type types-security:hash-algorithm;
                                    description "Hash algorithm used for the certificate signature";
                                }

                                leaf output-file {
                                    type types-security:pki-file-name;
                                    mandatory true;
                                    description "Name of the result file";
                                }

                                leaf force {
                                    type empty;
                                    description "Force an overwrite of the result file";
                                }

                                leaf validate-certificate-chain {
                                    type empty;
                                    description "Validate result certificate chain before importing";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action renew

                    } // container est

                    action export {
                        description "Export an imported file";

                        input {

                            leaf input-file {
                                type types-security:pki-file-name;
                                mandatory true;
                                description "Name of the file to be exported";
                            }

                            leaf output-url {
                                type types-sros:cflash-url;
                                mandatory true;
                                description "Full path to export the result file";
                            }

                            leaf type {
                                type types-security:cert-export-file-type;
                                mandatory true;
                                description "Type of file to be exported";
                            }

                            leaf format {
                                type types-security:cert-export-file-format;
                                mandatory true;
                                description "Output file format";
                            }

                            leaf password {
                                type string {
                                    length "1..32";
                                }
                                description "Password used to encrypt the output file";
                            }

                            leaf key-file {
                                type types-security:pki-file-name;
                                description "Name of the key file to be exported";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action export

                    action generate-keypair {
                        description "Generate PKI key pair";

                        input {

                            leaf save-path {
                                type types-sros:cflash-url;
                                mandatory true;
                                description "Full path to save the result key file";
                            }

                            choice key-type {
                                mandatory true;
                                case rsa {

                                    leaf rsa-key-size {
                                        type uint32 {
                                            range "512..8192";
                                        }
                                        default "2048";
                                        description "Length of the RSA key to be generated";
                                    }

                                }
                                case dsa {

                                    leaf dsa-key-size {
                                        type uint32 {
                                            range "512..8192";
                                        }
                                        default "2048";
                                        description "Length of the DSA key to be generated";
                                    }

                                }
                                case ecdsa {

                                    leaf ecdsa-curve {
                                        type types-security:ecdsa-curve;
                                        default "secp256r1";
                                        description "Elliptic curve of the ECDSA key to be generated";
                                    }

                                }
                            }
                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action generate-keypair

                    action generate-csr {
                        description "Generate a PKCS#10 certificate signing request file";

                        input {

                            leaf key-url {
                                type types-sros:cflash-url;
                                mandatory true;
                                description "Full path to the key file used to generate the request";
                            }

                            leaf hash-algorithm {
                                type types-security:hash-algorithm;
                                description "Hash algorithm used for the certificate signature";
                            }

                            leaf subject-dn {
                                type string {
                                    length "1..256";
                                }
                                description "Subject of the requesting certificate";
                            }

                            leaf domain-name {
                                type string {
                                    length "1..512";
                                }
                                description "FQDNs for the Subject Alternative Name";
                            }

                            leaf ip-address {
                                type types-sros:ip-address;
                                description "IP address for the Subject Alternative Name";
                            }

                            leaf output-url {
                                type types-sros:cflash-url;
                                mandatory true;
                                description "Full path to result certificate signing request file";
                            }

                            leaf use-printable {
                                type empty;
                                description "Force ASCII encoding for input subject DN attributes";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action generate-csr

                    action import {
                        description "Import a certificate related file";

                        input {

                            leaf input-url {
                                type types-sros:cflash-url;
                                mandatory true;
                                description "Full path to the file to import";
                            }

                            leaf output-file {
                                type types-security:pki-file-name;
                                mandatory true;
                                description "Name of the result file";
                            }

                            leaf type {
                                type types-security:cert-export-file-type;
                                mandatory true;
                                description "Type of file to be exported";
                            }

                            leaf format {
                                type types-security:cert-export-file-format;
                                mandatory true;
                                description "Output file format";
                            }

                            leaf password {
                                type string {
                                    length "1..32";
                                }
                                description "Password used to encrypt the output file";
                            }

                            leaf validate-certificate-chain {
                                type empty;
                                description "Validate the certificate chain";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action import

                    action reload {
                        description "Reload key or certificate files";

                        input {

                            leaf application {
                                type enumeration {
                                    enum ipsec                          { value 0; }
                                }
                                mandatory true;
                                description "Application to be reloaded";
                            }

                            leaf certificate {
                                type types-security:pki-file-name;
                                mandatory true;
                                description "Name of the certificate file to reload";
                            }

                            leaf key {
                                type types-security:pki-file-name;
                                mandatory true;
                                description "Name of the key file to reload";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action reload

                    action update-certificate {
                        description "Update End Entity certificate";

                        input {

                            leaf certificate {
                                type leafref {
                                    path "/state:state/state:system/state:security/state:pki/state:certificate-auto-update/state:certificate-file-name";
                                }
                                mandatory true;
                                description "Name of the certificate file to be updated";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action update-certificate

                } // container pki

            } // container security

            container license {
                description "Enter the license context";

                action activate {
                    description "Load and activate a system license";

                    input {

                        leaf file-url {
                            type string {
                                length "1..256";
                            }
                            description "Location of the license file to activate";
                        }

                        leaf now {
                            type empty;
                            description "Activate the license immediately";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            leaf active-sros-version {
                                type types-sros:description;
                                description "The current software version running on the system";
                            }

                            leaf license-file {
                                type types-sros:url;
                                description "The location of the validated license file";
                            }

                            leaf license-name {
                                type types-sros:description;
                                description "The name of the license";
                            }

                            leaf license-uuid {
                                type types-sros:description;
                                description "The target UUID of the license";
                            }

                            leaf license-secondary-uuid {
                                type types-sros:description;
                                description "The target secondary UUID of the license";
                            }

                            leaf machine-uuid {
                                type types-sros:description;
                                description "The UUID of this machine";
                            }

                            leaf license-description {
                                type types-sros:description;
                                description "The description of the license";
                            }

                            leaf license-product {
                                type types-sros:description;
                                description "The product for which the license was issued";
                            }

                            leaf license-applicable-versions {
                                type types-sros:description;
                                description "The software version(s) supported by the license";
                            }

                            leaf license-issue-time {
                                type yang:date-and-time;
                                description "The date and time at which the license was issued";
                            }

                            leaf license-start-time {
                                type yang:date-and-time;
                                description "The date and time at which the license becomes valid";
                            }

                            leaf license-end-time {
                                type yang:date-and-time;
                                description "The date and time at which the license expires";
                            }

                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            leaf validation-error-additional-details {
                                type types-sros:very-long-description-or-empty;
                                description "Additional text explaining a problem preventing license validation";
                            }

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action activate

                action clear {
                    description "Clear system license";

                    input {

                        leaf now {
                            type empty;
                            description "Clear license entitlements immediately";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            leaf active-sros-version {
                                type types-sros:description;
                                description "The current software version running on the system";
                            }

                            leaf license-file {
                                type types-sros:url;
                                description "The location of the validated license file";
                            }

                            leaf license-name {
                                type types-sros:description;
                                description "The name of the license";
                            }

                            leaf license-uuid {
                                type types-sros:description;
                                description "The target UUID of the license";
                            }

                            leaf license-secondary-uuid {
                                type types-sros:description;
                                description "The target secondary UUID of the license";
                            }

                            leaf machine-uuid {
                                type types-sros:description;
                                description "The UUID of this machine";
                            }

                            leaf license-description {
                                type types-sros:description;
                                description "The description of the license";
                            }

                            leaf license-product {
                                type types-sros:description;
                                description "The product for which the license was issued";
                            }

                            leaf license-applicable-versions {
                                type types-sros:description;
                                description "The software version(s) supported by the license";
                            }

                            leaf license-issue-time {
                                type yang:date-and-time;
                                description "The date and time at which the license was issued";
                            }

                            leaf license-start-time {
                                type yang:date-and-time;
                                description "The date and time at which the license becomes valid";
                            }

                            leaf license-end-time {
                                type yang:date-and-time;
                                description "The date and time at which the license expires";
                            }

                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            leaf validation-error-additional-details {
                                type types-sros:very-long-description-or-empty;
                                description "Additional text explaining a problem preventing license validation";
                            }

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action clear

                action validate {
                    description "Load and validate a system license";

                    input {

                        leaf file-url {
                            type string {
                                length "1..256";
                            }
                            description "Location of the license file to validate";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            leaf active-sros-version {
                                type types-sros:description;
                                description "The current software version running on the system";
                            }

                            leaf license-file {
                                type types-sros:url;
                                description "The location of the validated license file";
                            }

                            leaf license-name {
                                type types-sros:description;
                                description "The name of the license";
                            }

                            leaf license-uuid {
                                type types-sros:description;
                                description "The target UUID of the license";
                            }

                            leaf license-secondary-uuid {
                                type types-sros:description;
                                description "The target secondary UUID of the license";
                            }

                            leaf machine-uuid {
                                type types-sros:description;
                                description "The UUID of this machine";
                            }

                            leaf license-description {
                                type types-sros:description;
                                description "The description of the license";
                            }

                            leaf license-product {
                                type types-sros:description;
                                description "The product for which the license was issued";
                            }

                            leaf license-applicable-versions {
                                type types-sros:description;
                                description "The software version(s) supported by the license";
                            }

                            leaf license-issue-time {
                                type yang:date-and-time;
                                description "The date and time at which the license was issued";
                            }

                            leaf license-start-time {
                                type yang:date-and-time;
                                description "The date and time at which the license becomes valid";
                            }

                            leaf license-end-time {
                                type yang:date-and-time;
                                description "The date and time at which the license expires";
                            }

                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            leaf validation-error-additional-details {
                                type types-sros:very-long-description-or-empty;
                                description "Additional text explaining a problem preventing license validation";
                            }

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action validate

            } // container license

            container telemetry {
                description "Enter the telemetry context";

                container grpc {
                    description "Enter the grpc context";

                    action cancel {
                        description "Cancel the gRPC dynamic telemetry subscription";

                        input {

                            choice cancel-options {
                                mandatory true;
                                case subscription {

                                    leaf subscription-id {
                                        type uint32;
                                        description "ID of the telemetry subscription to cancel";
                                    }

                                }
                                case all {

                                    leaf all {
                                        type empty;
                                        description "Cancel gRPC dynamic telemetry for all subscriptions";
                                    }

                                }
                            }
                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action cancel

                } // container grpc

            } // container telemetry

            container management-interface {
                description "Enter the management-interface context";

                container operations {
                    description "Enter the operations context";

                    action delete-operation {
                        description "Stop and remove an operation";

                        input {

                            leaf op-table-bypass {
                                type types-operation:operation-op-table-bypass;
                                description "Avoid operation ID allocation";
                            }

                            leaf delete-id {
                                type types-operation:operation-id;
                                mandatory true;
                                description "ID of the operation to remove";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action delete-operation

                    action stop-operation {
                        description "Stop the execution of an operational command";

                        input {

                            leaf op-table-bypass {
                                type types-operation:operation-op-table-bypass;
                                description "Avoid operation ID allocation";
                            }

                            leaf stop-id {
                                type types-operation:operation-id;
                                mandatory true;
                                description "ID of the operation to stop";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stop-operation

                } // container operations

                container commit {
                    description "Enter the commit context";

                    container confirmed {
                        description "Enter the confirmed context";

                        action accept {
                            description "Accept commit confirmed and cancel automatic rollback";

                            output {

                                leaf operation-id {
                                    type types-operation:operation-id;
                                    description "ID assigned to the operation.";
                                }

                                leaf start-time {
                                    type types-operation:operation-timestamp;
                                    description "Time when the operation started its execution.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action accept

                        action cancel {
                            description "Cancel commit confirmed and roll back changes";

                            output {

                                leaf operation-id {
                                    type types-operation:operation-id;
                                    description "ID assigned to the operation.";
                                }

                                leaf start-time {
                                    type types-operation:operation-timestamp;
                                    description "Time when the operation started its execution.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action cancel

                    } // container confirmed

                } // container commit

            } // container management-interface

        } // container system

        container ipsec {
            description "Perform IPsec operations";

            container show {
                description "Display IPsec information";

                action key {
                    description "Display IPsec key history";

                    input {

                        leaf type {
                            type types-security:ipsec-display-key-type;
                            mandatory true;
                            description "Key type";
                        }

                        choice tunnel {
                            mandatory true;
                            case static {

                                leaf ipsec-tunnel {
                                    type types-sros:named-item;
                                    description "IPsec tunnel name";
                                }

                            }
                            case ip {

                                leaf ip-tunnel {
                                    type types-sros:interface-name;
                                    description "IPsec transport mode IP tunnel name";
                                }

                            }
                            case dynamic {

                                leaf gateway {
                                    type types-sros:named-item;
                                    description "IPsec gateway name";
                                }

                                leaf peer-tunnel-ip-address {
                                    type types-sros:ip-address;
                                    description "Dynamic tunnel IP address";
                                }

                                leaf peer-tunnel-port {
                                    type types-sros:tcp-udp-port;
                                    description "Dynamic tunnel port";
                                }

                            }
                        }
                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        container results {
                            description "Enter the results context";

                            leaf local-ip-address {
                                type types-sros:ip-address;
                            }

                            leaf remote-ip-address {
                                type types-sros:ip-address;
                            }

                            leaf max-number-of-records {
                                type uint32;
                            }

                            list key-history {
                                key "index";
                                description "The ipsec key history.";

                                leaf index {
                                    type uint32;
                                    description "The display index of the showing key history record.";
                                }

                                leaf established-time {
                                    type yang:date-and-time;
                                    description "Time when ipsec Security Association (SA) was established.";
                                }

                                choice type {
                                    case ike {

                                        leaf initiator-spi {
                                            type string {
                                                length "1..16";
                                            }
                                            description "Initiator Security Parameter Index (SPI).";
                                        }

                                        leaf responder-spi {
                                            type string {
                                                length "1..16";
                                            }
                                            description "Responder Security Parameter Index (SPI).";
                                        }

                                        choice ike-version {
                                            case ikev2 {

                                                container responder-encryption-key {
                                                    description "Enter the responder-encryption-key context";

                                                    leaf algorithm {
                                                        type types-security:ipsec-encryption-algorithm;
                                                        description "The encryption algorithm.";
                                                    }

                                                    leaf key-length {
                                                        type uint32 {
                                                            range "1..128";
                                                        }
                                                        description "The length of the key.";
                                                    }

                                                    leaf key-hex {
                                                        type string {
                                                            length "1..265";
                                                        }
                                                        description "The hex string of the key.";
                                                    }

                                                } // container responder-encryption-key

                                                container responder-authentication-key {
                                                    description "Enter the responder-authentication-key context";

                                                    leaf algorithm {
                                                        type types-security:ipsec-authentication-algorithm;
                                                        description "The authentication algorithm.";
                                                    }

                                                    leaf key-length {
                                                        type uint32 {
                                                            range "1..128";
                                                        }
                                                        description "The length of the key.";
                                                    }

                                                    leaf key-hex {
                                                        type string {
                                                            length "1..256";
                                                        }
                                                        description "The hex string of the key.";
                                                    }

                                                } // container responder-authentication-key

                                                container initiator-encryption-key {
                                                    description "Enter the initiator-encryption-key context";

                                                    leaf algorithm {
                                                        type types-security:ipsec-encryption-algorithm;
                                                        description "The encryption algorithm.";
                                                    }

                                                    leaf key-length {
                                                        type uint32 {
                                                            range "1..128";
                                                        }
                                                        description "The length of the key.";
                                                    }

                                                    leaf key-hex {
                                                        type string {
                                                            length "1..265";
                                                        }
                                                        description "The hex string of the key.";
                                                    }

                                                } // container initiator-encryption-key

                                                container initiator-authentication-key {
                                                    description "Enter the initiator-authentication-key context";

                                                    leaf algorithm {
                                                        type types-security:ipsec-authentication-algorithm;
                                                        description "The authentication algorithm.";
                                                    }

                                                    leaf key-length {
                                                        type uint32 {
                                                            range "1..128";
                                                        }
                                                        description "The length of the key.";
                                                    }

                                                    leaf key-hex {
                                                        type string {
                                                            length "1..256";
                                                        }
                                                        description "The hex string of the key.";
                                                    }

                                                } // container initiator-authentication-key

                                            }
                                            case ikev1 {

                                                container encryption-key {
                                                    description "Enter the encryption-key context";

                                                    leaf algorithm {
                                                        type types-security:ipsec-encryption-algorithm;
                                                        description "The encryption algorithm.";
                                                    }

                                                    leaf key-length {
                                                        type uint32 {
                                                            range "1..128";
                                                        }
                                                        description "The length of the key.";
                                                    }

                                                    leaf key-hex {
                                                        type string {
                                                            length "1..265";
                                                        }
                                                        description "The hex string of the key.";
                                                    }

                                                } // container encryption-key

                                            }
                                        }
                                    }
                                    case child {

                                        container inbound {
                                            description "Enter the inbound context";

                                            leaf spi {
                                                type uint32;
                                                description "Inbound Security Parameter Index (SPI).";
                                            }

                                            container encryption-key {
                                                description "Enter the encryption-key context";

                                                leaf algorithm {
                                                    type types-security:ipsec-encryption-algorithm;
                                                    description "The encryption algorithm.";
                                                }

                                                leaf key-length {
                                                    type uint32 {
                                                        range "1..128";
                                                    }
                                                    description "The length of the key.";
                                                }

                                                leaf key-hex {
                                                    type string {
                                                        length "1..265";
                                                    }
                                                    description "The hex string of the key.";
                                                }

                                            } // container encryption-key

                                            container authentication-key {
                                                description "Enter the authentication-key context";

                                                leaf algorithm {
                                                    type types-security:ipsec-authentication-algorithm;
                                                    description "The authentication algorithm.";
                                                }

                                                leaf key-length {
                                                    type uint32 {
                                                        range "1..128";
                                                    }
                                                    description "The length of the key.";
                                                }

                                                leaf key-hex {
                                                    type string {
                                                        length "1..256";
                                                    }
                                                    description "The hex string of the key.";
                                                }

                                            } // container authentication-key

                                        } // container inbound

                                        container outbound {
                                            description "Enter the outbound context";

                                            leaf spi {
                                                type uint32;
                                                description "Outbound Security Parameter Index (SPI).";
                                            }

                                            container encryption-key {
                                                description "Enter the encryption-key context";

                                                leaf algorithm {
                                                    type types-security:ipsec-encryption-algorithm;
                                                    description "The encryption algorithm.";
                                                }

                                                leaf key-length {
                                                    type uint32 {
                                                        range "1..128";
                                                    }
                                                    description "The length of the key.";
                                                }

                                                leaf key-hex {
                                                    type string {
                                                        length "1..265";
                                                    }
                                                    description "The hex string of the key.";
                                                }

                                            } // container encryption-key

                                            container authentication-key {
                                                description "Enter the authentication-key context";

                                                leaf algorithm {
                                                    type types-security:ipsec-authentication-algorithm;
                                                    description "The authentication algorithm.";
                                                }

                                                leaf key-length {
                                                    type uint32 {
                                                        range "1..128";
                                                    }
                                                    description "The length of the key.";
                                                }

                                                leaf key-hex {
                                                    type string {
                                                        length "1..256";
                                                    }
                                                    description "The hex string of the key.";
                                                }

                                            } // container authentication-key

                                        } // container outbound

                                    }
                                }
                            } // list key-history

                        } // container results

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action key

            } // container show

        } // container ipsec

    } // container admin

}
