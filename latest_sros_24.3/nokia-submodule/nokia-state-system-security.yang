submodule nokia-state-system-security {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-router             { prefix "types-router"; }
    import nokia-types-services           { prefix "types-services"; }
    import nokia-types-sros               { prefix "types-sros"; }

    include nokia-state-system-security-aaa;
    include nokia-state-system-security-cpm;
    include nokia-state-system-security-management-access-filter;
    include nokia-state-system-security-pki;
    include nokia-state-system-security-ssh;
    include nokia-state-system-security-tls;
    include nokia-state-system-security-user-parameters;

    sros-ext:sros-major-release "rel24";
    organization "Nokia";
    contact
        "Nokia SR OS Support
         Web: <http://www.nokia.com>";
    description
        "Nokia YANG Data model with operational state for system security parameters. on SR OS based routers.

         Copyright 2016 Nokia. All rights reserved. Reproduction of this document
         is authorized on the condition that the foregoing copyright notice is included.

         This nokia-state-system-security YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-12";

    grouping state-system-security {
        container security {
            description "Enter the security context";

            leaf telnet-server-oper-state {
                type types-sros:oper-state;
                description "Indicates the operational status of the telnet server.";
            }

            leaf ftp-server-oper-state {
                type types-sros:oper-state;
                description "Indicates the operational status of the FTP server.";
            }

            leaf telnet6-server-oper-state {
                type types-sros:oper-state;
                description "Indicates the operational status of the IPv6 telnet server.";
            }

            container cpu-protection {
                description "Enter the cpu-protection context";

                container violators {
                    description "Enter the violators context";

                    container interfaces {
                        description "Enter the interfaces context";

                        container overall-rate {
                            description "Enter the overall-rate context";

                            list interface {
                                key "vrtr-id if-index";
                                description "Enter the interface list instance";

                                leaf vrtr-id {
                                    type int32;
                                    description "The virtual router index.";
                                }

                                leaf if-index {
                                    type int32;
                                    description "The interface index.";
                                }

                                leaf service-name {
                                    type types-services:service-name;
                                    description
                                        "The name of the service containing the interface.
                                         This is only applicable for a service interface.";
                                }

                                leaf interface-type {
                                    type types-router:interface-type;
                                    description "The type of interface.";
                                }

                                leaf interface-name {
                                    type types-sros:interface-name;
                                    description "The name of the interface.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list interface

                        } // container overall-rate

                        container out-of-profile-rate {
                            description "Enter the out-of-profile-rate context";

                            list interface {
                                key "vrtr-id if-index";
                                description "Enter the interface list instance";

                                leaf vrtr-id {
                                    type int32;
                                    description "The virtual router index.";
                                }

                                leaf if-index {
                                    type int32;
                                    description "The interface index.";
                                }

                                leaf service-name {
                                    type types-services:service-name;
                                    description
                                        "The name of the service containing the interface.
                                         This is only applicable for a service interface.";
                                }

                                leaf interface-type {
                                    type types-router:interface-type;
                                    description "The type of interface.";
                                }

                                leaf interface-name {
                                    type types-sros:interface-name;
                                    description "The name of the interface.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list interface

                        } // container out-of-profile-rate

                    } // container interfaces

                    container saps {
                        description "Enter the saps context";

                        container overall-rate {
                            description "Enter the overall-rate context";

                            list sap {
                                key "service-id sap-id";
                                description "Enter the sap list instance";

                                leaf service-id {
                                    type types-services:external-service-id;
                                    description "The service index.";
                                }

                                leaf sap-id {
                                    type types-sros:sap;
                                    description "The SAP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list sap

                        } // container overall-rate

                        container out-of-profile-rate {
                            description "Enter the out-of-profile-rate context";

                            list sap {
                                key "service-id sap-id";
                                description "Enter the sap list instance";

                                leaf service-id {
                                    type types-services:external-service-id;
                                    description "The service index.";
                                }

                                leaf sap-id {
                                    type types-sros:sap;
                                    description "The SAP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list sap

                        } // container out-of-profile-rate

                        container eth-cfm-rate {
                            description "Enter the eth-cfm-rate context";

                            list aggregate-flow {
                                key "service-id sap-id level opcode";
                                description "Enter the aggregate-flow list instance";

                                leaf service-id {
                                    type types-services:external-service-id;
                                    description "The service index.";
                                }

                                leaf sap-id {
                                    type types-sros:sap;
                                    description "The SAP identifier.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list aggregate-flow

                            list mac-flow {
                                key "service-id sap-id mac-address level opcode";
                                description "Enter the mac-flow list instance";

                                leaf service-id {
                                    type types-services:external-service-id;
                                    description "The service index.";
                                }

                                leaf sap-id {
                                    type types-sros:sap;
                                    description "The SAP identifier.";
                                }

                                leaf mac-address {
                                    type yang:mac-address;
                                    description "The source MAC address.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-flow

                        } // container eth-cfm-rate

                    } // container saps

                    container sdps {
                        description "Enter the sdps context";

                        container overall-rate {
                            description "Enter the overall-rate context";

                            list spoke-sdp {
                                key "service-id sdp-bind-id";
                                description "Enter the spoke-sdp list instance";

                                leaf service-id {
                                    type types-services:external-service-id;
                                    description "The service index.";
                                }

                                leaf sdp-bind-id {
                                    type types-services:sdp-bind-id;
                                    description "The spoke SDP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list spoke-sdp

                        } // container overall-rate

                        container out-of-profile-rate {
                            description "Enter the out-of-profile-rate context";

                            list spoke-sdp {
                                key "service-id sdp-bind-id";
                                description "Enter the spoke-sdp list instance";

                                leaf service-id {
                                    type types-services:external-service-id;
                                    description "The service index.";
                                }

                                leaf sdp-bind-id {
                                    type types-services:sdp-bind-id;
                                    description "The spoke SDP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list spoke-sdp

                        } // container out-of-profile-rate

                        container eth-cfm-rate {
                            description "Enter the eth-cfm-rate context";

                            list aggregate-flow {
                                key "service-id sdp-bind-id level opcode";
                                description "Enter the aggregate-flow list instance";

                                leaf service-id {
                                    type types-services:external-service-id;
                                    description "The service index.";
                                }

                                leaf sdp-bind-id {
                                    type types-services:sdp-bind-id;
                                    description "The spoke SDP identifier.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list aggregate-flow

                            list mac-flow {
                                key "service-id sdp-bind-id mac-address level opcode";
                                description "Enter the mac-flow list instance";

                                leaf service-id {
                                    type types-services:external-service-id;
                                    description "The service index.";
                                }

                                leaf sdp-bind-id {
                                    type types-services:sdp-bind-id;
                                    description "The spoke SDP identifier.";
                                }

                                leaf mac-address {
                                    type yang:mac-address;
                                    description "The source MAC address.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-flow

                        } // container eth-cfm-rate

                    } // container sdps

                    container ports {
                        description "Enter the ports context";

                        list port {
                            key "port-id";
                            description "Enter the port list instance";

                            leaf port-id {
                                type types-sros:port;
                                description "The identifier that uniquely identifies the port.";
                            }

                            container link-specific-rate {
                                description "Enter the link-specific-rate context";

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // container link-specific-rate

                            container overall-rate {
                                description "Enter the overall-rate context";

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // container overall-rate

                        } // list port

                    } // container ports

                    container mac-sources {
                        description "Enter the mac-sources context";

                        container sap-sources {
                            description "Enter the sap-sources context";

                            list mac-source {
                                key "service-id sap-id mac-address";
                                description "Enter the mac-source list instance";

                                leaf service-id {
                                    type types-services:external-service-id;
                                    description "The service index.";
                                }

                                leaf sap-id {
                                    type types-sros:sap;
                                    description "The SAP identifier.";
                                }

                                leaf mac-address {
                                    type yang:mac-address;
                                    description "MAC address.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-source

                        } // container sap-sources

                    } // container mac-sources

                } // container violators

            } // container cpu-protection

            container dot1x {
                description "Enter the dot1x context";

                list radius-policy {
                    key "policy-name";
                    description "Enter the radius-policy list instance";

                    leaf policy-name {
                        type types-sros:named-item;
                        description "RADIUS server policy name for 802.1X authentication";
                    }

                    list server {
                        key "server-index";
                        description "Enter the server list instance";

                        leaf server-index {
                            type uint32 {
                                range "1..5";
                            }
                            description "RADIUS server index";
                        }

                        leaf oper-state {
                            type types-sros:oper-state;
                            description "Indicates the current status of the RADIUS server";
                        }

                    } // list server

                } // list radius-policy

            } // container dot1x

            container keychains {
                description "Enter the keychains context";

                list keychain {
                    key "keychain-name";
                    description "Enter the keychain list instance";

                    leaf keychain-name {
                        type types-sros:named-item;
                        description "Keychain name";
                    }

                    leaf oper-state {
                        type types-sros:oper-state;
                        description "Indicates the operational state of the keychain.";
                    }

                    leaf expired {
                        type boolean;
                        description "Indicates if the keychain is expired.";
                    }

                } // list keychain

            } // container keychains

            container source-address {
                description "Enter the source-address context";

                list ipv4 {
                    key "application";
                    description "Enter the ipv4 list instance";

                    leaf application {
                        type enumeration {
                            enum telnet                         { value 1; }
                            enum ftp                            { value 2; }
                            enum ssh                            { value 3; }
                            enum radius                         { value 4; }
                            enum tacplus                        { value 5; }
                            enum snmptrap                       { value 6; }
                            enum syslog                         { value 7; }
                            enum ping                           { value 8; }
                            enum traceroute                     { value 9; }
                            enum dns                            { value 10; }
                            enum sntp                           { value 11; }
                            enum ntp                            { value 12; }
                            enum cflowd                         { value 13; }
                            enum ptp                            { value 23; }
                            enum mcreporter                     { value 24; }
                            enum sflow                          { value 27; }
                            enum icmp-error                     { value 29; }
                            enum ldap                           { value 31; }
                        }
                        description "Application that uses the source IP address";
                    }

                    leaf oper-state {
                        type types-sros:up-down-status;
                        description "Indicates the operational status of the source IP entry.";
                    }

                } // list ipv4

                list ipv6 {
                    key "application";
                    description "Enter the ipv6 list instance";

                    leaf application {
                        type enumeration {
                            enum telnet                         { value 14; }
                            enum ftp                            { value 15; }
                            enum radius                         { value 16; }
                            enum tacplus                        { value 17; }
                            enum snmptrap                       { value 18; }
                            enum syslog                         { value 19; }
                            enum ping                           { value 20; }
                            enum traceroute                     { value 21; }
                            enum dns                            { value 22; }
                            enum cflowd                         { value 25; }
                            enum ntp                            { value 26; }
                            enum sflow                          { value 28; }
                            enum icmp6-error                    { value 30; }
                            enum ldap                           { value 32; }
                            enum ssh                            { value 33; }
                            enum ptp                            { value 34; }
                        }
                        description "Application which uses the source IPv6 address";
                    }

                    leaf oper-state {
                        type types-sros:up-down-status;
                        description "Indicates the operational status of the soure IPv6 entry.";
                    }

                } // list ipv6

            } // container source-address

            container management {
                description "Enter the management context";

                container global {
                    description "Enter the global context";

                    container telnet {
                        description "Enter the telnet context";

                        leaf admin-state {
                            status obsolete;
                            type types-sros:admin-state;
                            description "The administrative state for global server";
                        }

                        leaf oper-state {
                            type types-sros:oper-state;
                            description "Indicates the current oper state of global server";
                        }

                    } // container telnet

                    container telnet6 {
                        description "Enter the telnet6 context";

                        leaf admin-state {
                            status obsolete;
                            type types-sros:admin-state;
                            description "The administrative state for global server";
                        }

                        leaf oper-state {
                            type types-sros:oper-state;
                            description "Indicates the current oper state of global server";
                        }

                    } // container telnet6

                    container ftp {
                        description "Enter the ftp context";

                        leaf admin-state {
                            status obsolete;
                            type types-sros:admin-state;
                            description "The administrative state for global server";
                        }

                        leaf oper-state {
                            type types-sros:oper-state;
                            description "Indicates the current oper state of global server";
                        }

                    } // container ftp

                    container ssh {
                        description "Enter the ssh context";

                        leaf admin-state {
                            status obsolete;
                            type types-sros:admin-state;
                            description "The administrative state for global server";
                        }

                        leaf oper-state {
                            type types-sros:oper-state;
                            description "Indicates the current oper state of global server";
                        }

                    } // container ssh

                    container netconf {
                        description "Enter the netconf context";

                        leaf admin-state {
                            status obsolete;
                            type types-sros:admin-state;
                            description "The administrative state for global server";
                        }

                        leaf oper-state {
                            type types-sros:oper-state;
                            description "Indicates the current oper state of global server";
                        }

                    } // container netconf

                    container grpc {
                        description "Enter the grpc context";

                        leaf admin-state {
                            status obsolete;
                            type types-sros:admin-state;
                            description "The administrative state for global server";
                        }

                        leaf oper-state {
                            type types-sros:oper-state;
                            description "Indicates the current oper state of global server";
                        }

                    } // container grpc

                } // container global

                list router-instance {
                    key "router";
                    description "Enter the router-instance list instance";

                    leaf router {
                        type types-sros:router-instance;
                        description "Server router instance";
                    }

                    leaf allow-telnet {
                        type boolean;
                        description "Allow/disallow access to telnet server.";
                    }

                    leaf allow-telnet6 {
                        type boolean;
                        description "Allow/disallow access to telnet IPv6 server.";
                    }

                    leaf allow-ftp {
                        type boolean;
                        description "Allow/disallow access to ftp server.";
                    }

                    leaf allow-ssh {
                        type boolean;
                        description "Allow/disallow access to ssh server.";
                    }

                    leaf allow-netconf {
                        type boolean;
                        description "Allow/disallow access to netconf server.";
                    }

                    leaf allow-grpc {
                        type boolean;
                        description "Allow/disallow access to grpc server.";
                    }

                } // list router-instance

            } // container management

            uses state-system-security-aaa;
            uses state-system-security-cpm-cpm-filter;
            uses state-system-security-cpm-cpm-queue;
            uses state-system-security-management-access-filter;
            uses state-system-security-pki;
            uses state-system-security-ssh;
            uses state-system-security-tls;
            uses state-system-security-user-parameters-user-params;
        } // container security

    } // grouping state-system-security

}
