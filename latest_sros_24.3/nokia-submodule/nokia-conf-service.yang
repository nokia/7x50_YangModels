submodule nokia-conf-service {

    yang-version "1.1";

    belongs-to nokia-conf { prefix "conf"; }

    import ietf-yang-types                { prefix "yang"; }
    import nokia-sros-yang-extensions     { prefix "sros-ext"; }
    import nokia-types-igmp               { prefix "types-igmp"; }
    import nokia-types-isa                { prefix "types-isa"; }
    import nokia-types-log                { prefix "types-log"; }
    import nokia-types-qos                { prefix "types-qos"; }
    import nokia-types-services           { prefix "types-services"; }
    import nokia-types-sros               { prefix "types-sros"; }

    include nokia-conf-filter;
    include nokia-conf-groups;
    include nokia-conf-lag;
    include nokia-conf-port;
    include nokia-conf-pw-port;
    include nokia-conf-pxc;
    include nokia-conf-qos;
    include nokia-conf-router;
    include nokia-conf-svc-cpipe;
    include nokia-conf-svc-epipe;
    include nokia-conf-svc-ies;
    include nokia-conf-svc-ipfix;
    include nokia-conf-svc-ipipe;
    include nokia-conf-svc-nat;
    include nokia-conf-svc-sdp;
    include nokia-conf-svc-vpls;
    include nokia-conf-svc-vprn;

    sros-ext:sros-major-release "rel24";
    organization "Nokia";
    contact
        "Nokia SR OS Support
         Web: <http://www.nokia.com>";
    description
        "Nokia YANG Data model to configure services on SR OS based routers.

         Copyright 2016 Nokia. All rights reserved. Reproduction of this document
         is authorized on the condition that the foregoing copyright notice is included.

         This nokia-conf-service YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-02-05";

    grouping conf-service {
        container service {
            description "Enter the service context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container sdp-group {
                description "Enter the sdp-group context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list group-name {
                    key "group-name";
                    description "Enter the group-name list instance";

                    leaf group-name {
                        type types-sros:named-item;
                        description "SDP administrative group name";
                    }

                    leaf value {
                        type uint32 {
                            range "0..31";
                        }
                        sros-ext:immutable;
                        mandatory true;
                        description "Unique group value associated with the SDP admin group";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list group-name

            } // container sdp-group

            list customer {
                key "customer-name";
                description "Enter the customer list instance";

                leaf customer-name {
                    type types-services:customer-name;
                    description "Customer name for a service";
                }

                leaf customer-id {
                    type types-services:customer-id;
                    sros-ext:immutable;
                    description "Customer ID";
                }

                leaf description {
                    type types-sros:description;
                    description "Text description";
                }

                leaf contact {
                    type types-sros:description;
                    description "Service customer contact information";
                }

                leaf phone {
                    type types-sros:description;
                    description "Service customer telephone number information";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list multi-service-site {
                    key "multi-service-site-name";
                    description "Enter the multi-service-site list instance";

                    leaf multi-service-site-name {
                        type types-sros:named-item;
                        description "Customer site name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container assignment {
                        description "Enter the assignment context";

                        choice assignment {
                            case port {

                                leaf port {
                                    type types-sros:port-named;
                                    description "Multi-service-site assignment to the port";
                                }

                            }
                            case card {

                                leaf card {
                                    type uint32 {
                                        range "1..20";
                                    }
                                    description "Multi-service-site assignment to the card slot";
                                }

                            }
                            case fpe {

                                leaf fpe {
                                    type leafref {
                                        path "../../../../../fwd-path-ext/fpe/fpe-id";
                                    }
                                    description "Multi-service-site assignment to the FPE object";
                                }

                            }
                        }
                    } // container assignment

                    container ingress {
                        description "Enter the ingress context";

                        leaf policer-control-policy {
                            type leafref {
                                path "../../../../../qos/policer-control-policy/policer-control-policy-name";
                            }
                            description "Policer control policy";
                        }

                        container scheduler-policy {
                            description "Enter the scheduler-policy context";

                            leaf policy-name {
                                type leafref {
                                    path "../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR for the scheduler";
                                        }

                                        leaf cir {
                                            type union {
                                                type int64 {
                                                    range "0..6400000000";
                                                }
                                                type enumeration {
                                                    enum sum                            { value -3; }
                                                    enum max                            { value -1; }
                                                }
                                            }
                                            units "kilobps";
                                            description "CIR for the scheduler";
                                        }

                                    } // container rate

                                } // list scheduler

                            } // container overrides

                        } // container scheduler-policy

                    } // container ingress

                    container egress {
                        description "Enter the egress context";

                        leaf policer-control-policy {
                            type leafref {
                                path "../../../../../qos/policer-control-policy/policer-control-policy-name";
                            }
                            description "Policer control policy";
                        }

                        container agg-rate {
                            description "Enter the agg-rate context";

                            leaf rate {
                                type types-services:agg-rate-rate;
                                units "kilobps";
                                description "Rate limit";
                            }

                            leaf queue-frame-based-accounting {
                                type boolean;
                                default "false";
                                description "Enable frame based accounting for policers and queues";
                            }

                            leaf limit-unused-bandwidth {
                                type boolean;
                                default "false";
                                description "Enable aggregate rate overrun protection";
                            }

                        } // container agg-rate

                        container scheduler-policy {
                            description "Enter the scheduler-policy context";

                            leaf policy-name {
                                type leafref {
                                    path "../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR for the scheduler";
                                        }

                                        leaf cir {
                                            type union {
                                                type int64 {
                                                    range "0..6400000000";
                                                }
                                                type enumeration {
                                                    enum sum                            { value -3; }
                                                    enum max                            { value -1; }
                                                }
                                            }
                                            units "kilobps";
                                            description "CIR for the scheduler";
                                        }

                                    } // container rate

                                } // list scheduler

                            } // container overrides

                        } // container scheduler-policy

                    } // container egress

                } // list multi-service-site

            } // list customer

            container mrp {
                description "Enter the mrp context";

                list policy {
                    key "policy-name";
                    description "Enter the policy list instance";

                    leaf policy-name {
                        type types-sros:named-item;
                        description "Specify the policy name associated with the MRP";
                    }

                    leaf description {
                        type types-sros:description;
                        description "Text description";
                    }

                    leaf scope {
                        type types-services:item-scope;
                        default "template";
                        description "Specify the scope of the mrp-policy definition";
                    }

                    leaf default-action {
                        type types-services:mrp-policy-default-action;
                        default "allow";
                        description "Action for packets not matching any MRP policy entries";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "entry-id";
                        description "Enter the entry list instance";

                        leaf entry-id {
                            type types-services:entry-id;
                            description "Sepcify an id for the MRP policy entry";
                        }

                        leaf action {
                            type types-services:mrp-policy-action;
                            description "Action applied for matching packets";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            list isid {
                                key "value";
                                description "Enter the isid list instance";

                                leaf value {
                                    type types-sros:svc-isid;
                                    description "Lowest service instance ID to match the entry";
                                }

                                leaf higher-value {
                                    type types-sros:svc-isid;
                                    description "Highest service instance ID to match the entry";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list isid

                        } // container match

                    } // list entry

                } // list policy

            } // container mrp

            list oper-group {
                key "name";
                max-elements 32768;
                description "Enter the oper-group list instance";

                leaf name {
                    type types-sros:named-item;
                    description "Operational group name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container hold-time {
                    description "Enter the hold-time context";

                    leaf down {
                        type uint32 {
                            range "1..3600";
                        }
                        units "seconds";
                        description "Oper group hold down time";
                    }

                    leaf up {
                        type uint32 {
                            range "0..3600";
                        }
                        units "seconds";
                        default "4";
                        description "Oper group hold up time";
                    }

                } // container hold-time

                container bfd-liveness {
                    presence "Enable the bfd-liveness context";
                    description "Enable the bfd-liveness context";

                    leaf router-instance {
                        type string;
                        sros-ext:immutable;
                        mandatory true;
                        description "Routing context used for route lookup";
                    }

                    leaf interface-name {
                        type types-sros:interface-name;
                        sros-ext:immutable;
                        mandatory true;
                        description "Source interface name";
                    }

                    leaf dest-ip {
                        type types-sros:ipv4-unicast-address;
                        sros-ext:immutable;
                        mandatory true;
                        description "Destination address for BFD";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container bfd-liveness

            } // list oper-group

            container pbb {
                description "Enter the pbb context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container source-bmac {
                    description "Enter the source-bmac context";

                    leaf address {
                        type types-sros:mac-unicast-address-no-zero;
                        description "Source B-VPLS MAC address to use with PBB";
                    }

                    leaf evpn-etree-leaf-address {
                        type types-sros:mac-unicast-address-no-zero;
                        description "Source Backbone VPLS MAC address to use with Provider Backbone Bridging (PBB)";
                    }

                } // container source-bmac

                list mac {
                    key "name";
                    description "Enter the mac list instance";

                    leaf name {
                        type types-sros:named-item;
                        description "MAC name for the MAC address";
                    }

                    leaf address {
                        type types-sros:mac-unicast-address-no-zero;
                        mandatory true;
                        description "IEEE address assigned to the MAC name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mac

                container mac-notification {
                    description "Enter the mac-notification context";

                    leaf interval {
                        type uint32 {
                            range "1..100";
                        }
                        units "deciseconds";
                        default "1";
                        description "Interval for MAC-notification messages";
                    }

                    leaf count {
                        type uint32 {
                            range "1..10";
                        }
                        default "3";
                        description "MAC notification messages count";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container mac-notification

            } // container pbb

            container upnp {
                description "Enter the upnp context";

                list policy {
                    key "name";
                    max-elements 255;
                    description "Enter the policy list instance";

                    leaf name {
                        type types-sros:external-named-item;
                        description "UPnP policy name";
                    }

                    leaf description {
                        type types-sros:description;
                        description "Text description";
                    }

                    leaf port {
                        type types-sros:tcp-udp-port-non-zero;
                        default "5000";
                        description "HTTP TCP port to which the UPnP IGD listens";
                    }

                    leaf mapping-limit {
                        type uint32 {
                            range "1..256";
                        }
                        default "256";
                        description "Maximum number of UPnP mappings per subscriber";
                    }

                    leaf strict-mode {
                        type boolean;
                        default "false";
                        description "Enable UPnP strict mode";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list policy

            } // container upnp

            container proxy-arp-nd {
                description "Enter the proxy-arp-nd context";

                container mac-list {
                    description "Enter the mac-list context";

                    list list {
                        key "list-name";
                        description "Enter the list list instance";

                        leaf list-name {
                            type types-sros:named-item;
                            description "Specify name for mac list";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list mac {
                            key "address";
                            max-elements 10;
                            description "Add a list entry for mac";

                            leaf address {
                                type types-sros:mac-unicast-address-no-zero;
                                description "MAC address to be added to the list";
                            }

                        } // list mac

                    } // list list

                } // container mac-list

            } // container proxy-arp-nd

            list pw-template {
                key "pw-template-name";
                max-elements 2048;
                description "Enter the pw-template list instance";

                leaf pw-template-name {
                    type types-services:pw-template-name;
                    description "SDP template name";
                }

                leaf pw-template-id {
                    type types-services:pw-template-id;
                    sros-ext:immutable;
                    description "PW Template Id";
                }

                leaf provisioned-sdp {
                    type types-services:provisioned-sdp;
                    sros-ext:immutable;
                    description "Provisioned SDP type";
                }

                leaf allow-fragmentation {
                    type boolean;
                    default "false";
                    description "Allow packets to be sent without setting DF bit";
                }

                leaf auto-gre-sdp {
                    type boolean;
                    sros-ext:immutable;
                    default "false";
                    description "Use a GRE tunnel to automatically create an SDP";
                }

                leaf vc-type {
                    type types-services:pw-template-sdp-bind-vc-type;
                    default "ether";
                    description "Virtual circuit type associated with the SDP bind";
                }

                leaf accounting-policy {
                    type types-log:log-policy-id;
                    description "Accounting policy";
                }

                leaf collect-stats {
                    type boolean;
                    default "false";
                    description "Collect statistics";
                }

                leaf vlan-vc-tag {
                    type types-services:vlan-vc-tag;
                    description "VLAN VC tag";
                }

                leaf force-vc-forwarding {
                    type enumeration {
                        enum vlan                           { value 1; }
                        enum qinq-c-tag-c-tag               { value 2; }
                        enum qinq-s-tag-c-tag               { value 3; }
                    }
                    description "VC forwarding action";
                }

                leaf control-word {
                    type boolean;
                    default "false";
                    description "Enable/Disable the use of ControlWord";
                }

                leaf block-on-peer-fault {
                    type boolean;
                    default "false";
                    description "Enable block traffic on peer fault";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice label {
                    case entropy {

                        leaf entropy-label {
                            type empty;
                            description "Enable the use of an entropy label";
                        }

                    }
                    case hash {

                        container hash-label {
                            presence "Enable the hash-label context";
                            description "Enable the hash-label context";

                            leaf signal-capability {
                                type empty;
                                description "Signal hash label capability to the remote PE";
                            }

                        } // container hash-label

                    }
                }
                container split-horizon-group {
                    description "Enter the split-horizon-group context";

                    leaf name {
                        type types-sros:named-item;
                        description "Split horizon group name to which the SDP belongs";
                    }

                    leaf description {
                        type types-sros:description;
                        description "Text description";
                    }

                    container fdb {
                        description "Enter the fdb context";

                        container saps {
                            description "Enter the saps context";

                            leaf auto-learn-mac-protect {
                                type boolean;
                                default "false";
                                description "Enable automatic update of MAC protect list";
                            }

                            leaf protected-src-mac-violation-action {
                                type types-services:sap-protected-src-mac-violation-action;
                                description "Action for protected source MAC restriction";
                            }

                            leaf discard-unprotected-dest-mac {
                                type boolean;
                                default "false";
                                description "Enable/disable unprotected dest MAC restriction";
                            }

                        } // container saps

                    } // container fdb

                } // container split-horizon-group

                container ingress {
                    description "Enter the ingress context";

                    container filter {
                        description "Enter the filter context";

                        leaf mac {
                            type types-sros:named-item-64;
                            description "MAC filter policy name";
                        }

                        leaf ip {
                            type types-sros:named-item-64;
                            description "IPv4 filter policy name";
                        }

                        leaf ipv6 {
                            type types-sros:named-item-64;
                            description "IPv6 filter policy name";
                        }

                    } // container filter

                    container qos {
                        description "Enter the qos context";

                        container network {
                            description "Enter the network context";

                            leaf policy-name {
                                type types-sros:named-item-64;
                                description "Network policy ID";
                            }

                            container fp-redirect-group {
                                description "Enter the fp-redirect-group context";

                                leaf group-name {
                                    type types-sros:named-item;
                                    description "Name of the forwarding plane queue group template";
                                }

                                leaf instance {
                                    type types-services:qos-qgrp-instance-id;
                                    description "Instance for FP ingress queue group";
                                }

                            } // container fp-redirect-group

                        } // container network

                    } // container qos

                } // container ingress

                container igmp-snooping {
                    description "Enter the igmp-snooping context";

                    leaf fast-leave {
                        type boolean;
                        default "false";
                        description "Allow IGMP fast leave processing";
                    }

                    leaf import-policy {
                        type types-sros:named-item;
                        description "Import policy that filters IGMP packets";
                    }

                    leaf query-last-member-interval {
                        type uint32 {
                            range "1..50";
                        }
                        units "deciseconds";
                        default "10";
                        description "Time between group-specific query messages";
                    }

                    leaf maximum-number-groups {
                        type uint32 {
                            range "1..1000";
                        }
                        description "Maximum multicast groups";
                    }

                    leaf query-interval {
                        type uint32 {
                            range "2..1024";
                        }
                        units "seconds";
                        default "125";
                        description "Time between two consecutive host-query messages";
                    }

                    leaf query-response-interval {
                        type uint32 {
                            range "1..1023";
                        }
                        units "seconds";
                        default "10";
                        description "Time to wait for a response to the host-query messages";
                    }

                    leaf robust-count {
                        type uint32 {
                            range "2..7";
                        }
                        default "2";
                        description "Number of retries after expected message loss";
                    }

                    leaf send-queries {
                        type boolean;
                        default "false";
                        description "Generate IGMP general queries";
                    }

                    leaf version {
                        type types-igmp:igmp-version;
                        default "3";
                        description "IGMP version";
                    }

                } // container igmp-snooping

                container stp {
                    description "Enter the stp context";

                    leaf admin-state {
                        type types-sros:admin-state;
                        description "Administrative state of STP";
                    }

                    leaf auto-edge {
                        type boolean;
                        default "true";
                        description "Enable automatic detection of edge port characteristics";
                    }

                    leaf edge-port {
                        type boolean;
                        default "false";
                        description "Designate SAP or SDP as an edge port";
                    }

                    leaf link-type {
                        type types-services:stp-link-type;
                        default "pt-pt";
                        description "Configure STP link-type";
                    }

                    leaf path-cost {
                        type types-services:stp-path-cost;
                        default "10";
                        description "Configure path-cost";
                    }

                    leaf priority {
                        type int32 {
                            range "0..255";
                        }
                        default "128";
                        description "Configure STP priority";
                    }

                    leaf root-guard {
                        type boolean;
                        default "false";
                        description "Enable/disable STP root-guard";
                    }

                } // container stp

                container l2pt {
                    description "Enter the l2pt context";

                    container termination {
                        presence "Enable the termination context";
                        description "Enable the termination context";

                        container protocols {
                            description "Enter the protocols context";

                            leaf stp {
                                type boolean;
                                default "true";
                                description "Enable all spanning tree protocols";
                            }

                            leaf cdp {
                                type boolean;
                                default "false";
                                description "Enable Cisco discovery protocol";
                            }

                            leaf vtp {
                                type boolean;
                                default "false";
                                description "Enable virtual trunk protocol";
                            }

                            leaf dtp {
                                type boolean;
                                default "false";
                                description "Enable dynamic trunking protocol";
                            }

                            leaf pagp {
                                type boolean;
                                default "false";
                                description "Enable port aggregation protocol";
                            }

                            leaf udld {
                                type boolean;
                                default "false";
                                description "Enable unidirectional link detection";
                            }

                        } // container protocols

                    } // container termination

                } // container l2pt

                container encryption-keygroup {
                    description "Enter the encryption-keygroup context";

                    leaf inbound {
                        type types-services:keygroup-id;
                        description "Keygroup identifier in the inbound direction";
                    }

                    leaf outbound {
                        type types-services:keygroup-id;
                        description "Keygroup identifier in the outbound direction";
                    }

                } // container encryption-keygroup

                container fdb {
                    description "Enter the fdb context";

                    leaf discard-unknown-source {
                        type boolean;
                        default "false";
                        description "Discard frames with unknown source";
                    }

                    leaf limit-mac-move {
                        type types-services:vpls-limit-mac-move;
                        default "blockable";
                        description "MAC move limit";
                    }

                    leaf mac-pinning {
                        type boolean;
                        default "false";
                        description "Enable MAC address pinning on this spoke SDP";
                    }

                    leaf maximum-mac-addresses {
                        type uint32 {
                            range "1..511999";
                        }
                        description "Maximum number of MAC address entries in the FDB";
                    }

                    leaf auto-learn-mac-protect {
                        type boolean;
                        default "false";
                        description "Enable automatic update of MAC protect list";
                    }

                    leaf auto-learn-mac-protect-exclude-list {
                        type types-sros:named-item;
                        description "Name of the MAC protect exclusion list";
                    }

                    leaf protected-src-mac-violation-action {
                        type types-services:sdp-protected-src-mac-violation-action;
                        description "Action for protected source MAC restriction";
                    }

                    container mac-learning {
                        description "Enter the mac-learning context";

                        leaf learning {
                            type boolean;
                            default "true";
                            description "Enable learning of new MAC addresses";
                        }

                        leaf aging {
                            type boolean;
                            default "true";
                            description "Enable aging of MAC addresses";
                        }

                    } // container mac-learning

                } // container fdb

                container egress {
                    description "Enter the egress context";

                    container filter {
                        description "Enter the filter context";

                        leaf mac {
                            type types-sros:named-item-64;
                            description "MAC filter policy name";
                        }

                        leaf ip {
                            type types-sros:named-item-64;
                            description "IPv4 filter policy name";
                        }

                        leaf ipv6 {
                            type types-sros:named-item-64;
                            description "IPv6 filter policy name";
                        }

                    } // container filter

                    container qos {
                        description "Enter the qos context";

                        container network {
                            description "Enter the network context";

                            leaf policy-name {
                                type types-sros:named-item-64;
                                description "Network policy ID";
                            }

                            container port-redirect-group {
                                description "Enter the port-redirect-group context";

                                leaf group-name {
                                    type types-sros:named-item;
                                    description "Name of the egress port queue group template";
                                }

                                leaf instance {
                                    type types-services:qos-qgrp-instance-id;
                                    description "Instance for FP ingress queue group";
                                }

                            } // container port-redirect-group

                        } // container network

                    } // container qos

                    container mfib-allowed-mda-destinations {
                        description "Enter the mfib-allowed-mda-destinations context";

                        list mda {
                            key "mda-id";
                            description "Add a list entry for mda";

                            leaf mda-id {
                                type types-isa:slot-mda;
                                description "MFIB allowed MDA destination";
                            }

                        } // list mda

                    } // container mfib-allowed-mda-destinations

                } // container egress

                list sdp-include {
                    key "group-name";
                    description "Add a list entry for sdp-include";

                    leaf group-name {
                        type leafref {
                            path "../../../sdp-group/group-name/group-name";
                        }
                        description "SDP group name";
                    }

                } // list sdp-include

                list sdp-exclude {
                    key "group-name";
                    description "Add a list entry for sdp-exclude";

                    leaf group-name {
                        type leafref {
                            path "../../../sdp-group/group-name/group-name";
                        }
                        description "SDP group name";
                    }

                } // list sdp-exclude

            } // list pw-template


            container system {
                description "Enter the system context";

                leaf extended-default-qinq-sap-lookup {
                    type boolean;
                    description "Control the forwarding of the packets";
                }

                leaf vpn-gre-source-ip {
                    type types-sros:ipv4-unicast-address;
                    description "VPN GRE source ip-address";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container pw-port-list {
                    description "Enter the pw-port-list context";

                    list port {
                        key "port-id";
                        description "Add a list entry for port";

                        leaf port-id {
                            type types-sros:port;
                            description "Port ID";
                        }

                    } // list port

                } // container pw-port-list

                container bgp-auto-rd-range {
                    description "Enter the bgp-auto-rd-range context";

                    leaf ip-address {
                        type types-sros:ipv4-address;
                        description "IP address used for selecting the route distinguisher";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container community-value {
                        description "Enter the community-value context";

                        leaf start {
                            type int32 {
                                range "1..65535";
                            }
                            description "Lower bound of BGP route distinguisher community range";
                        }

                        leaf end {
                            type int32 {
                                range "1..65535";
                            }
                            description "Upper bound of BGP route distinguisher community range";
                        }

                    } // container community-value

                } // container bgp-auto-rd-range

                container fdb {
                    description "Enter the fdb context";

                    leaf table-size {
                        type uint32 {
                            range "4095..2047999";
                        }
                        description "Maximum FDB entries in the system";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container fdb

                container vxlan {
                    description "Enter the vxlan context";

                    container assisted-replication {
                        description "Enter the assisted-replication context";

                        leaf ip-address {
                            type types-sros:ipv4-unicast-address;
                            description "IP address for assisted replication in the router";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container assisted-replication

                    list tunnel-termination {
                        key "ip-address";
                        description "Enter the tunnel-termination list instance";

                        leaf ip-address {
                            type types-sros:ip-unicast-address;
                            description "Non-system IP address that terminates the VXLAN";
                        }

                        leaf fpe-id {
                            type leafref {
                                path "../../../../../fwd-path-ext/fpe/fpe-id";
                            }
                            sros-ext:immutable;
                            mandatory true;
                            description "FPE id for this entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list tunnel-termination

                } // container vxlan

                container gre-eth-bridged {
                    description "Enter the gre-eth-bridged context";

                    list tunnel-termination {
                        key "ip-address";
                        description "Enter the tunnel-termination list instance";

                        leaf ip-address {
                            type types-sros:ip-unicast-address;
                            description "Tunnel end-point IP address in the SR OS node";
                        }

                        leaf fpe-id {
                            type leafref {
                                path "../../../../../fwd-path-ext/fpe/fpe-id";
                            }
                            sros-ext:immutable;
                            mandatory true;
                            description "FPE ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list tunnel-termination

                } // container gre-eth-bridged

                container bgp {
                    description "Enter the bgp context";

                    container evpn {
                        description "Enter the evpn context";

                        leaf etree-leaf-label {
                            type boolean;
                            default "false";
                            description "Enable E-Tree leaf label for PE";
                        }

                        leaf etree-leaf-label-value {
                            type union {
                                type int32 {
                                    range "32..524526";
                                }
                                type enumeration {
                                    enum dynamic                        { value -1; }
                                }
                            }
                            default "dynamic";
                            description "Global E-tree leaf label for PE in EVPN E-Tree services";
                        }

                        leaf route-distinguisher {
                            type types-services:vpn-route-distinguisher;
                            description "Route distinguisher for ES routes";
                        }

                        leaf ingress-replication-bum-label-block {
                            type leafref {
                                path "../../../../../router/mpls-labels/reserved-label-block/label-block-name";
                            }
                            description "Reserved label block name for BUM traffic";
                        }

                        leaf multicast-leave-sync-propagation {
                            type int32 {
                                range "0..300";
                            }
                            units "seconds";
                            default "5";
                            description "Multicast leave group synchronization delay";
                        }

                        list ethernet-segment {
                            key "ethernet-segment-name";
                            max-elements 20480;
                            description "Enter the ethernet-segment list instance";

                            leaf ethernet-segment-name {
                                type types-sros:named-item;
                                description "Specify name for Ethernet segment";
                            }

                            leaf admin-state {
                                type types-sros:admin-state;
                                default "disable";
                                description "Administrative state of the Ethernet segment instance";
                            }

                            leaf type {
                                type enumeration {
                                    enum none                           { value 1; }
                                    enum virtual                        { value 2; }
                                }
                                sros-ext:immutable;
                                default "none";
                                description "Ethernet Segment type";
                            }

                            leaf esi {
                                type types-services:ethernet-segment-id-mac-based;
                                sros-ext:auto-restart-to-modify;
                                description "Ethernet segment identifier";
                            }

                            leaf orig-ip {
                                type types-sros:ip-unicast-address;
                                sros-ext:auto-restart-to-modify;
                                description "Originating IP address advertised in the ES route";
                            }

                            leaf route-next-hop {
                                type types-sros:ip-unicast-address;
                                sros-ext:auto-restart-to-modify;
                                description "Next-hop IP address for ES and AD per ES routes";
                            }

                            leaf multi-homing-mode {
                                type enumeration {
                                    enum none                           { value 0; }
                                    enum single-active                  { value 1; }
                                    enum single-active-no-esi-label     { value 2; }
                                    enum all-active                     { value 3; }
                                    enum all-active-no-esi-label        { value 4; }
                                }
                                sros-ext:auto-restart-to-modify;
                                default "none";
                                description "Multihoming mode of the Ethernet segment";
                            }

                            leaf oper-group {
                                type leafref {
                                    path "../../../../../oper-group/name";
                                }
                                description "Operational group ID";
                            }

                            leaf auto-esi {
                                type enumeration {
                                    enum none                           { value 0; }
                                    enum type-1                         { value 1; }
                                }
                                sros-ext:auto-restart-to-modify;
                                default "none";
                                description "EVPN Ethernet segment auto-ESI type";
                            }

                            leaf ac-df-capability {
                                type enumeration {
                                    enum include                        { value 0; }
                                    enum exclude                        { value 1; }
                                }
                                sros-ext:auto-restart-to-modify;
                                default "include";
                                description "AC-influenced DF election capability";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container df-election {
                                description "Enter the df-election context";

                                leaf es-activation-timer {
                                    type int32 {
                                        range "0..100";
                                    }
                                    units "seconds";
                                    description "Activation timer per Ethernet segment";
                                }

                                leaf service-carving-mode {
                                    type enumeration {
                                        enum auto                           { value 1; }
                                        enum manual                         { value 2; }
                                        enum off                            { value 3; }
                                    }
                                    sros-ext:auto-restart-to-modify;
                                    default "auto";
                                    description "Mode of service carving enabled per EVPN associated with this Ethernet segment entry";
                                }

                                container manual {
                                    description "Enter the manual context";

                                    list evi {
                                        key "start";
                                        description "Enter the evi list instance";

                                        leaf start {
                                            type uint32 {
                                                range "1..16777215";
                                            }
                                            description "Lower bound of EVI range for which the PE is primary";
                                        }

                                        leaf end {
                                            type uint32 {
                                                range "1..16777215";
                                            }
                                            mandatory true;
                                            description "Upper bound of EVI range for which the PE is primary";
                                        }

                                        leaf-list apply-groups {
                                            type leafref {
                                                path "../../../../../../../../../groups/group/name";
                                            }
                                            max-elements 8;
                                            ordered-by user;
                                            description "Apply a configuration group at this level";
                                        }

                                        leaf-list apply-groups-exclude {
                                            type leafref {
                                                path "../../../../../../../../../groups/group/name";
                                            }
                                            max-elements 8;
                                            ordered-by user;
                                            description "Exclude a configuration group at this level";
                                        }

                                    } // list evi

                                    list isid {
                                        key "start";
                                        description "Enter the isid list instance";

                                        leaf start {
                                            type types-sros:svc-isid-non-zero;
                                            description "Lower bound of ISID range for which the PE is primary";
                                        }

                                        leaf end {
                                            type types-sros:svc-isid-non-zero;
                                            mandatory true;
                                            description "Upper bound of ISID range for which the PE is primary";
                                        }

                                        leaf-list apply-groups {
                                            type leafref {
                                                path "../../../../../../../../../groups/group/name";
                                            }
                                            max-elements 8;
                                            ordered-by user;
                                            description "Apply a configuration group at this level";
                                        }

                                        leaf-list apply-groups-exclude {
                                            type leafref {
                                                path "../../../../../../../../../groups/group/name";
                                            }
                                            max-elements 8;
                                            ordered-by user;
                                            description "Exclude a configuration group at this level";
                                        }

                                    } // list isid

                                    container preference {
                                        presence "Enable the preference context";
                                        description "Enable the preference context";

                                        leaf mode {
                                            type enumeration {
                                                enum revertive                      { value 1; }
                                                enum non-revertive                  { value 2; }
                                            }
                                            sros-ext:immutable;
                                            default "revertive";
                                            description "Method used to elect the DF";
                                        }

                                        leaf value {
                                            type uint32 {
                                                range "0..65535";
                                            }
                                            default "32767";
                                            description "Preference that is used to elect the designated forwarder";
                                        }

                                        leaf-list apply-groups {
                                            type leafref {
                                                path "../../../../../../../../../groups/group/name";
                                            }
                                            max-elements 8;
                                            ordered-by user;
                                            description "Apply a configuration group at this level";
                                        }

                                        leaf-list apply-groups-exclude {
                                            type leafref {
                                                path "../../../../../../../../../groups/group/name";
                                            }
                                            max-elements 8;
                                            ordered-by user;
                                            description "Exclude a configuration group at this level";
                                        }

                                    } // container preference

                                } // container manual

                            } // container df-election

                            container association {
                                description "Enter the association context";

                                choice object {
                                    description "Object being multi homed with this Ethernet segment";
                                    case port {

                                        list port {
                                            key "port-id";
                                            max-elements 1;
                                            description "Enter the port list instance";

                                            leaf port-id {
                                                type leafref {
                                                    path "../../../../../../../../port/port-id";
                                                }
                                                description "Port multi-homed with this Ethernet segment entry";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                when "../../../type = 'virtual'" {
                                                    description "virtual-ranges allowed only on virtual ethernet-segments";
                                                }
                                                description "Enter the virtual-ranges context";

                                                container dot1q {
                                                    description "Enter the dot1q context";

                                                    list q-tag {
                                                        key "start";
                                                        max-elements 8;
                                                        description "Enter the q-tag list instance";

                                                        leaf start {
                                                            type types-services:ethernet-segment-vlan-range-encap;
                                                            description "Lower bound of the q-tag VLAN ID range";
                                                        }

                                                        leaf end {
                                                            type types-services:ethernet-segment-vlan-range-encap;
                                                            mandatory true;
                                                            description "Upper bound of the q-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                container qinq {
                                                    description "Enter the qinq context";

                                                    list s-tag-c-tag {
                                                        key "s-tag c-tag-start";
                                                        max-elements 8;
                                                        description "Enter the s-tag-c-tag list instance";

                                                        leaf s-tag {
                                                            type types-services:ethernet-segment-vlan-range-encap-with-null;
                                                            description "Starting value of the qinq s-tag range associated with a virtual ethernet segment";
                                                        }

                                                        leaf c-tag-start {
                                                            type types-services:ethernet-segment-vlan-range-encap-with-null;
                                                            description "Starting value of the qinq c-tag range";
                                                        }

                                                        leaf c-tag-end {
                                                            type types-services:ethernet-segment-vlan-range-encap-with-null;
                                                            mandatory true;
                                                            description "End value of the qinq c-tag range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    list s-tag {
                                                        key "start";
                                                        max-elements 8;
                                                        description "Enter the s-tag list instance";

                                                        leaf start {
                                                            type types-services:ethernet-segment-vlan-range-encap;
                                                            description "Lower bound of the s-tag VLAN ID range";
                                                        }

                                                        leaf end {
                                                            type types-services:ethernet-segment-vlan-range-encap;
                                                            mandatory true;
                                                            description "Upper bound of the s-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list port

                                    }
                                    case lag {

                                        list lag {
                                            key "lag-name";
                                            max-elements 1;
                                            description "Enter the lag list instance";

                                            leaf lag-name {
                                                type leafref {
                                                    path "../../../../../../../../lag/lag-name";
                                                }
                                                description "LAG multi-homed with the Ethernet segment entry";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                when "../../../type = 'virtual'" {
                                                    description "virtual-ranges allowed only on virtual ethernet-segments";
                                                }
                                                description "Enter the virtual-ranges context";

                                                container dot1q {
                                                    description "Enter the dot1q context";

                                                    list q-tag {
                                                        key "start";
                                                        max-elements 8;
                                                        description "Enter the q-tag list instance";

                                                        leaf start {
                                                            type types-services:ethernet-segment-vlan-range-encap;
                                                            description "Lower bound of the q-tag VLAN ID range";
                                                        }

                                                        leaf end {
                                                            type types-services:ethernet-segment-vlan-range-encap;
                                                            mandatory true;
                                                            description "Upper bound of the q-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                container qinq {
                                                    description "Enter the qinq context";

                                                    list s-tag-c-tag {
                                                        key "s-tag c-tag-start";
                                                        max-elements 8;
                                                        description "Enter the s-tag-c-tag list instance";

                                                        leaf s-tag {
                                                            type types-services:ethernet-segment-vlan-range-encap-with-null;
                                                            description "Starting value of the qinq s-tag range associated with a virtual ethernet segment";
                                                        }

                                                        leaf c-tag-start {
                                                            type types-services:ethernet-segment-vlan-range-encap-with-null;
                                                            description "Starting value of the qinq c-tag range";
                                                        }

                                                        leaf c-tag-end {
                                                            type types-services:ethernet-segment-vlan-range-encap-with-null;
                                                            mandatory true;
                                                            description "End value of the qinq c-tag range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    list s-tag {
                                                        key "start";
                                                        max-elements 8;
                                                        description "Enter the s-tag list instance";

                                                        leaf start {
                                                            type types-services:ethernet-segment-vlan-range-encap;
                                                            description "Lower bound of the s-tag VLAN ID range";
                                                        }

                                                        leaf end {
                                                            type types-services:ethernet-segment-vlan-range-encap;
                                                            mandatory true;
                                                            description "Upper bound of the s-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list lag

                                    }
                                    case sdp {

                                        list sdp {
                                            key "sdp-id";
                                            max-elements 1;
                                            description "Enter the sdp list instance";

                                            leaf sdp-id {
                                                type leafref {
                                                    path "../../../../../../../sdp/sdp-id";
                                                }
                                                description "Sdp multi-homed with this Ethernet segment entry";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                when "../../../type = 'virtual'" {
                                                    description "virtual-ranges allowed only on virtual ethernet-segments";
                                                }
                                                description "Enter the virtual-ranges context";

                                                list vc-id {
                                                    key "start";
                                                    max-elements 8;
                                                    description "Enter the vc-id list instance";

                                                    leaf start {
                                                        type types-services:vc-id;
                                                        description "Lower bound of the VC-ID range";
                                                    }

                                                    leaf end {
                                                        type types-services:vc-id;
                                                        mandatory true;
                                                        description "Upper bound of the VC-ID range";
                                                    }

                                                    leaf-list apply-groups {
                                                        type leafref {
                                                            path "../../../../../../../../../../groups/group/name";
                                                        }
                                                        max-elements 8;
                                                        ordered-by user;
                                                        description "Apply a configuration group at this level";
                                                    }

                                                    leaf-list apply-groups-exclude {
                                                        type leafref {
                                                            path "../../../../../../../../../../groups/group/name";
                                                        }
                                                        max-elements 8;
                                                        ordered-by user;
                                                        description "Exclude a configuration group at this level";
                                                    }

                                                } // list vc-id

                                            } // container virtual-ranges

                                        } // list sdp

                                    }
                                    case network-interconnect-vxlan {

                                        list network-interconnect-vxlan {
                                            when "../../type = 'virtual'" {
                                                description "network-interconnect-vxlan allowed only on virtual ethernet-segments";
                                            }
                                            key "network-interconnect-vxlan-id";
                                            max-elements 1;
                                            description "Enter the network-interconnect-vxlan list instance";

                                            leaf network-interconnect-vxlan-id {
                                                type uint32 {
                                                    range "1";
                                                }
                                                description "VXLAN instance ID associated with the virtual ES";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                description "Enter the virtual-ranges context";

                                                list service-id {
                                                    key "start";
                                                    max-elements 8;
                                                    description "Enter the service-id list instance";

                                                    leaf start {
                                                        type types-services:external-service-id;
                                                        description "Lower bound of the service ID range";
                                                    }

                                                    leaf end {
                                                        type types-services:external-service-id;
                                                        mandatory true;
                                                        description "Upper bound of the service ID range";
                                                    }

                                                    leaf-list apply-groups {
                                                        type leafref {
                                                            path "../../../../../../../../../../groups/group/name";
                                                        }
                                                        max-elements 8;
                                                        ordered-by user;
                                                        description "Apply a configuration group at this level";
                                                    }

                                                    leaf-list apply-groups-exclude {
                                                        type leafref {
                                                            path "../../../../../../../../../../groups/group/name";
                                                        }
                                                        max-elements 8;
                                                        ordered-by user;
                                                        description "Exclude a configuration group at this level";
                                                    }

                                                } // list service-id

                                            } // container virtual-ranges

                                        } // list network-interconnect-vxlan

                                    }
                                    case pw-port {

                                        list pw-port {
                                            key "pw-port-id";
                                            max-elements 1;
                                            description "Enter the pw-port list instance";

                                            leaf pw-port-id {
                                                type leafref {
                                                    path "../../../../../../../../pw-port/pw-port-id";
                                                }
                                                description "Pw-port multi-homed with this Ethernet segment entry";
                                            }

                                            leaf pw-port-headend {
                                                type boolean;
                                                sros-ext:immutable;
                                                default "false";
                                                description "Control state of PW SAPs on PW port using EVPN";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                when "../../../type = 'virtual'" {
                                                    description "virtual-ranges allowed only on virtual ethernet-segments";
                                                }
                                                description "Enter the virtual-ranges context";

                                                container dot1q {
                                                    description "Enter the dot1q context";

                                                    list q-tag {
                                                        key "start";
                                                        max-elements 8;
                                                        description "Enter the q-tag list instance";

                                                        leaf start {
                                                            type types-services:ethernet-segment-vlan-range-encap;
                                                            description "Lower bound of the q-tag VLAN ID range";
                                                        }

                                                        leaf end {
                                                            type types-services:ethernet-segment-vlan-range-encap;
                                                            mandatory true;
                                                            description "Upper bound of the q-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                container qinq {
                                                    description "Enter the qinq context";

                                                    list s-tag-c-tag {
                                                        key "s-tag c-tag-start";
                                                        max-elements 8;
                                                        description "Enter the s-tag-c-tag list instance";

                                                        leaf s-tag {
                                                            type types-services:ethernet-segment-vlan-range-encap-with-null;
                                                            description "Starting value of the qinq s-tag range associated with a virtual ethernet segment";
                                                        }

                                                        leaf c-tag-start {
                                                            type types-services:ethernet-segment-vlan-range-encap-with-null;
                                                            description "Starting value of the qinq c-tag range";
                                                        }

                                                        leaf c-tag-end {
                                                            type types-services:ethernet-segment-vlan-range-encap-with-null;
                                                            mandatory true;
                                                            description "End value of the qinq c-tag range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    list s-tag {
                                                        key "start";
                                                        max-elements 8;
                                                        description "Enter the s-tag list instance";

                                                        leaf start {
                                                            type types-services:ethernet-segment-vlan-range-encap;
                                                            description "Lower bound of the s-tag VLAN ID range";
                                                        }

                                                        leaf end {
                                                            type types-services:ethernet-segment-vlan-range-encap;
                                                            mandatory true;
                                                            description "Upper bound of the s-tag VLAN ID range";
                                                        }

                                                        leaf-list apply-groups {
                                                            type leafref {
                                                                path "../../../../../../../../../../../groups/group/name";
                                                            }
                                                            max-elements 8;
                                                            ordered-by user;
                                                            description "Apply a configuration group at this level";
                                                        }

                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list pw-port

                                    }
                                    case vprn-next-hop {

                                        list vprn-next-hop {
                                            when "../../type = 'virtual'" {
                                                description "vprn-next-hop allowed only on virtual ethernet-segments";
                                            }
                                            key "ip-address";
                                            max-elements 1;
                                            description "Enter the vprn-next-hop list instance";

                                            leaf ip-address {
                                                type types-sros:ip-address;
                                                description "VPRN next-hop address";
                                            }

                                            leaf-list apply-groups {
                                                type leafref {
                                                    path "../../../../../../../../groups/group/name";
                                                }
                                                max-elements 8;
                                                ordered-by user;
                                                description "Apply a configuration group at this level";
                                            }

                                            leaf-list apply-groups-exclude {
                                                type leafref {
                                                    path "../../../../../../../../groups/group/name";
                                                }
                                                max-elements 8;
                                                ordered-by user;
                                                description "Exclude a configuration group at this level";
                                            }

                                            container virtual-ranges {
                                                description "Enter the virtual-ranges context";

                                                list evi {
                                                    key "start";
                                                    max-elements 1;
                                                    description "Add a list entry for evi";

                                                    leaf start {
                                                        type uint32 {
                                                            range "1..16777215";
                                                        }
                                                        description "EVI range start information";
                                                    }

                                                } // list evi

                                            } // container virtual-ranges

                                        } // list vprn-next-hop

                                    }
                                }
                            } // container association

                            container pbb {
                                description "Enter the pbb context";

                                leaf source-bmac-lsb {
                                    type types-services:bmac-lsb-no-zero;
                                    sros-ext:auto-restart-to-modify;
                                    description "Least significant bytes of the B-MAC for packet source";
                                }

                                leaf es-bmac-table-size {
                                    type uint32 {
                                        range "1..511999";
                                    }
                                    default "8";
                                    description "Size of virtual backbone mac table for this ethernet segment";
                                }

                            } // container pbb

                        } // list ethernet-segment

                        container ad-per-es-route {
                            description "Enter the ad-per-es-route context";

                            leaf route-target-type {
                                type enumeration {
                                    enum evi-route-target               { value 1; }
                                    enum evi-route-target-set           { value 2; }
                                }
                                default "evi-route-target";
                                description "Method for the AD per-ES routes advertisement";
                            }

                            leaf route-distinguisher-ip-address {
                                type types-sros:ipv4-address;
                                description "IP address for route distinguisher for EVPN AD-ES routes";
                            }

                            leaf extended-evi-range {
                                type boolean;
                                default "false";
                                description "Reserve extended RD comm-values for AD per-ES routes";
                            }

                        } // container ad-per-es-route

                        container ip-prefix-routes {
                            description "Enter the ip-prefix-routes context";

                            leaf iff-attribute-uniform-propagation {
                                status obsolete;
                                type boolean;
                                default "false";
                                description "Enable uniform propagation of BGP attributes";
                            }

                            leaf iff-bgp-path-selection {
                                status obsolete;
                                type boolean;
                                default "false";
                                description "Enable BGP path selection for EVPN-IFF routes";
                            }

                            leaf d-path-length-ignore {
                                status obsolete;
                                type boolean;
                                default "false";
                                description "Ignore D-PATH length for BGP path selection of EVPN-IFF";
                            }

                            container interface-ful {
                                description "Enter the interface-ful context";

                                leaf attribute-uniform-propagation {
                                    type boolean;
                                    default "false";
                                    description "Enable/Disable attribute uniform propagation.";
                                }

                                leaf bgp-path-selection {
                                    type boolean;
                                    default "false";
                                    description "Enable/Disable bgp path selection.";
                                }

                                leaf d-path-length-ignore {
                                    type boolean;
                                    default "false";
                                    description "Ignore d-path length when using bgp-path-selection";
                                }

                            } // container interface-ful

                        } // container ip-prefix-routes

                        container mpls {
                            description "Enter the mpls context";

                            leaf vpls-control-word {
                                type boolean;
                                default "false";
                                description "Enable VPLS control word functionality";
                            }

                        } // container mpls

                        container ad-per-evi-routes {
                            description "Enter the ad-per-evi-routes context";

                            leaf d-path-ignore {
                                type boolean;
                                default "false";
                                description "Ignore D-PATH for BGP path selection";
                            }

                            leaf attribute-propagation {
                                type boolean;
                                default "false";
                                description "Enable propagation of BGP path attributes";
                            }

                            leaf bgp-path-selection {
                                type boolean;
                                default "false";
                                description "Enable BGP path selection";
                            }

                        } // container ad-per-evi-routes

                    } // container evpn

                } // container bgp

                container ldp {
                    description "Enter the ldp context";

                    leaf hash-label-block {
                        type leafref {
                            path "../../../../router/mpls-labels/reserved-label-block/label-block-name";
                        }
                        description "Reserved label block from which to select hash labels";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container ldp

            } // container system

            list mac-list {
                key "name";
                description "Enter the mac-list list instance";

                leaf name {
                    type types-sros:named-item;
                    description "MAC list name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list mac {
                    key "address";
                    description "Enter the mac list instance";

                    leaf address {
                        type yang:mac-address;
                        description "MAC address";
                    }

                    leaf mask {
                        type yang:mac-address;
                        default "ff:ff:ff:ff:ff:ff";
                        description "Mask for the MAC address";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mac

            } // list mac-list

            container md-auto-id {
                description "Enter the md-auto-id context";

                container service-id-range {
                    presence "Enable the service-id-range context";
                    description "Enable the service-id-range context";

                    leaf start {
                        type types-services:external-service-id;
                        sros-ext:immutable;
                        mandatory true;
                        description "Lower bound of the service ID range";
                    }

                    leaf end {
                        type types-services:external-service-id;
                        sros-ext:immutable;
                        mandatory true;
                        description "Upper bound of the service ID range";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container service-id-range

                container customer-id-range {
                    presence "Enable the customer-id-range context";
                    description "Enable the customer-id-range context";

                    leaf start {
                        type types-services:customer-id {
                            range "2..2147483647";
                        }
                        sros-ext:immutable;
                        mandatory true;
                        description "Lower bound of the ID range";
                    }

                    leaf end {
                        type types-services:customer-id {
                            range "2..2147483647";
                        }
                        sros-ext:immutable;
                        mandatory true;
                        description "Upper bound of the ID range";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container customer-id-range

                container pw-template-id-range {
                    presence "Enable the pw-template-id-range context";
                    description "Enable the pw-template-id-range context";

                    leaf start {
                        type types-services:pw-template-id {
                            range "1..2147483647";
                        }
                        sros-ext:immutable;
                        mandatory true;
                        description "Lower bound of the PW template ID range";
                    }

                    leaf end {
                        type types-services:pw-template-id {
                            range "1..2147483647";
                        }
                        sros-ext:immutable;
                        mandatory true;
                        description "Upper bound of the PW template ID range";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container pw-template-id-range

            } // container md-auto-id

            container template {
                description "Enter the template context";

                list epipe-sap-template {
                    key "name";
                    description "Enter the epipe-sap-template list instance";

                    leaf name {
                        type types-sros:named-item;
                        description "SAP template name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container egress {
                        description "Enter the egress context";

                        container filter {
                            description "Enter the filter context";

                            leaf mac {
                                type leafref {
                                    path "../../../../../../filter/mac-filter/filter-name";
                                }
                                description "MAC filter policy name";
                            }

                            leaf ip {
                                type leafref {
                                    path "../../../../../../filter/ip-filter/filter-name";
                                }
                                description "IPv4 filter policy name";
                            }

                            leaf ipv6 {
                                type leafref {
                                    path "../../../../../../filter/ipv6-filter/filter-name";
                                }
                                description "IPv6 filter policy name";
                            }

                        } // container filter

                        container qos {
                            description "Enter the qos context";

                            leaf policy-name {
                                type leafref {
                                    path "../../../../../../qos/sap-egress/sap-egress-policy-name";
                                }
                                description "SAP egress QoS policy name to apply to the SAP";
                            }

                        } // container qos

                    } // container egress

                    container ingress {
                        description "Enter the ingress context";

                        container filter {
                            description "Enter the filter context";

                            leaf mac {
                                type leafref {
                                    path "../../../../../../filter/mac-filter/filter-name";
                                }
                                description "MAC filter policy name";
                            }

                            leaf ip {
                                type leafref {
                                    path "../../../../../../filter/ip-filter/filter-name";
                                }
                                description "IPv4 filter policy name";
                            }

                            leaf ipv6 {
                                type leafref {
                                    path "../../../../../../filter/ipv6-filter/filter-name";
                                }
                                description "IPv6 filter policy name";
                            }

                        } // container filter

                        container qos {
                            description "Enter the qos context";

                            leaf policy-name {
                                type leafref {
                                    path "../../../../../../qos/sap-ingress/sap-ingress-policy-name";
                                }
                                description "SAP ingress QoS policy name to apply to the SAP";
                            }

                            leaf queuing-type {
                                type types-services:services-sap-queuing-type;
                                description "Queuing type";
                            }

                        } // container qos

                    } // container ingress

                } // list epipe-sap-template


            } // container template

            uses conf-svc-cpipe;
            uses conf-svc-epipe;
            uses conf-svc-ies;
            uses conf-svc-ipfix;
            uses conf-svc-ipipe;
            uses conf-svc-nat;
            uses conf-svc-sdp;
            uses conf-svc-vpls;
            uses conf-svc-vprn;
        } // container service

    } // grouping conf-service

}
