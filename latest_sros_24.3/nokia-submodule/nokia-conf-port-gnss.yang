submodule nokia-conf-port-gnss {

    yang-version "1.1";

    belongs-to nokia-conf { prefix "conf"; }

    import nokia-sros-yang-extensions     { prefix "sros-ext"; }

    include nokia-conf-groups;

    sros-ext:sros-major-release "rel24";
    organization "Nokia";
    contact
        "Nokia SR OS Support
         Web: <http://www.nokia.com>";
    description
        "Nokia YANG Data model to configure Global Navigation Satellite System (GNSS) CPM ports on SR OS based routers.

         Copyright 2016 Nokia. All rights reserved. Reproduction of this document
         is authorized on the condition that the foregoing copyright notice is included.

         This nokia-conf-port-gnss YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-01-16";

    grouping conf-port-gnss {
        container gnss {
            description "Enter the gnss context";

            leaf antenna-cable-delay {
                type uint32 {
                    range "0..32767";
                }
                units "nanoseconds";
                default "0";
                description "Signal delay resulting from GNSS antenna cable length";
            }

            leaf elevation-mask-angle {
                type uint32 {
                    range "0..89";
                }
                units "degrees angle";
                default "10";
                description "Minimum elevation mask angle";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container constellation {
                description "Enter the constellation context";

                leaf gps {
                    type boolean;
                    default "true";
                    description "Enable GNSS receiver to use GPS constellation type";
                }

                leaf glonass {
                    type boolean;
                    default "false";
                    description "Enable GNSS receiver to use GLONASS constellation type";
                }

                leaf galileo {
                    type boolean;
                    default "false";
                    description "Enable GNSS receiver to use GALILEO constellation type";
                }

            } // container constellation

        } // container gnss

    } // grouping conf-port-gnss

}
