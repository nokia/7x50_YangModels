submodule nokia-state-svc-vprn-vdo-if {

    yang-version "1.1";

    belongs-to nokia-state { prefix "state"; }

    import ietf-inet-types                { prefix "inet"; }
    import ietf-yang-types                { prefix "yang"; }
    import nokia-sros-yang-extensions     { prefix "sros-ext"; }
    import nokia-types-mcast-mgmt         { prefix "types-mcast-mgmt"; }
    import nokia-types-services           { prefix "types-services"; }
    import nokia-types-sros               { prefix "types-sros"; }

    sros-ext:sros-major-release "rel24";
    organization "Nokia";
    contact
        "Nokia SR OS Support
         Web: <http://www.nokia.com>";
    description
        "Nokia YANG Data model with operational state for vprn service video interfaces on SR OS based routers.

         Copyright 2016 Nokia. All rights reserved. Reproduction of this document
         is authorized on the condition that the foregoing copyright notice is included.

         This nokia-state-svc-vprn-vdo-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-06";

    grouping state-svc-vprn-vdo-if-video-interface {
        list video-interface {
            key "interface-name";
            description "Enter the video-interface list instance";

            leaf interface-name {
                type types-sros:interface-name {
                    length "1..29";
                }
                description "Video interface name";
            }

            leaf oper-state {
                type types-sros:oper-state;
                description "Oerational state of this video interface.";
            }

            leaf vrtr-if-index {
                type int32;
                description
                    "The value indicates the secondary index corresponding to this video
                     interface. The primary index is specified by svcId";
            }

            leaf sap-id {
                type string {
                    length "0..255";
                }
                description "The value indicates the control SAP for this video interface.";
            }

            leaf mcast-protocol {
                type enumeration {
                    enum none                           { value 1; }
                    enum pim                            { value 2; }
                    enum igmp-snooping                  { value 3; }
                }
                description
                    "The value indicates the multicast routing protocol where this video
                     interface is configured.";
            }

            leaf sessions {
                type uint32;
                description "The value indicates the number of active sessions on this interface.";
            }

            list channel {
                key "mcast-address source";
                description "Enter the channel list instance";

                leaf mcast-address {
                    type types-sros:ipv4-multicast-address;
                    description "Multicast channel address";
                }

                leaf source {
                    type types-sros:ipv4-unicast-address;
                    description "Unicast source address";
                }

                container src-statistics {
                    description "Enter the src-statistics context";

                    leaf stream-type {
                        type enumeration {
                            enum network                        { value 0; }
                            enum zone                           { value 1; }
                        }
                        description
                            "The value indicates the type of stream being transmitted from the video
                             ISA perspective. Network stream is the stream ingressing the video ISA
                             and being stored by it. Zone stream is the stream egressing the video ISA
                             into which AD streams will be inserted.";
                    }

                    leaf vdo-grp-id {
                        type uint32 {
                            range "0..4";
                        }
                        description "The value indicates the identifier of the video group.";
                    }

                    leaf admin-rt-buffer-size {
                        type uint32 {
                            range "300..8000";
                        }
                        units "milliseconds";
                        description
                            "The value indicates the number of milliseconds worth of channel packets
                             to store for the Retransmission (RT) server.";
                    }

                    leaf ssrc-id {
                        type uint32;
                        description
                            "The value indicates the synchronization source (SSRC) identifier carried
                             in the Real-time Transport Protocol (RTP) header to identify the source
                             of a stream of RTP packets.";
                    }

                    leaf udp-src-port {
                        type inet:port-number;
                        description "The value indicates the UDP source port in the received RTP multicast stream.";
                    }

                    leaf udp-dest-port {
                        type inet:port-number;
                        description "The value indicates the UDP destination port in the received RTP multicast stream.";
                    }

                    leaf up-time {
                        type uint32;
                        units "seconds";
                        description "The value indicates the time since this source group entry was created.";
                    }

                    leaf admin-bw {
                        type uint32;
                        units "kilobps";
                        description "The value indicates the administrative bandwidth of the multicast group.";
                    }

                    leaf buffer-size {
                        type yang:gauge32;
                        units "milliseconds";
                        description
                            "The value indicates the number of milliseconds worth of channel packets stored by
                             the Retransmission (RT) server or Fast Channel Change (FCC) server on this channel.";
                    }

                    leaf rx-bytes {
                        type yang:counter64;
                        units "bytes";
                        description "The value indicates the total number of bytes received on this multicast channel.";
                    }

                    leaf rx-packets {
                        type yang:counter64;
                        description "The value indicates the total number of packets received on this multicast channel.";
                    }

                    leaf rx-invalid-packets {
                        type yang:counter64;
                        description
                            "The value indicates the total number of invalid packets received on this
                             multicast channel.";
                    }

                    leaf tx-bytes {
                        type yang:counter64;
                        units "bytes";
                        description "The value indicates the total number of bytes transmitted on this multicast channel.";
                    }

                    leaf tx-packets {
                        type yang:counter64;
                        description "The value indicates the total number of packets transmitted on this multicast channel.";
                    }

                    leaf tx-failed-packets {
                        type yang:counter64;
                        description
                            "The value indicates the total number of failures during the transmission of packets on
                             this multicast channel. Failure happens when the packet to be sent is not stored in
                             the video cache.";
                    }

                    leaf rt-client-admin-state {
                        status obsolete;
                        type types-services:oper-admin-state;
                        description "The value indicates the administrative state of the retransmission client.";
                    }

                    leaf rt-clnt-rt-svr-addr {
                        status obsolete;
                        type types-sros:ipv4-unicast-address;
                        description "The value indicates the address of the Retransmission (RT) server for this channel.";
                    }

                    leaf rt-client-rt-srvr-port {
                        status obsolete;
                        type inet:port-number;
                        description "The value indicates the Retransmission (RT) server port for this channel.";
                    }

                    leaf rt-client-rx-re-tx-bytes {
                        status obsolete;
                        type yang:counter64;
                        units "bytes";
                        description
                            "The value indicates the total number of retransmitted bytes received by
                             the Retransmission (RT) client.";
                    }

                    leaf rt-client-rx-re-tx-pkts {
                        status obsolete;
                        type yang:counter64;
                        description
                            "The value indicates the total number of retransmitted packets received by
                             the Retransmission (RT) client.";
                    }

                    leaf rt-client-tx-rt-req {
                        status obsolete;
                        type yang:counter32;
                        description
                            "The value indicates the total number of Retransmission (RT) requests sent
                             by the RT client.";
                    }

                    leaf rt-client-tx-rt-req-re-tx {
                        status obsolete;
                        type yang:counter32;
                        description
                            "The value indicates the total number of repeat Retransmission (RT) requests
                             attempted by the RT client.";
                    }

                    leaf rt-client-gaps-detectd {
                        status obsolete;
                        type yang:counter32;
                        description
                            "The value indicates the total number of gaps in the sequence numbers detected
                             by the Retransmission (RT) client.";
                    }

                    leaf rt-client-failed-req {
                        status obsolete;
                        type yang:counter32;
                        description
                            "The value indicates the total number of Retransmission (RT) requests that could
                             not be generated by the RT client due to gaps in the sequence numbers.";
                    }

                    leaf rt-srvr-admin-state {
                        type types-services:oper-admin-state;
                        description "The value indicates the administrative state of the Retransmission (RT) server.";
                    }

                    leaf rt-srvr-rtp-pkts-req {
                        type yang:counter32;
                        description
                            "The value indicates the total number of Real-time Transport Protocol (RTP) packets
                             requested in the Real-time Transport Control Protocol (RTCP) feedback (FB) messages
                             received on this channel.";
                    }

                    leaf rt-srvr-rx-rt-req {
                        type yang:counter32;
                        description
                            "The value indicates the total number of RT requests received by the Retransmission
                             (RT) server.";
                    }

                    leaf rt-srvr-rx-failed-req {
                        type yang:counter32;
                        description
                            "The value indicates the total number of failed requests at the Retransmission (RT)
                             server due to congestion or lack of resources.";
                    }

                    leaf rt-srvr-tx-rt-replies {
                        type yang:counter32;
                        description
                            "The value indicates the total number of Retransmission (RT) replies sent by
                             the RT server.";
                    }

                    leaf rt-srvr-tx-bytes {
                        type yang:counter64;
                        units "bytes";
                        description "The value indicates the total number of bytes sent by the Retransmission (RT) server.";
                    }

                    leaf rt-srvr-tx-packets {
                        type yang:counter64;
                        description
                            "The value indicates the total number of packets sent by the Retransmission
                             (RT) server.";
                    }

                    leaf fcc-srvr-admin-state {
                        type types-services:oper-admin-state;
                        description
                            "The value indicates whether the Fast Channel Change (FCC) server is enabled
                             on this channel.";
                    }

                    leaf fcc-srvr-chnl-type {
                        type types-mcast-mgmt:channel-type;
                        description
                            "The value indicates the type of channel served by the Fast Channel Change
                             (FCC) server.";
                    }

                    leaf fcc-srvr-rx-fcc-req {
                        type yang:counter32;
                        description
                            "The value indicates the total number of Fast Channel Change (FCC) requests
                             received by the FCC server.";
                    }

                    leaf fcc-srvr-rx-failed-req {
                        type yang:counter32;
                        description
                            "The value indicates the total number of failed requests at the Fast Channel
                             Change (FCC) server.";
                    }

                    leaf fcc-srvr-tx-fcc-replies {
                        type yang:counter32;
                        description
                            "The value indicates the total number of Fast Channel Change (FCC) replies
                             sent by the FCC server.";
                    }

                    leaf fcc-srvr-tx-bytes {
                        type yang:counter64;
                        units "bytes";
                        description
                            "The value indicates the total number of bytes sent by the Fast Channel
                             Change (FCC) server.";
                    }

                    leaf fcc-srvr-tx-packets {
                        type yang:counter64;
                        description
                            "The value indicates the total number of packets sent by the Fast Channel
                             Change (FCC) server.";
                    }

                    leaf adi-admin-state {
                        type types-services:oper-admin-state;
                        description "The value indicates whether Ad Insertion is enabled on the video ISA.";
                    }

                    leaf adi-current-state {
                        type enumeration {
                            enum network                        { value 0; }
                            enum ad                             { value 1; }
                        }
                        description
                            "The value indicates whether the video ISA is transmitting network
                             stream or ads.";
                    }

                    leaf adi-pat-version {
                        type uint32;
                        description "The value indicates the version of the Program Association Table (PAT).";
                    }

                    leaf adi-pmt-version {
                        type uint32;
                        description "The value indicates the version of the Program Map Table (PMT).";
                    }

                    leaf adi-pat-changes {
                        type yang:counter32;
                        description
                            "The value indicates the total number of Program Association Table
                             (PAT) version changes.";
                    }

                    leaf adi-pmt-changes {
                        type yang:counter32;
                        description
                            "The value indicates the total number of Program Map Table (PMT)
                             version changes.";
                    }

                    leaf adi-rx-packets {
                        type yang:counter64;
                        description
                            "The value indicates the total number of Ad Insert (ADI) packets received
                             by the video ISA.";
                    }

                    leaf adi-tx-packets {
                        type yang:counter64;
                        description
                            "The value indicates the total number of Ad Insert (ADI) packets sent by
                             the video ISA.";
                    }

                    leaf adi-rx-scte35-msgs {
                        type yang:counter32;
                        description
                            "The value indicates the total number of Society of Cable Telecommunications
                             Engineers (SCTE-35) messages received by the video ISA.";
                    }

                    leaf adi-rx-scte35-msg-enc {
                        type yang:counter32;
                        description
                            "The value indicates the total number of encrypted Society of Cable
                             Telecommunications Engineers (SCTE-35) messages received by
                             the video ISA.";
                    }

                    leaf adi-adi-rx-scte35-msg-unsup {
                        type yang:counter32;
                        description
                            "The value indicates the total number of unsupported Society of Cable
                             Telecommunications Engineers (SCTE-35) messages received by the video ISA.";
                    }

                    leaf adi-adi-rx-scte35-msg-disc {
                        type yang:counter32;
                        description
                            "The value indicates the total number of Society of Cable Telecommunications
                             Engineers (SCTE-35) messages received by the video ISA and discarded. SCTE-35
                             messages with unsupported commands and encrypted SCTE-35 messages are discarded.";
                    }

                    leaf adi-unsupp-ts-len-pkts {
                        type yang:counter32;
                        description
                            "The value indicates the total number of data packets received whose size is not
                             equal to 188 bytes. The value of this object is valid only when the corresponding
                             tmnxVdoGrpADIServerState value is set to 'true'.";
                    }

                    leaf rt-client-port {
                        status obsolete;
                        type uint32 {
                            range "6000..8000";
                        }
                        description
                            "The value indicates the local port on which the Retransmission (RT) requests
                             are received.";
                    }

                    leaf dup-seq-number {
                        type yang:counter32;
                        description
                            "The value indicates the total number of Real-time Transport Protocol (RTP)
                             packets detected with a duplicate sequence number.";
                    }

                    leaf rts-tx-mc-ret-pkts {
                        type yang:counter64;
                        description
                            "The value indicates the total number of multicast packets sent in response
                             to retransmission requests.";
                    }

                    leaf rts-tx-mc-ret-bytes {
                        type yang:counter64;
                        units "bytes";
                        description
                            "The value indicates the total number of multicast bytes sent in response
                             to retransmission requests.";
                    }

                    leaf rts-tx-mc-ret-errs {
                        type yang:counter64;
                        description
                            "The value indicates the total number of errors occurred while doing multicast
                             retransmission in response to requests.";
                    }

                    leaf rts-ret-req-qnc {
                        type yang:counter64;
                        description
                            "The value indicates the total number of unicast retransmission requests quenced
                             by carrying out multicast response requests.";
                    }

                    leaf rts-ret-req-crt {
                        type yang:counter64;
                        description
                            "The value indicates the total number of multicast retransmission requests
                             created in response to the unicast retransmission.";
                    }

                    leaf rx-dup-ssrc-drops {
                        type yang:counter32;
                        description
                            "The value indicates the number of receive-packets dropped with a duplicate
                             synchronization source (SSRC) identifier.";
                    }

                    leaf dup-ssrc {
                        type yang:counter32;
                        description
                            "The value indicates the number of packets detected with a duplicate
                             synchronization source (SSRC) identifier.";
                    }

                    leaf fcc-min-duration {
                        type uint32 {
                            range "1..100000";
                        }
                        units "milliseconds";
                        description
                            "The value indicates the minimum FCC duration in msecs for FCC requests for
                             this channel.";
                    }

                    leaf audio-reorder {
                        type uint32 {
                            range "1..100000";
                        }
                        units "milliseconds";
                        description
                            "The value indicates in msecs how much earlier the audio frames are sent during
                             an FCC burst to achieve a good audio fast-channel-change experience.";
                    }

                    leaf rx-bytes-saved {
                        type yang:counter64;
                        units "bytes";
                        description
                            "The value indicates the total number of received bytes that are saved
                             on this multicast channel.";
                    }

                    leaf rx-packets-saved {
                        type yang:counter64;
                        description
                            "The value indicates the total number of received packets that are saved
                             on this multicast channel.";
                    }

                    leaf stat-oper-bw {
                        type uint32;
                        units "kilobps";
                        description
                            "The value indicates the most recently computed bandwidth of the video
                             stream averaged over the last one second.";
                    }

                    leaf router-if-name {
                        type types-sros:named-item;
                        description "The value indicates the ingress interface name for this video channel.";
                    }

                    leaf num-fcc-dented-pkts {
                        type yang:counter32;
                        description
                            "The value indicates the number of packets in the unicast FCC stream
                             that were dropped due to denting.";
                    }

                    leaf max-rtp-ts-delta {
                        type yang:counter32;
                        description
                            "The value indicates the maximum Real Time Protocol(RTP) Timestamps(Ts)
                             delta recorded up to this point in time.";
                    }

                    leaf max-ticks-delta {
                        type yang:counter64;
                        description
                            "The value indicates the maximum arrival Timestamps(Ts) delta recorded up
                             to this point in time.";
                    }

                    leaf max-ticks-delta-l32 {
                        type yang:counter32;
                        description "The value indicates the lower 32 bits of the value of max-ticks-delta.";
                    }

                    leaf max-ticks-delta-h32 {
                        type yang:counter32;
                        description "The value indicates the higher 32 bits of the value of max-ticks-delta.";
                    }

                    leaf cur-ts-jitter {
                        type yang:counter64;
                        description
                            "The value indicates the difference between the current arrival Timestamps(Ts)
                             delta and current Real Time Protocol(RTP) Timestamps(Ts) delta.";
                    }

                    leaf cur-ts-jitter-l32 {
                        type yang:counter32;
                        description "The value indicates the lower 32 bits of the value of cur-ts-jitter.";
                    }

                    leaf cur-ts-jitter-h32 {
                        type yang:counter32;
                        description "The value indicates the higher 32 bits of the value of cur-ts-jitter.";
                    }

                    leaf max-ts-jitter {
                        type yang:counter64;
                        description
                            "The value indicates the maximum difference between the arrival Timestamps(Ts)
                             delta and current Real Time Protocol(RTP) Timestamps(Ts) delta.";
                    }

                    leaf max-ts-jitter-l32 {
                        type yang:counter32;
                        description "The value indicates the lower 32 bits of the value of max-ts-jitter.";
                    }

                    leaf max-ts-jitter-h32 {
                        type yang:counter32;
                        description "The value indicates the higher 32 bits of the value of max-ts-jitter.";
                    }

                } // container src-statistics

                container src-vqm {
                    description "Enter the src-vqm context";

                    leaf oper-analyzer-st {
                        type boolean;
                        description
                            "The value indicates whether or not the analyzer is enabled for
                             the multicast stream.";
                    }

                    leaf oper-cc-error {
                        type boolean;
                        description
                            "The value indicates whether or not the continuity counter error is enabled
                             for the multicast stream.";
                    }

                    leaf oper-pat-rep-error {
                        type boolean;
                        description
                            "The value indicates whether or not PAT (Program Association Table) repetition
                             error is enabled for the multicast stream.";
                    }

                    leaf oper-tnc-pat-rep {
                        type uint32;
                        units "milliseconds";
                        description
                            "The value indicates the value of TNC (Tech Non-Conformant) in milli-seconds
                             for PAT repetition and is always a multiple of 100.";
                    }

                    leaf oper-qos-pat-rep {
                        type uint32;
                        units "milliseconds";
                        description
                            "The value indicates the value of QOS (Quality of Service) in milli-seconds
                             for PAT repetition and is always a multiple of 100.";
                    }

                    leaf oper-poa-pat-rep {
                        type uint32;
                        units "milliseconds";
                        description
                            "The value indicates the value of TOA (Transport Stream off Air) in milli-seconds
                             for PAT repetition and is always a multiple of 100.";
                    }

                    leaf oper-pat-syntax {
                        type boolean;
                        description
                            "The value indicates whether or not PAT syntax error is enabled for
                             the multicast stream.";
                    }

                    leaf oper-pcr-rep-error {
                        type boolean;
                        description
                            "The value indicates whether or not PCR (Program Clock Reference) repetition
                             error is enabled for the multicast stream.";
                    }

                    leaf oper-tnc-pcr-rep {
                        type uint32;
                        units "milliseconds";
                        description
                            "The value indicates the value of TNC (Tech Non-Conformant) in milli-seconds
                             for PCR repetition and is always a multiple of 100.";
                    }

                    leaf oper-qos-pcr-rep {
                        type uint32;
                        units "milliseconds";
                        description
                            "The value indicates the value of QOS (Quality of Service) in milli-seconds
                             for PCR repetition and is always a multiple of 100.";
                    }

                    leaf oper-poa-pcr-rep {
                        type uint32;
                        units "milliseconds";
                        description
                            "The value indicates the value of POA (Program off Air) in milli-seconds for
                             PAT repetition and is always a multiple of 100.";
                    }

                    leaf oper-vid-pid-abs {
                        type uint32;
                        units "milliseconds";
                        description
                            "The value indicates the counting interval which accumulates the
                             number of video PID absent errors for the multicast PID stream.";
                    }

                    leaf oper-pid-pmt-unref {
                        type boolean;
                        description
                            "The value indicates whether or not unreferenced PID (i.e. PIDs not specified
                             in the PMT) error is enabled for the multicast stream.";
                    }

                    leaf oper-pmt-rep-error {
                        type boolean;
                        description
                            "The value indicates whether or not PMT (Program Map Table) repetition error
                             is enabled for the multicast stream.";
                    }

                    leaf oper-tnc-pmt-rep {
                        type uint32;
                        units "milliseconds";
                        description
                            "The value of tmnxVdoGrpSrcVqmOperTncPmtRep indicates the value of
                             TNC (Tech Non-Conformance) in milli-seconds for PMT repetition and
                             is always a multiple of 100.";
                    }

                    leaf oper-qos-pmt-rep {
                        type uint32;
                        units "milliseconds";
                        description
                            "The value indicates the value of QOS (Quality of Service) in milli-seconds
                             for PMT repetition and is always a multiple of 100.";
                    }

                    leaf oper-poa-pmt-rep {
                        type uint32;
                        units "milliseconds";
                        description
                            "The value indicates the value of POA (Program off Air) in milli-seconds
                             for PMT repetition and is always a multiple of 100.";
                    }

                    leaf oper-pmt-syntax {
                        type boolean;
                        description
                            "The value indicates whether or not PMT syntax error is enabled for
                             the multicast stream.";
                    }

                    leaf oper-scte35-error {
                        type boolean;
                        description
                            "The value indicates whether or not Society of Cable Telecommunications
                             Engineers (SCTE-35) errors are enabled for the multicast stream.";
                    }

                    leaf oper-tei-error {
                        type boolean;
                        description
                            "The value indicates whether or not TEI (Transport Error Indicator) error
                             is enabled for the multicast stream.";
                    }

                    leaf oper-ts-sync-loss {
                        type boolean;
                        description
                            "The value indicates whether or not sync loss error is enabled for
                             the multicast stream.";
                    }

                    leaf oper-non-vid-pid-abs {
                        type uint32;
                        units "milliseconds";
                        description
                            "The value indicates the counting interval for an the instance of
                             which accumulates the number of non-video PID absent errors for
                             the multicast PID stream.";
                    }

                    leaf oper-report-alarm {
                        type enumeration {
                            enum none                           { value 0; }
                            enum tnc                            { value 1; }
                            enum qos                            { value 2; }
                            enum poa                            { value 3; }
                        }
                        description
                            "The value indicates the severity of the analyzer state alarm for
                             the multicast stream.";
                    }

                } // container src-vqm

                list src-vqm-statistics {
                    key "stats-period stats-time";
                    description "Enter the src-vqm-statistics list instance";

                    leaf stats-period {
                        type enumeration {
                            enum current                        { value 1; }
                            enum interval                       { value 2; }
                        }
                        description
                            "The value of indicates the period of statistics that the user is interested
                             in. The parameter can take a value of 'current' which would display to the user
                             all statistics within the last second. Alternatively it could be a value of
                             'interval' in which case the actual time-duration for which statistics are displayed
                             to the user is specified by 'stats-time'.";
                    }

                    leaf stats-time {
                        type uint32;
                        description
                            "The value is effectively based on the value of 'stats-period'. If 'stats-period' has
                             a value of 'current', then this object has no functionality and gets assigned
                             a numerical value of '0'. If 'stats-period' has a value of 'interval', then this
                             object specifies the duration of the time-interval in minutes for which the statistics
                             will be displayed to the user.";
                    }

                    leaf good-secs {
                        type uint32;
                        units "seconds";
                        description
                            "The value indicates the total number of good seconds for the stream
                             on this multicast channel.";
                    }

                    leaf err-secs {
                        type uint32;
                        units "seconds";
                        description
                            "The value indicates the total number of errored seconds for the stream
                             on this multicast channel.";
                    }

                    leaf degr-secs {
                        type uint32;
                        units "seconds";
                        description
                            "The value indicates the total number of degraded seconds for the stream
                             on this multicast channel.";
                    }

                    leaf impair-secs {
                        type uint32;
                        units "seconds";
                        description
                            "The value indicates the total number of impaired seconds for the stream
                             on this multicast channel.";
                    }

                    leaf pmt-rep-err-secs {
                        type uint32;
                        units "seconds";
                        description
                            "The value indicates the total number of PMT (Program Map Table) repetition
                             error seconds for the stream on this multicast channel.";
                    }

                    leaf pmt-rep-deg-secs {
                        type uint32;
                        units "seconds";
                        description
                            "The value indicates the total number of PMT (Program Map Table) repetition
                             degraded seconds for the stream on this multicast channel.";
                    }

                    leaf pmt-rep-imp-secs {
                        type uint32;
                        units "seconds";
                        description
                            "The value indicates the total number of PMT (Program Map Table) repetition
                             impaired seconds for the stream on this multicast channel.";
                    }

                    leaf pmt-syntx-err-secs {
                        type uint32;
                        units "seconds";
                        description
                            "The value indicates  the total number of PMT syntax error seconds for
                             the stream on this multicast channel.";
                    }

                    leaf pat-rep-err-secs {
                        type uint32;
                        units "seconds";
                        description
                            "The value indicates the total number of PAT (Program Association Table)
                             repetition error seconds for the stream on this multicast channel.";
                    }

                    leaf pat-rep-deg-secs {
                        type uint32;
                        units "seconds";
                        description
                            "The value indicates the total number of PAT (Program Association Table)
                             repetition degraded seconds for the stream on this multicast channel.";
                    }

                    leaf pat-rep-imp-secs {
                        type uint32;
                        units "seconds";
                        description
                            "The value indicates the total number of PAT (Program Association Table)
                             repetition impaired seconds for the stream on this multicast channel.";
                    }

                    leaf pat-syntx-err-secs {
                        type uint32;
                        units "seconds";
                        description
                            "The value indicates  the total number of PAT syntax error seconds for
                             the stream on this multicast channel.";
                    }

                    leaf pcr-rep-err-secs {
                        type uint32;
                        units "seconds";
                        description
                            "The value indicates the total number of PCR (Program Clock Reference)
                             repetition error seconds for the video stream with VQM.";
                    }

                    leaf pcr-rep-deg-secs {
                        type uint32;
                        units "seconds";
                        description
                            "The value indicates the total number of PCR (Program Clock Reference)
                             repetition degraded seconds for the stream on this multicast channel.";
                    }

                    leaf pcr-rep-imp-secs {
                        type uint32;
                        units "seconds";
                        description
                            "The value indicates the total number of PCR (Program Clock Reference)
                             repetition impaired seconds for the stream on this multicast channel.";
                    }

                    leaf sync-byte-err-secs {
                        type uint32;
                        units "seconds";
                        description
                            "The value indicates the total number of sync byte error seconds for
                             the stream on this multicast channel.";
                    }

                    leaf sync-loss-secs {
                        type uint32;
                        units "seconds";
                        description
                            "The value indicates the total number of sync loss seconds for the stream
                             on this multicast channel.";
                    }

                    leaf cat-err-secs {
                        type uint32;
                        units "seconds";
                        description
                            "The value indicates the total number of CAT (Conditional Access Table)
                             error seconds for the stream on this multicast channel.";
                    }

                    leaf unref-pid-err-secs {
                        type uint32;
                        units "seconds";
                        description
                            "The value indicates the total number of unreferenced PID error seconds
                             for the stream on this multicast channel.";
                    }

                    leaf mdi-delay-factor {
                        type uint32;
                        units "milliseconds";
                        description
                            "The value indicates Media Delivery Index (MDI) delay factor. If the value
                             of this object is '4294967295' (0xFFFFFFFF) then this indicates there is
                             no media stream.";
                    }

                    leaf mdi-loss-rate {
                        type binary {
                            length "8";
                        }
                        description "The value indicates Media Delivery Index (MDI) loss Rate.";
                    }

                    leaf min-gop-length {
                        type uint32;
                        units "pictures";
                        description
                            "The value indicates the minimum distance in a Group Of Pictures (GOP) between
                             two consecutive I-frames within a sequence of frames in that video stream
                             on a multicast channel.";
                    }

                    leaf min-frm-per-sec {
                        type uint32;
                        units "fps";
                        description
                            "The value indicates the minimum number of frames per second in a video stream
                             on a multicast channel.";
                    }

                    leaf avg-gop-length {
                        type uint32;
                        units "pictures";
                        description
                            "The value indicates the average distance in a Group Of Pictures (GOP) between
                             two consecutive I-frames within a sequence of frames in that video stream
                             on a multicast channel.";
                    }

                    leaf avg-frm-per-sec {
                        type uint32;
                        units "fps";
                        description
                            "The value indicates the average number of frames per second in a video stream
                             on a multicast channel.";
                    }

                    leaf max-gop-length {
                        type uint32;
                        units "pictures";
                        description
                            "The value indicates the maximum distance in a Group Of Pictures (GOP) between
                             two consecutive I-frames within a sequence of frames in that video stream
                             on a multicast channel.";
                    }

                    leaf max-frm-per-sec {
                        type uint32;
                        units "fps";
                        description
                            "The value indicates the maximum number of frames per second in a video stream
                             on a multicast channel.";
                    }

                    leaf good-i-frames {
                        type uint32;
                        description
                            "The value indicates the number of good 'I' frames in a video stream on
                             a multicast channel.";
                    }

                    leaf bad-i-frames {
                        type uint32;
                        description
                            "The value indicates the number of bad 'I' frames in a video stream on
                             a multicast channel.";
                    }

                    leaf good-p-frames {
                        type uint32;
                        description
                            "The value indicates the number of good 'P' frames in a video stream on
                             a multicast channel.";
                    }

                    leaf bad-p-frames {
                        type uint32;
                        description
                            "The value indicates the number of bad 'P' frames in a video stream on
                             a multicast channel.";
                    }

                    leaf good-b-frames {
                        type uint32;
                        description
                            "The value indicates the number of good 'B' frames in a video stream on
                             a multicast channel.";
                    }

                    leaf bad-b-frames {
                        type uint32;
                        description
                            "The value indicates the number of bad 'B' frames in a video stream on
                             a multicast channel.";
                    }

                    leaf traffic-loss-secs {
                        type uint32;
                        units "seconds";
                        description
                            "The value indicates loss of traffic seconds in a stream on a multicast
                             channel.";
                    }

                } // list src-vqm-statistics

                list pid {
                    key "pid";
                    description "Enter the pid list instance";

                    leaf pid {
                        type uint32 {
                            range "0..8191";
                        }
                        description
                            "The value indicates the 13-bit packet identifier used to identify the type
                             of data stored in the packet payload.";
                    }

                    leaf pid-type {
                        type enumeration {
                            enum other                          { value 0; }
                            enum audio                          { value 1; }
                            enum video                          { value 2; }
                            enum data                           { value 3; }
                            enum ca                             { value 4; }
                            enum scte35                         { value 5; }
                            enum pat                            { value 6; }
                            enum pcr                            { value 7; }
                            enum pmt                            { value 8; }
                        }
                        description
                            "The value indicates the type of the packet identifier.
                             other  (0) - Unspecified stream type
                             audio  (1) - audio stream
                             video  (2) - video stream
                             data   (3) - data stream
                             ca     (4) - conditional access stream
                             scte35 (5) - Society of Cable Telecommunications
                                          Engineers 35 stream
                             pat    (6) - program association table
                             pcr    (7) - program clock reference
                             pmt    (8) - program map table.";
                    }

                    leaf pid-mpeg-stream-type {
                        type uint32;
                        description "The value indicates the type of MPEG stream.";
                    }

                    leaf pid-language {
                        type types-sros:named-item;
                        description "The value indicates the language of the MPEG stream.";
                    }

                    leaf pid-cc-err-secs {
                        type uint32;
                        units "seconds";
                        description
                            "The value indicates the total number of continuity counter error seconds
                             for the MPEG stream.";
                    }

                    leaf pid-tei-err-secs {
                        type uint32;
                        units "seconds";
                        description
                            "The value indicates the total number of TEI (Transport Error Indicator)
                             error seconds for the MPEG stream.";
                    }

                    leaf pid-absent-err-secs {
                        type uint32;
                        description
                            "The value of tmnxVdoPIDAbsentErrSecs indicates the total number of
                             video or non-video PID (Program Identifier) absent error seconds for
                             the MPEG stream based on the PID type. This object has separate
                             instances for each PID type within a video stream based on bundle,
                             channel and source-override configurations.";
                    }

                    leaf pid-bit-rate {
                        type uint32;
                        units "kilobps";
                        description "The value indicates the bitrate of the stream.";
                    }

                    leaf pid-is-pcr {
                        type boolean;
                        description "The value indicates whether or not this is a Program Clock Reference(PCR) PID.";
                    }

                } // list pid

                list splice-status {
                    status obsolete;
                    key "sg-splice-start-time";
                    description "Enter the splice-status list instance";

                    leaf sg-splice-start-time {
                        status obsolete;
                        type uint32;
                        units "seconds";
                        description "The value indicates the start time of splice in seconds.";
                    }

                    leaf sg-splice-ad-server-addr {
                        status obsolete;
                        type types-sros:ipv4-address;
                        description
                            "The value indicates the address of the Ad Insert (ADI) server that issued
                             the splice request.";
                    }

                    leaf sg-splice-status {
                        status obsolete;
                        type enumeration {
                            enum init                           { value 1; }
                            enum pending                        { value 2; }
                            enum in-progress                    { value 3; }
                            enum complete                       { value 4; }
                        }
                        description "The value indicates the status of this splice request.";
                    }

                    leaf sg-splice-duration-req {
                        status obsolete;
                        type uint32;
                        units "seconds";
                        description
                            "The value indicates the splice duration, in seconds, of the ad requested
                             by the Ad Insert (ADI) server.";
                    }

                    leaf sg-splice-duration-played {
                        status obsolete;
                        type uint32;
                        units "seconds";
                        description "The value indicates the splice duration, in seconds, played by the splicer.";
                    }

                    leaf sg-splice-rate {
                        status obsolete;
                        type uint32;
                        units "kilobps";
                        description
                            "The value indicates the rate of the ad stream, in kilobits per second (kbps),
                             received by the splicer.";
                    }

                    leaf sg-splice-session-id {
                        status obsolete;
                        type uint32;
                        description "The value indicates the session ID of the ad request.";
                    }

                    leaf sg-splice-prior-session-id {
                        status obsolete;
                        type uint32;
                        description
                            "The value indicates the prior session id of the ad. If the value of this object
                             is not equal to 0xFFFFFFFF, then this splice is a back-to-back ad insertion.";
                    }

                    leaf sg-splice-abort-reason {
                        status obsolete;
                        type enumeration {
                            enum none                           { value 0; }
                            enum unknown                        { value 1; }
                            enum ad-srvr-req                    { value 2; }
                            enum splice-not-found               { value 3; }
                            enum no-primary-channel             { value 4; }
                            enum no-insert-channel              { value 5; }
                            enum too-early                      { value 6; }
                            enum splice-failed                  { value 7; }
                            enum splice-collision               { value 8; }
                            enum splice-too-late                { value 9; }
                            enum splice-queue-full              { value 10; }
                            enum invalid-session-id             { value 11; }
                            enum session-incomplete             { value 12; }
                        }
                        description
                            "The value indicates the reason if a splice operation has been aborted. If the value
                             of this object is equal to 'none', then the splice has not been aborted. ";
                    }

                    leaf sg-splice-splice-in-seq-num {
                        status obsolete;
                        type uint32;
                        description "The value indicates the sequence number at which the splice-in to the ad occurred.";
                    }

                    leaf sg-splice-splice-out-seq-num {
                        status obsolete;
                        type uint32;
                        description "The value indicates the sequence number at which the splice-out to the ad occurred.";
                    }

                    leaf sg-splice-num-blk-frames {
                        status obsolete;
                        type uint32;
                        description "The value indicates the number of black frames inserted.";
                    }

                    leaf sg-splice-blk-frame-pts {
                        status obsolete;
                        type types-sros:named-item;
                        description "The value indicates the Presentation Timestamp (PTS) of the first black frame.";
                    }

                    leaf sg-splice-max-ad-pts {
                        status obsolete;
                        type types-sros:named-item;
                        description
                            "The value indicates the maximum Presentation Timestamp (PTS) value of the last Group
                             of Pictures (GOP) of ad stream (non-black frame).";
                    }

                    leaf sg-splice-min-nw-pts {
                        status obsolete;
                        type types-sros:named-item;
                        description
                            "The value indicates the minimum Presentation Timestamp (PTS) value from the first
                             Group of Pictures (GOP) of the network stream after the splice out has occurred.";
                    }

                } // list splice-status

                list adi-statistics {
                    status obsolete;
                    key "adi-server-addr";
                    description "Enter the adi-statistics list instance";

                    leaf adi-server-addr {
                        status obsolete;
                        type types-sros:ipv4-address;
                        description "The value indicates the address of Ad Insert (ADI) server on this channel.";
                    }

                    leaf adi-server-uptime {
                        status obsolete;
                        type uint32;
                        units "seconds";
                        description
                            "The value indicates the time in seconds since the connection with
                             Ad Insert (ADI) server was established.";
                    }

                    leaf adi-init-req {
                        status obsolete;
                        type yang:counter32;
                        description
                            "The value indicates the total number of init requests received from
                             the Ad Insert (ADI) server.";
                    }

                    leaf adi-suc-init-resp {
                        status obsolete;
                        type yang:counter32;
                        description
                            "The value indicates the total number of successful init responses sent
                             to the Ad Insert (ADI) server.";
                    }

                    leaf adi-unsuc-init-resp {
                        status obsolete;
                        type yang:counter32;
                        description
                            "The value indicates the total number of unsuccessful init responses sent
                             to the Ad Insert (ADI) server.";
                    }

                    leaf adi-alive-req {
                        status obsolete;
                        type yang:counter32;
                        description
                            "The value indicates the total number of alive messages received from
                             the Ad Insert (ADI) server.";
                    }

                    leaf adi-suc-alive-resp {
                        status obsolete;
                        type yang:counter32;
                        description
                            "The value indicates the total number of successful alive messages sent
                             to the Ad Insert (ADI) server.";
                    }

                    leaf adi-un-suc-alive-resp {
                        status obsolete;
                        type yang:counter32;
                        description
                            "The value indicates the total number of unsuccessful alive messages sent
                             to the Ad Insert (ADI) server.";
                    }

                    leaf adi-cue-req {
                        status obsolete;
                        type yang:counter32;
                        description
                            "The value indicates the total number of total number of cue requests sent
                             to the Ad Insert (ADI) server.";
                    }

                    leaf adi-suc-cue-resp {
                        status obsolete;
                        type yang:counter32;
                        description
                            "The value indicates the total number of successful cue responses received
                             from the Ad Insert (ADI) server.";
                    }

                    leaf adi-unsuc-cue-resp {
                        status obsolete;
                        type yang:counter32;
                        description
                            "The value indicates the total number of unsuccessful cue responses received
                             from the Ad Insert (ADI) server.";
                    }

                    leaf adi-abort-req {
                        status obsolete;
                        type yang:counter32;
                        description
                            "The value indicates the total number of abort requests received from
                             the Ad Insert (ADI) server.";
                    }

                    leaf adi-suc-abort-resp {
                        status obsolete;
                        type yang:counter32;
                        description
                            "The value indicates the total number of successful abort responses sent
                             to the Ad Insert (ADI) server. ";
                    }

                    leaf adi-unsuc-abort-resp {
                        status obsolete;
                        type yang:counter32;
                        description
                            "The value indicates the total number of unsuccessful abort responses sent
                             to the Ad Insert (ADI) server.";
                    }

                    leaf adi-unknown-scte30-req {
                        status obsolete;
                        type yang:counter32;
                        description
                            "The value indicates the total number of invalid Society of Cable
                             Telecommunications Engineers 30 (SCTE-30) requests received from
                             the Ad Insert (ADI) server.";
                    }

                    leaf adi-splice-req {
                        status obsolete;
                        type yang:counter32;
                        description
                            "The value indicates the total number of splice requests received from
                             the Ad Insert (ADI) server.";
                    }

                    leaf adi-suc-splice-resp {
                        status obsolete;
                        type yang:counter32;
                        description
                            "The value indicates the total number of successful splice responses sent
                             to the Ad Insert (ADI) server.";
                    }

                    leaf adi-unsuc-splice-resp {
                        status obsolete;
                        type yang:counter32;
                        description
                            "The value indicates the total number of unsuccessful splice responses sent
                             to the Ad Insert (ADI) server.";
                    }

                    leaf adi-suc-splice-in-comp-resp {
                        status obsolete;
                        type yang:counter32;
                        description
                            "The value indicates the total number of successful splice-in complete responses
                             sent to the Ad Insert (ADI) server.";
                    }

                    leaf adi-suc-splice-out-comp-resp {
                        status obsolete;
                        type yang:counter32;
                        description
                            "The value indicates the total number of successful splice-out complete responses
                             sent to the Ad Insert (ADI) server.";
                    }

                    leaf adi-unsuc-splice-out-com-res {
                        status obsolete;
                        type yang:counter32;
                        description
                            "The value indicates the total number of unsuccessful splice-out complete responses
                             sent to the Ad Insert (ADI) server.";
                    }

                    leaf adi-min-port {
                        status obsolete;
                        type yang:counter32;
                        description
                            "The value indicates the minimum ip port number where the Ad Insert (ADI) server's
                             insertion stream is connected.";
                    }

                    leaf adi-max-port {
                        status obsolete;
                        type yang:counter32;
                        description
                            "The value indicates the maximum ip port number where the Ad Insert (ADI) server's
                             insertion stream is connected.";
                    }

                    leaf adi-chl-name {
                        status obsolete;
                        type types-sros:named-item;
                        description "The value indicates the channel name associated for this multicast group.";
                    }

                } // list adi-statistics

            } // list channel

            list statistics {
                key "address";
                description "Enter the statistics list instance";

                leaf address {
                    type types-sros:ipv4-prefix-with-host-bits;
                    description "The value of this object specifies the IPv4 address assigned to a router's interface.";
                }

                leaf hd-rt-server-state {
                    type boolean;
                    description
                        "The value indicates whether the High Definition (HD)
                         retransmission server is enabled on this interface.";
                }

                leaf sd-rt-server-state {
                    type boolean;
                    description
                        "The value indicates whether the Standard Definition (SD)
                         retransmission server is enabled on this interface.";
                }

                leaf pip-rt-server-state {
                    type boolean;
                    description
                        "The value indicates whether the Picture-in-Picture (PIP)
                         retransmission server is enabled on this interface.";
                }

                leaf rt-svr-sd-rtp-pkts-req {
                    type yang:counter64;
                    description
                        "The value indicates the total number of Standard Definition (SD)
                         channel Real-time Transport Protocol (RTP)packets requested in
                         the Real-time Transport Control Protocol (RTCP) feedback (FB)
                         messages received on this interface.";
                }

                leaf rt-svr-hd-rtp-pkts-req {
                    type yang:counter64;
                    description
                        "The value indicates the total number of High Definition (HD) channel
                         Real-time Transport Protocol (RTP) packets requested in the Real-time
                         Transport Control Protocol (RTCP) feedback (FB) messages received on
                         this interface.";
                }

                leaf rt-svr-pip-rtp-pkts-req {
                    type yang:counter64;
                    description
                        "The value indicates the total number of Picture-In-Picture (PIP) channel
                         Real-time Transport Protocol (RTP) packets requested in the Real-time
                         Transport Control Protocol (RTCP) feedback (FB) messages received on
                         this interface.";
                }

                leaf rt-svr-rx-sd-rt-req {
                    type yang:counter64;
                    description
                        "The value indicates the total number of Retransmission (RT) requests
                         received from Standard Definition (SD) channels on this interface.";
                }

                leaf rt-svr-rx-sd-failed-req {
                    type yang:counter64;
                    description
                        "The value indicates the total number of failed Retransmission (RT) requests
                         received from Standard Definition (SD) channels on this interface.";
                }

                leaf rt-svr-rx-hd-rt-req {
                    type yang:counter64;
                    description
                        "The value indicates the total number of Retransmission (RT) requests
                         received from High Definition (HD) channels on this interface.";
                }

                leaf rt-svr-rx-hd-failed-req {
                    type yang:counter64;
                    description
                        "The value indicates the total number of failed Retransmission (RT) requests
                         received from High Definition (HD) channels on this interface.";
                }

                leaf rt-svr-rx-pip-rt-req {
                    type yang:counter64;
                    description
                        "The value indicates the total number of Retransmission (RT) requests received
                         from Picture-In-Picture (PIP) channels on this interface.";
                }

                leaf rt-svr-rx-pip-failed-req {
                    type yang:counter64;
                    description
                        "The value indicates the total number of failed Retransmission (RT) requests
                         received from Picture-In-Picture (PIP) channels on this interface.";
                }

                leaf rt-svr-tx-sd-rt-replies {
                    type yang:counter64;
                    description
                        "The value indicates the total number of Standard Definition (SD) channel
                         Retransmission (RT) replies sent from this interface.";
                }

                leaf rt-svr-tx-sd-bytes {
                    type yang:counter64;
                    units "bytes";
                    description
                        "The value indicates the total number of Standard Definition (SD) channel
                         bytes sent from this interface.";
                }

                leaf rt-svr-tx-sd-packets {
                    type yang:counter64;
                    description
                        "The value indicates the total number of Standard Definition (SD) channel
                         packets sent from this interface.";
                }

                leaf rt-svr-tx-hd-rt-replies {
                    type yang:counter64;
                    description
                        "The value indicates the total number of High Definition (HD) channel
                         Retransmission (RT) replies sent from this interface.";
                }

                leaf rt-svr-tx-hd-bytes {
                    type yang:counter64;
                    units "bytes";
                    description
                        "The value indicates the total number of High Definition (HD) channel
                         bytes sent from this interface.";
                }

                leaf rt-svr-tx-hd-packets {
                    type yang:counter64;
                    description
                        "The value indicates the total number of High Definition (HD) channel
                         packets sent from this interface.";
                }

                leaf rt-svr-tx-pip-rt-replies {
                    type yang:counter64;
                    description
                        "The value indicates the total number of Picture-In-Picture (PIP) channel
                         Retransmission (RT) replies sent from this interface.";
                }

                leaf rt-svr-tx-pip-bytes {
                    type yang:counter64;
                    units "bytes";
                    description
                        "The value indicates the total number of Picture-In-Picture (PIP) channel
                         bytes sent from this interface.";
                }

                leaf rt-svr-tx-pip-packets {
                    type yang:counter64;
                    description
                        "The value indicates the total number of Picture-In-Picture (PIP) channel
                         packets sent from this interface.";
                }

                leaf hd-fcc-server-mode {
                    type types-mcast-mgmt:mode;
                    description
                        "The value indicates the mode of the High Definition (HD) Fast Channel Change
                         (FCC) server on this interface.";
                }

                leaf sd-fcc-server-mode {
                    type types-mcast-mgmt:mode;
                    description
                        "The value indicates the mode of the Standard Definition (SD) Fast Channel Change
                         (FCC) server on this interface.";
                }

                leaf pip-fcc-server-mode {
                    type types-mcast-mgmt:mode;
                    description
                        "The value indicates the mode of the Picture-in-Picture (PIP) Fast Channel Change
                         (FCC) server on this interface.";
                }

                leaf fcc-sr-rx-sd-fcc-req {
                    type yang:counter64;
                    description
                        "The value indicates the total number of Fast Channel Change (FCC) requests
                         received from Standard Definition (SD) channels on this interface.";
                }

                leaf fcc-sr-rx-sd-failed-req {
                    type yang:counter64;
                    description
                        "The value indicates the total number of failed Fast Channel Change (FCC)
                         requests received from Standard Definition (SD) channels on this interface.";
                }

                leaf fcc-sr-rx-hd-fcc-req {
                    type yang:counter64;
                    description
                        "The value indicates the total number of Fast Channel Change (FCC) requests
                         received from High Definition (HD) channels on this interface.";
                }

                leaf fcc-sr-rx-hd-failed-req {
                    type yang:counter64;
                    description
                        "The value indicates the total number of failed Fast Channel Change (FCC)
                         requests received from High Definition (HD) channels on this interface.";
                }

                leaf fcc-sr-rx-pip-fcc-req {
                    type yang:counter64;
                    description
                        "The value indicates the total number of Fast Channel Change (FCC) requests
                         received from Picture-In-Picture (PIP) channels on this interface.";
                }

                leaf fcc-sr-rx-pip-failed-req {
                    type yang:counter64;
                    description
                        "The value indicates the total number of failed Fast Channel Change (FCC)
                         requests received from Picture-In-Picture (PIP) channels on this interface.";
                }

                leaf fcc-sr-tx-sd-fcc-replies {
                    type yang:counter64;
                    description
                        "The value indicates the total number of Standard Definition (SD) channel
                         Fast Channel Change (FCC) replies sent from this interface.";
                }

                leaf fcc-sr-tx-sd-bytes {
                    type yang:counter64;
                    units "bytes";
                    description
                        "The value indicates the total number of Standard Definition (SD) channel bytes
                         sent from this interface.";
                }

                leaf fcc-sr-tx-sd-packets {
                    type yang:counter64;
                    description
                        "The value indicates the total number of Standard Definition (SD) channel
                         packets sent from this interface.";
                }

                leaf fcc-sr-tx-hd-fcc-replies {
                    type yang:counter64;
                    description
                        "The value indicates the total number of High Definition (HD) channel
                         Fast Channel Change (FCC) replies sent from this interface.";
                }

                leaf fcc-sr-tx-hd-bytes {
                    type yang:counter64;
                    units "bytes";
                    description
                        "The value indicates the total number of High Definition (HD) channel bytes
                         sent from this interface.";
                }

                leaf fcc-sr-tx-hd-packets {
                    type yang:counter64;
                    description
                        "The value indicates the total number of High Definition (HD) channel packets
                         sent from this interface.";
                }

                leaf fcc-sr-tx-pip-fcc-replies {
                    type yang:counter64;
                    description
                        "The value indicates the total number of Picture-In-Picture (PIP) channel
                         Fast Channel Change (FCC) replies sent from this interface.";
                }

                leaf fcc-sr-tx-pip-bytes {
                    type yang:counter64;
                    units "bytes";
                    description
                        "The value indicates the total number of Picture-In-Picture (PIP) channel
                         bytes sent from this interface.";
                }

                leaf fcc-sr-tx-pip-packets {
                    type yang:counter64;
                    description
                        "The value indicates the total number of Picture-In-Picture (PIP) channel
                         packets sent from this interface.";
                }

                leaf tx-failed-packets {
                    type yang:counter64;
                    description
                        "The value indicates the total number of failures during the transmission
                         of packets from this video interface. Failure happens when the packet to be
                         sent is not stored in the video cache.";
                }

                leaf scte30-tcp-sessions {
                    status obsolete;
                    type yang:counter32;
                    description
                        "The value indicates the total number of scte30 tcp sessions with the Ad Insert
                         (ADI) servers for this interface.";
                }

                leaf scte30-init-sessions {
                    status obsolete;
                    type yang:counter32;
                    description
                        "The value indicates the total number of scte30 init sessions with the Ad Insert
                         (ADI) servers for this interface.";
                }

                leaf rts-sd-mc-rd-pkts-req {
                    type yang:counter64;
                    description
                        "The value indicates the total number of multicast retransmission requests created
                         for Standard Definition (SD) channels on this interface.";
                }

                leaf rts-hd-mc-rd-pkts-req {
                    type yang:counter64;
                    description
                        "The value indicates the total number of multicast retransmission requests
                         created for High Definition (HD) channels on this interface.";
                }

                leaf rts-pip-mc-rd-pkt-req {
                    type yang:counter64;
                    description
                        "The value indicates the total number of multicast retransmission requests
                         created for Picture-In-Picture (PIP) channels on this interface.";
                }

                leaf sd-pkt-lost-in-seq10 {
                    type yang:counter32;
                    description
                        "The value indicates the total number of packets within sequences of
                         2 to 10 consecutive lost packets for Standard Definition (SD) channels
                         on this video interface.";
                }

                leaf sd-pkt-lost-in-seq20 {
                    type yang:counter32;
                    description
                        "The value indicates the total number of packets within sequences of
                         11 to 20 consecutive lost packets for Standard Definition (SD) channels
                         on this video interface.";
                }

                leaf sd-pkt-lost-in-seq30 {
                    type yang:counter32;
                    description
                        "The value indicates the total number of packets within sequences of
                         21 to 30 consecutive lost packets for Standard Definition (SD) channels
                         on this video interface.";
                }

                leaf sd-pkt-lost-in-seq40 {
                    type yang:counter32;
                    description
                        "The value indicates the total number of packets within sequences of
                         31 to 40 consecutive lost packets for Standard Definition (SD) channels
                         on this video interface.";
                }

                leaf sd-pkt-lost-in-seq-more {
                    type yang:counter32;
                    description
                        "The value indicates the total number of packets within sequences of
                         41 or more consecutive lost packets for Standard Definition (SD) channels
                         on this video interface.";
                }

                leaf hd-pkt-lost-in-seq10 {
                    type yang:counter32;
                    description
                        "The value indicates the total number of packets within sequences of
                         2 to 10 consecutive lost packets for High Definition (HD) channels
                         on this video interface.";
                }

                leaf hd-pkt-lost-in-seq20 {
                    type yang:counter32;
                    description
                        "The value indicates the total number of packets within sequences of
                         11 to 20 consecutive lost packets for High Definition (HD) channels
                         on this video interface.";
                }

                leaf hd-pkt-lost-in-seq30 {
                    type yang:counter32;
                    description
                        "The value indicates the total number of packets within sequences of
                         21 to 30 consecutive lost packets for High Definition (HD) channels
                         on this video interface.";
                }

                leaf hd-pkt-lost-in-seq40 {
                    type yang:counter32;
                    description
                        "The value indicates the total number of packets within sequences of
                         31 to 40 consecutive lost packets for High Definition (HD) channels on
                         this video interface.";
                }

                leaf hd-pkt-lost-in-seq-more {
                    type yang:counter32;
                    description
                        "The value indicates the total number of packets within sequences of 41
                         or more consecutive lost packets for High Definition (HD) channels on
                         this video interface.";
                }

                leaf pip-pkt-lost-in-seq10 {
                    type yang:counter32;
                    description
                        "The value indicates the total number of packets within sequences of 2 to 10
                         consecutive lost packets for Picture-In-Picture (PIP) channels on this video
                         interface.";
                }

                leaf pip-pkt-lost-in-seq20 {
                    type yang:counter32;
                    description
                        "The value indicates the total number of packets within sequences of
                         11 to 20 consecutive lost packets for Picture-In-Picture (PIP) channels
                         on this video interface.";
                }

                leaf pip-pkt-lost-in-seq30 {
                    type yang:counter32;
                    description
                        "The value indicates the total number of packets within sequences of
                         21 to 30 consecutive lost packets for
                         Picture-In-Picture (PIP) channels on this video interface.";
                }

                leaf pip-pkt-lost-in-seq40 {
                    type yang:counter32;
                    description
                        "The value indicates the total number of packets within sequences of
                         31 to 40 consecutive lost packets for Picture-In-Picture (PIP) channels
                         on this video interface.";
                }

                leaf pip-pkt-lost-in-seq-more {
                    type yang:counter32;
                    description
                        "The value indicates the total number of packets within sequences of 41
                         or more consecutive lost packets for Picture-In-Picture (PIP) channels
                         on this video interface.";
                }

                leaf rx-rtcp-app-rep-sum {
                    type yang:counter64;
                    description
                        "The value indicates the total number of  Real Time Transport Control
                         Protocol (RTCP) App requests processed for currently active sessions
                         for the interface.";
                }

                leaf rx-rtcp-app-rep-sum-l {
                    type yang:counter32;
                    description "The value indicates the lower 32 bits of the value of rx-rtcp-app-rep-sum.";
                }

                leaf rx-rtcp-app-rep-sum-h {
                    type yang:counter32;
                    description "The value indicates the higher 32 bits of the value of rx-rtcp-app-rep-sum.";
                }

                leaf rx-rtcp-app-req-sum {
                    type yang:counter64;
                    description
                        "The value indicates the total number of  Real Time Transport Control Protocol
                         (RTCP) App requests received for currently active sessions for the interface.";
                }

                leaf rx-rtcp-app-req-sum-l {
                    type yang:counter32;
                    description "The value indicates the lower 32 bits of the value of rx-rtcp-app-req-sum.";
                }

                leaf rx-rtcp-app-req-sum-h {
                    type yang:counter32;
                    description "The value indicates the higher 32 bits of the value of rx-rtcp-app-req-sum.";
                }

                leaf rx-rtcp-fb-rep-sum {
                    type yang:counter64;
                    description
                        "The value indicates the total number of Real Time Transport Control Protocol
                         (RTCP) feedback (FB) requests processed for currently active sessions for
                         the interface.";
                }

                leaf rx-rtcp-fb-rep-sum-l {
                    type yang:counter32;
                    description "The value indicates the lower 32 bits of the value of rx-rtcp-fb-rep-sum.";
                }

                leaf rx-rtcp-fb-rep-sum-h {
                    type yang:counter32;
                    description "The value indicates the higher 32 bits of the value of rx-rtcp-fb-rep-sum.";
                }

                leaf rx-rtcp-fb-req-sum {
                    type yang:counter64;
                    description
                        "The value indicates the total number of Real Time Transport Control Protocol
                         (RTCP) feedback (FB) requests received for currently active sessions for
                         the interface.";
                }

                leaf rx-rtcp-fb-req-sum-l {
                    type yang:counter32;
                    description "The value indicates the lower 32 bits of the value of rx-rtcp-fb-req-sum.";
                }

                leaf rx-rtcp-fb-req-sum-h {
                    type yang:counter32;
                    description "The value indicates the higher 32 bits of the value of rx-rtcp-fb-req-sum.";
                }

                leaf rx-rudp-fb-rep-sum {
                    type yang:counter64;
                    description
                        "The value indicates the total number of Reliable User Datagram Protocol
                         (RUDP) feedback (FB) messages processed for currently active sessions
                         for the interface.";
                }

                leaf rx-rudp-fb-rep-sum-l {
                    type yang:counter32;
                    description "The value indicates the lower 32 bits of the value of rx-rudp-fb-rep-sum.";
                }

                leaf rx-rudp-fb-rep-sum-h {
                    type yang:counter32;
                    description "The value indicates the higher 32 bits of the value of rx-rudp-fb-rep-sum.";
                }

                leaf tx-fcc-pkts-sum {
                    type yang:counter64;
                    description
                        "The value indicates the total number of data packets sent against Fast Channel
                         Change (FCC) requests for the interface for currently active sessions.";
                }

                leaf tx-fcc-pkts-sum-l {
                    type yang:counter32;
                    description "The value indicates the lower 32 bits of the value of tx-fcc-pkts-sum.";
                }

                leaf tx-fcc-pkts-sum-h {
                    type yang:counter32;
                    description "The value indicates the higher 32 bits of the value of tx-fcc-pkts-sum.";
                }

                leaf tx-fcc-octets-sum {
                    type yang:counter64;
                    units "bytes";
                    description
                        "The value indicates the total number of data octets sent against Fast Channel
                         Change (FCC) requests for the interface for currently active sessions.";
                }

                leaf tx-fcc-octets-sum-l {
                    type yang:counter32;
                    units "bytes";
                    description "The value indicates the lower 32 bits of the value of tx-fcc-octets-sum.";
                }

                leaf tx-fcc-octets-sum-h {
                    type yang:counter32;
                    units "bytes";
                    description "The value indicates the higher 32 bits of the value of tx-fcc-octets-sum.";
                }

                leaf tx-ret-pkts-sum {
                    type yang:counter64;
                    description
                        "The value indicates the total number of data packets sent against
                         retransmission (Ret) requests for the interface for currently active
                         sessions.";
                }

                leaf tx-ret-pkts-sum-l {
                    type yang:counter32;
                    description "The value indicates the lower 32 bits of the value of tx-ret-pkts-sum.";
                }

                leaf tx-ret-pkts-sum-h {
                    type yang:counter32;
                    description "The value indicates the higher 32 bits of the value of tx-ret-pkts-sum.";
                }

                leaf tx-ret-octets-sum {
                    type yang:counter64;
                    description
                        "The value indicates the total number of data octets sent against retransmission
                         (Ret) requests for the interface for currently active sessions.";
                }

                leaf tx-ret-octets-sum-l {
                    type yang:counter32;
                    description "The value indicates the lower 32 bits of the value of tx-ret-octets-sum.";
                }

                leaf tx-ret-octets-sum-h {
                    type yang:counter32;
                    description "The value indicates the higher 32 bits of the value of tx-ret-octets-sum.";
                }

                leaf tx-rudp-pkts-sum {
                    type yang:counter64;
                    description
                        "The value indicates the total number of data packets sent against Reliable
                         User Datagram Protocol (RUDP) retransmission requests for the interface for
                         currently active sessions.";
                }

                leaf tx-rudp-pkts-sum-l {
                    type yang:counter32;
                    description "The value indicates the lower 32 bits of the value of tx-rudp-pkts-sum.";
                }

                leaf tx-rudp-pkts-sum-h {
                    type yang:counter32;
                    description "The value indicates the higher 32 bits of the value of tx-rudp-pkts-sum.";
                }

                leaf tx-rudp-byte-sum {
                    type yang:counter64;
                    units "bytes";
                    description
                        "The value indicates the total number of data octets sent against Reliable User
                         Datagram Protocol (RUDP) retransmission requests for the interface for currently
                         active sessions.";
                }

                leaf tx-rudp-byte-sum-l {
                    type yang:counter32;
                    units "bytes";
                    description "The value indicates the lower 32 bits of the value of tx-rudp-byte-sum.";
                }

                leaf tx-rudp-byte-sum-h {
                    type yang:counter32;
                    units "bytes";
                    description "The value indicates the higher 32 bits of the value of tx-rudp-byte-sum.";
                }

            } // list statistics

            list session {
                key "source-address source-port";
                description "Enter the session list instance";

                leaf source-address {
                    type types-sros:ipv4-unicast-address;
                    description
                        "The value indicates the address of the Fast Channel Change (FCC) server or
                         Retransmission (RT) server.";
                }

                leaf source-port {
                    type inet:port-number;
                    description
                        "The value indicates the server port on which the Fast Channel Change or Retransmission
                         services are being provided.";
                }

                leaf ssrc-id {
                    type yang:counter32;
                    description "The value indicates the synchronization source (SSRC) identifier of the server.";
                }

                leaf up-time {
                    type uint32;
                    units "seconds";
                    description "The value indicates how long it has been since the session was established.";
                }

                leaf expire-time {
                    type uint32;
                    units "seconds";
                    description
                        "The value indicates the expiry time of this session. The value of this object
                         ticks backwards and indicates the remaining time that the row may exist before
                         it is aged out.";
                }

                leaf c-name {
                    type types-sros:named-item;
                    description "The value indicates the canonical name of the server.";
                }

                leaf dest-addr {
                    type types-sros:ipv4-address;
                    description "The value indicates the address of the destionation in this session.";
                }

                leaf rx-fcc-requests {
                    type yang:counter32;
                    description
                        "The value indicates the total number of Fast Channel Change (FCC) requests
                         received by the server.";
                }

                leaf tx-fcc-replies {
                    type yang:counter32;
                    description
                        "The value indicates the total number of Fast Channel Change (FCC) replies sent
                         by the server.";
                }

                leaf tx-fcc-packets {
                    type yang:counter32;
                    description
                        "The value indicates the total number of Fast Channel Change (FCC) packets sent
                         by the server.";
                }

                leaf tx-fcc-octets {
                    type yang:counter32;
                    description
                        "The value indicates the total number of Fast Channel Change (FCC) octets sent
                         by the server.";
                }

                leaf tx-fcc-failed-packets {
                    type yang:counter32;
                    description
                        "The value indicates the total number of failures during the transmission of
                         Fast Channel Change (FCC) packets. Failure happens when the packet to be sent
                         is not stored in the video cache.";
                }

                leaf rx-rt-requests {
                    type yang:counter32;
                    description
                        "The value indicates the total number of Retransmission (RT) requests received
                         by the server.";
                }

                leaf tx-rt-replies {
                    type yang:counter32;
                    description
                        "The value indicates the total number of Retransmission (RT) replies sent by
                         the server.";
                }

                leaf tx-rt-packets {
                    type yang:counter32;
                    description
                        "The value indicates the total number of Retransmission (RT) packets sent by
                         the server.";
                }

                leaf tx-rt-octets {
                    type yang:counter32;
                    description
                        "The value indicates the total number of Retransmission (RT) octets sent by
                         the server.";
                }

                leaf tx-rt-failed-packets {
                    type yang:counter32;
                    description
                        "The value indicates the total number of failures during the transmission of
                         Retransmission (RT) packets. Failure happens when the packet to be sent is
                         not stored in the video cache.";
                }

                leaf requested-rtp-pkts {
                    type yang:counter32;
                    description
                        "The value indicates the number of Real-time Transport Protocol (RTP) packets
                         requested in the Real-time Transport Control Protocol (RTCP) feedback (FB)
                         messages received in this session.";
                }

                leaf rt-req-quenched {
                    type yang:counter32;
                    description
                        "The value indicates the number of unicast retransmission requests quenched
                         with multicast retransmission in this session.";
                }

                leaf rt-mcast-req-created {
                    type yang:counter32;
                    description
                        "The value indicates the number of multicast retransmission requests created
                         in response to unicast retransmission requests in this session.";
                }

                leaf pkts-lost-in-seq-10 {
                    type yang:counter32;
                    description
                        "The value indicates the total number of packets within sequences of 2 to 10
                         consecutive lost packets in this session.";
                }

                leaf pkts-lost-in-seq-20 {
                    type yang:counter32;
                    description
                        "The value indicates the total number of packets within sequences of 11 to 20
                         consecutive lost packets in this session.";
                }

                leaf pkts-lost-in-seq-30 {
                    type yang:counter32;
                    description
                        "The value indicates the total number of packets within sequences of 21 to 30
                         consecutive lost packets in this session.";
                }

                leaf pkts-lost-in-seq-40 {
                    type yang:counter32;
                    description
                        "The value indicates the total number of packets within sequences of 31 to 40
                         consecutive lost packets in this session.";
                }

                leaf pkts-lost-in-seq-more {
                    type yang:counter32;
                    description
                        "The value indicates the total number of packets within sequences of 41 or more
                         consecutive lost packets in this session.";
                }

            } // list session

        } // list video-interface

    } // grouping state-svc-vprn-vdo-if-video-interface

}
