module nokia-bof-conf {

    yang-version "1.1";

    namespace "urn:nokia.com:sros:ns:yang:sr:bof-conf";

    prefix "bof-conf";

    import nokia-sros-yang-extensions     { prefix "sros-ext"; }
    import nokia-types-port               { prefix "types-port"; }
    import nokia-types-router             { prefix "types-router"; }
    import nokia-types-sros               { prefix "types-sros"; }

    sros-ext:sros-major-release "rel22";

    organization "Nokia";

    contact
        "Nokia SR OS Support
         Web: <http://www.nokia.com>";

    description
        "Nokia YANG Data model to show state data on SR OS based routers.

         Copyright 2016 Nokia. All rights reserved. Reproduction of this document
         is authorized on the condition that the foregoing copyright notice is included.

         This nokia-bof-conf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2024-08-21";

    container bof {
        description "Enter the bof context";

        container auto-boot {
            presence "Enable the auto-boot context";
            sros-ext:bof-parameter-effect "boot";
            description "Enable the auto-boot context";

            leaf port-mtu {
                type uint32 {
                    range "512..9800";
                }
                units "bytes";
                sros-ext:bof-parameter-effect "boot";
                description "Port MTU setting";
            }

            leaf timeout {
                type uint32 {
                    range "30..1440";
                }
                units "minutes";
                sros-ext:bof-parameter-effect "boot";
                description "ZTP timeout";
            }

            choice auto-boot-mode {
                default "dhcp";
                case dhcp {

                    container dhcp {
                        presence "Enable the dhcp context";
                        sros-ext:bof-parameter-effect "boot";
                        description "Enable the dhcp context";

                        leaf client-id {
                            type union {
                                type enumeration {
                                    enum "use-chassis-mac-address"      { value 0; }
                                }
                                type types-sros:hex-string {
                                    length "3..118";
                                }
                                type string {
                                    length "1..58";
                                }
                            }
                            sros-ext:bof-parameter-effect "boot";
                            description "DHCP client ID";
                        }

                        leaf management-port {
                            type boolean;
                            sros-ext:bof-parameter-effect "boot";
                            default "true";
                            description "Use auto boot on the management port";
                        }

                        leaf ipv4 {
                            type boolean;
                            sros-ext:bof-parameter-effect "boot";
                            default "true";
                            description "Use auto boot with IPv4";
                        }

                        leaf ipv6 {
                            type boolean;
                            sros-ext:bof-parameter-effect "boot";
                            default "true";
                            description "Use auto boot with IPv6";
                        }

                        leaf include-user-class {
                            type boolean;
                            sros-ext:bof-parameter-effect "boot";
                            default "true";
                            description "Include user class in auto boot provisioning";
                        }

                        container inband {
                            presence "Enable the inband context";
                            sros-ext:bof-parameter-effect "boot";
                            description "Enable the inband context";

                            choice inband-options {
                                default "discovery-mode";
                                case specific-vlan {

                                    leaf vlan {
                                        type types-sros:vlan-id;
                                        sros-ext:bof-parameter-effect "boot";
                                        description "In-band VLAN ID";
                                    }

                                }
                                case discovery-mode {

                                    leaf vlan-discovery {
                                        type boolean;
                                        sros-ext:bof-parameter-effect "boot";
                                        default "true";
                                        description "Use VLAN discovery";
                                    }

                                }
                                case null-encapsulation {

                                    leaf null-encapsulation {
                                        type boolean;
                                        sros-ext:bof-parameter-effect "boot";
                                        default "true";
                                        description "Use null encapsulation";
                                    }

                                }
                                case disabled {

                                    leaf disabled {
                                        type boolean;
                                        sros-ext:bof-parameter-effect "boot";
                                        default "true";
                                        description "Do not use in-band ports";
                                    }

                                }
                            }
                        } // container inband

                    } // container dhcp

                }
                case ospf {

                    container ospf {
                        presence "Enable the ospf context";
                        sros-ext:bof-parameter-effect "boot";
                        description "Enable the ospf context";

                        leaf neid {
                            type types-sros:hex-string {
                                length "3";
                            }
                            sros-ext:bof-parameter-effect "boot";
                            description "Network element ID";
                        }

                        leaf neip-ipv4 {
                            type types-sros:ipv4-unicast-address;
                            sros-ext:bof-parameter-effect "boot";
                            description "Network element IPv4 address";
                        }

                        leaf neip-ipv6 {
                            type types-sros:ipv6-address;
                            sros-ext:bof-parameter-effect "boot";
                            description "Network element IPv6 address";
                        }

                        leaf mtu {
                            type types-router:ip-mtu-ext;
                            units "bytes";
                            sros-ext:bof-parameter-effect "boot";
                            default "1500";
                            description "OSPF MTU";
                        }

                        leaf vendor-id {
                            type uint32 {
                                range "1..254";
                            }
                            sros-ext:bof-parameter-effect "boot";
                            default "140";
                            description "Vendor ID";
                        }

                    } // container ospf

                }
            }
        } // container auto-boot


        container auto-configure {
            description "Enter the auto-configure context";

            container ipv4 {
                description "Enter the ipv4 context";

                container dhcp {
                    presence "Enable the dhcp context";
                    sros-ext:bof-parameter-effect "boot";
                    description "Enable the dhcp context";

                    leaf client-id {
                        type union {
                            type types-sros:hex-string {
                                length "3..256";
                            }
                            type string {
                                length "1..127";
                            }
                        }
                        sros-ext:immutable;
                        sros-ext:bof-parameter-effect "boot";
                        description "DHCP client ID";
                    }

                    leaf include-user-class {
                        type boolean;
                        sros-ext:immutable;
                        sros-ext:bof-parameter-effect "boot";
                        default "false";
                        description "Include user class information";
                    }

                    leaf timeout {
                        type uint32 {
                            range "1..65535";
                        }
                        sros-ext:immutable;
                        sros-ext:bof-parameter-effect "boot";
                        default "30";
                        description "DHCP timeout";
                    }

                } // container dhcp

            } // container ipv4

            container ipv6 {
                description "Enter the ipv6 context";

                container dhcp {
                    presence "Enable the dhcp context";
                    sros-ext:bof-parameter-effect "boot";
                    description "Enable the dhcp context";

                    leaf client-type {
                        type enumeration {
                            enum "duid-enterprise"              { value 2; }
                            enum "duid-link-local"              { value 3; }
                        }
                        sros-ext:immutable;
                        sros-ext:bof-parameter-effect "boot";
                        description "DHCP client type";
                    }

                    leaf client-id {
                        type union {
                            type types-sros:hex-string {
                                length "3..250";
                            }
                            type string {
                                length "1..124";
                            }
                        }
                        sros-ext:immutable;
                        sros-ext:bof-parameter-effect "boot";
                        description "DHCP client ID";
                    }

                    leaf include-user-class {
                        type boolean;
                        sros-ext:immutable;
                        sros-ext:bof-parameter-effect "boot";
                        default "false";
                        description "Include user class information";
                    }

                    leaf timeout {
                        type uint32 {
                            range "1..65535";
                        }
                        sros-ext:immutable;
                        sros-ext:bof-parameter-effect "boot";
                        default "30";
                        description "DHCP timeout";
                    }

                } // container dhcp

            } // container ipv6

        } // container auto-configure


        container configuration {
            description "Enter the configuration context";

            leaf primary-location {
                type types-sros:cflash-and-url;
                sros-ext:bof-parameter-effect "commit";
                description "Primary configuration location";
            }

            leaf secondary-location {
                type types-sros:cflash-and-url;
                sros-ext:bof-parameter-effect "commit";
                description "Secondary configuration location";
            }

            leaf tertiary-location {
                type types-sros:cflash-and-url;
                sros-ext:bof-parameter-effect "commit";
                description "Tertiary configuration location";
            }

            leaf encrypt {
                type boolean;
                sros-ext:bof-parameter-effect "commit";
                default "false";
                description "Enable encryption of BOF configuration files";
            }

            leaf encryption-key {
                type types-sros:encrypted-leaf {
                    length "1..71";
                }
                sros-ext:bof-parameter-effect "commit";
                description "Secret key for encryption of configuration files";
            }

            leaf password {
                type types-sros:encrypted-leaf {
                    length "1..71";
                }
                sros-ext:bof-parameter-effect "boot";
                description "Password for boot-time modification of boot options";
            }

        } // container configuration


        container console {
            description "Enter the console context";

            leaf speed {
                type uint32 {
                    range "9600|19200|38400|57600|115200";
                }
                units "bps";
                sros-ext:bof-parameter-effect "commit";
                default "19200";
                description "Console port speed";
            }

            leaf wait-time {
                type uint32 {
                    range "1..10";
                }
                units "seconds";
                sros-ext:bof-parameter-effect "boot";
                default "3";
                description "Wait time for interrupt to change boot parameters";
            }

        } // container console



        container dns {
            description "Enter the dns context";

            leaf domain {
                type string {
                    length "1..178";
                }
                sros-ext:bof-parameter-effect "commit";
                description "System DNS domain name for DNS address resolution";
            }

            leaf primary-server {
                type types-sros:ip-address;
                sros-ext:bof-parameter-effect "commit";
                description "Primary DNS server";
            }

            leaf secondary-server {
                type types-sros:ip-address;
                sros-ext:bof-parameter-effect "commit";
                description "Secondary DNS server";
            }

            leaf tertiary-server {
                type types-sros:ip-address;
                sros-ext:bof-parameter-effect "commit";
                description "Tertiary DNS server";
            }

        } // container dns


        container image {
            description "Enter the image context";

            leaf primary-location {
                type types-sros:cflash-and-url;
                sros-ext:bof-parameter-effect "boot";
                description "Primary image location";
            }

            leaf secondary-location {
                type types-sros:cflash-and-url;
                sros-ext:bof-parameter-effect "boot";
                description "Secondary image location";
            }

            leaf tertiary-location {
                type types-sros:cflash-and-url;
                sros-ext:bof-parameter-effect "boot";
                description "Tertiary image location";
            }

        } // container image


        container li {
            description "Enter the li context";

            leaf local-save {
                type boolean;
                sros-ext:bof-parameter-effect "boot";
                default "false";
                description "Save the LI configuration locally";
            }

            leaf separate {
                type boolean;
                sros-ext:bof-parameter-effect "boot";
                default "false";
                description "Separate access to the LI information";
            }

        } // container li


        container license {
            description "Enter the license context";

            leaf primary-location {
                type types-sros:cflash-and-url;
                sros-ext:bof-parameter-effect "commit";
                description "Primary license file location";
            }

        } // container license


        list port {
            key "router-name";
            max-elements 1;
            sros-ext:bof-parameter-effect "commit";
            description "Enter the port list instance";

            leaf router-name {
                type types-sros:named-item-64 {
                    pattern "management" {
                        error-message "Only management is allowed for this router context";
                    }
                }
                description "Administrative router name";
            }

            leaf autonegotiate {
                type enumeration {
                    enum "false"                        { value 0; }
                    enum "true"                         { value 1; }
                }
                sros-ext:bof-parameter-effect "commit";
                default "true";
                description "Auto-negotiate speed and duplex type on Ethernet port";
            }

            leaf duplex {
                type types-port:duplex-mode;
                sros-ext:bof-parameter-effect "commit";
                default "full";
                description "Duplex type for the Ethernet port";
            }

            leaf speed {
                type uint32 {
                    range "10|100|1000";
                }
                units "megabps";
                sros-ext:bof-parameter-effect "commit";
                default "100";
                description "Speed of the Ethernet port";
            }

        } // list port


        list router {
            key "router-name";
            max-elements 1;
            sros-ext:bof-parameter-effect "commit";
            description "Enter the router list instance";

            leaf router-name {
                type types-sros:named-item-64 {
                    pattern "management" {
                        error-message "Only management is allowed for this router context";
                    }
                }
                description "Administrative router name";
            }

            list interface {
                key "interface-name";
                max-elements 1;
                sros-ext:bof-parameter-effect "commit";
                description "Enter the interface list instance";

                leaf interface-name {
                    type types-sros:interface-name {
                        pattern "management" {
                            error-message "Only management is allowed for this router context";
                        }
                    }
                    description "Router interface name";
                }

                leaf ip-mtu {
                    type types-router:ip-mtu-ext;
                    units "bytes";
                    sros-ext:bof-parameter-effect "commit";
                    description "Interface IP MTU";
                }

                list cpm {
                    key "cpm-type";
                    sros-ext:bof-parameter-effect "commit";
                    description "Enter the cpm list instance";

                    leaf cpm-type {
                        type enumeration {
                            enum "active"                       { value 0; }
                            enum "standby"                      { value 1; }
                            enum "a"                            { value 2; }
                            enum "b"                            { value 3; }
                            enum "c"                            { value 4; }
                            enum "d"                            { value 5; }
                        }
                        description "CPM type";
                    }

                    container ipv4 {
                        presence "Enable the ipv4 context";
                        sros-ext:bof-parameter-effect "commit";
                        description "Enable the ipv4 context";

                        leaf ip-address {
                            type types-sros:ipv4-unicast-address;
                            sros-ext:bof-parameter-effect "commit";
                            mandatory true;
                            description "IPv4 address assigned to the interface";
                        }

                        leaf prefix-length {
                            type uint32 {
                                range "0..32";
                            }
                            sros-ext:bof-parameter-effect "commit";
                            mandatory true;
                            description "IPv4 address prefix length";
                        }

                    } // container ipv4

                    container ipv6 {
                        presence "Enable the ipv6 context";
                        sros-ext:bof-parameter-effect "commit";
                        description "Enable the ipv6 context";

                        leaf ipv6-address {
                            type types-sros:ipv6-address;
                            sros-ext:bof-parameter-effect "commit";
                            description "IPv6 address assigned to the interface";
                        }

                        leaf prefix-length {
                            type uint32 {
                                range "0..128";
                            }
                            sros-ext:bof-parameter-effect "commit";
                            mandatory true;
                            description "IPv6 address prefix length";
                        }

                    } // container ipv6

                } // list cpm

            } // list interface

            container static-routes {
                description "Enter the static-routes context";

                list route {
                    key "ip-prefix";
                    sros-ext:bof-parameter-effect "commit";
                    description "Enter the route list instance";

                    leaf ip-prefix {
                        type types-sros:ip-prefix;
                        description "IP prefix for the static route";
                    }

                    leaf next-hop {
                        type types-sros:ip-address;
                        sros-ext:immutable;
                        sros-ext:bof-parameter-effect "commit";
                        mandatory true;
                        description "Next-hop IP address";
                    }

                } // list route

            } // container static-routes

        } // list router


        container system {
            description "Enter the system context";

            leaf base-mac-address {
                type types-sros:mac-unicast-address;
                sros-ext:bof-parameter-effect "boot";
                description "Base system MAC address";
            }

            leaf fips-140-2 {
                type boolean;
                sros-ext:bof-parameter-effect "boot";
                default "false";
                description "Operate in FIPS 140-2 mode";
            }

            leaf persistent-indices {
                type boolean;
                sros-ext:bof-parameter-effect "boot";
                default "false";
                description "Classic and mixed management mode persistent indices";
            }

            leaf profile {
                type enumeration {
                    enum "profile-a"                    { value 1; }
                    enum "profile-b"                    { value 2; }
                }
                sros-ext:bof-parameter-effect "boot";
                description "System capabilities profile";
            }

        } // container system


    } // container bof

}
