submodule nokia-conf-port-eth-efm-oam {

    yang-version "1.1";

    belongs-to nokia-conf { prefix "conf"; }

    import nokia-sros-yang-extensions     { prefix "sros-ext"; }
    import nokia-types-port               { prefix "types-port"; }
    import nokia-types-sros               { prefix "types-sros"; }

    include nokia-conf-groups;


    sros-ext:sros-major-release "rel22";

    organization "Nokia";

    contact
        "Nokia SR OS Support
         Web: <http://www.nokia.com>";

    description
        "Nokia YANG Data model to configure ethernet ports supporting efm-oam on SR OS based routers.

         Copyright 2016 Nokia. All rights reserved. Reproduction of this document
         is authorized on the condition that the foregoing copyright notice is included.

         This nokia-conf-port-eth-efm-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-07-21";

    grouping conf-port-eth-efm-oam {
        container efm-oam {
            description "Enter the efm-oam context";

            leaf accept-remote-loopback {
                type boolean;
                default "false";
                description "Enable reactions to loopback control OAMPDUs from peers";
            }

            leaf admin-state {
                type types-sros:admin-state;
                default "disable";
                description "Administrative state of the EFM OAM operation";
            }

            leaf dying-gasp-tx-on-reset {
                type boolean;
                default "true";
                description "Enable generation of the Information OAMPDU off-cycle";
            }

            leaf grace-tx {
                type boolean;
                description "Enable the sending of Grace TLV for EFM-OAM";
            }

            leaf grace-vendor-oui {
                type string;
                default "00:16:4D";
                description "Peer vendor OUI to support grace function";
            }

            leaf hold-time {
                type uint32 {
                    range "1..50";
                }
                units "seconds";
                description "Wait time before protocol returns to operational state";
            }

            leaf ignore-efm-state {
                type boolean;
                default "false";
                description "Suppress port state changes for EFM-OAM faults";
            }

            leaf mode {
                type enumeration {
                    enum "passive"                      { value 1; }
                    enum "active"                       { value 2; }
                }
                default "active";
                description "Mode of OAM operation for the Ethernet port";
            }

            leaf transmit-interval {
                type uint32 {
                    range "1..600";
                }
                units "deciseconds";
                default "10";
                description "Transmit interval of OAMPDUs";
            }

            leaf multiplier {
                type uint32 {
                    range "2..5";
                }
                default "5";
                description "Multiplier for the transmit interval of OAMPDUs";
            }

            leaf trigger-fault {
                type enumeration {
                    enum "dying-gasp"                   { value 2; }
                    enum "critical-event"               { value 3; }
                }
                description "Flag setting in the information OAMPDU";
            }

            leaf tunneling {
                type boolean;
                default "false";
                description "Enable EFM-OAM PDU tunneling";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container discovery {
                description "Enter the discovery context";

                container advertise-capabilities {
                    description "Enter the advertise-capabilities context";

                    leaf link-monitoring {
                        type boolean;
                        default "true";
                        description "Advertise link monitoring capabilities to peer";
                    }

                } // container advertise-capabilities

            } // container discovery

            container link-monitoring {
                description "Enter the link-monitoring context";

                leaf admin-state {
                    type types-sros:admin-state;
                    default "disable";
                    description "Administrative state of link monitoring on the port";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container errored-frame {
                    description "Enter the errored-frame context";

                    leaf admin-state {
                        type types-sros:admin-state;
                        default "disable";
                        description "Administrative state of link monitoring on the port";
                    }

                    leaf event-notification {
                        type boolean;
                        default "true";
                        description "Transmit Event Notification OAMPDU with link event TLV";
                    }

                    leaf sd-threshold {
                        type uint32 {
                            range "1..1000000";
                        }
                        description "SD threshold";
                    }

                    leaf sf-threshold {
                        type uint32 {
                            range "1..1000000";
                        }
                        default "1";
                        description "SF threshold";
                    }

                    leaf window {
                        type uint32 {
                            range "10..600";
                        }
                        units "deciseconds";
                        default "10";
                        description "Window size";
                    }

                } // container errored-frame

                container errored-frame-period {
                    description "Enter the errored-frame-period context";

                    leaf admin-state {
                        type types-sros:admin-state;
                        default "disable";
                        description "Administrative state of link monitoring on the port";
                    }

                    leaf event-notification {
                        type boolean;
                        default "true";
                        description "Transmit Event Notification OAMPDU with link event TLV";
                    }

                    leaf sd-threshold {
                        type uint32 {
                            range "1..1000000";
                        }
                        description "SD threshold";
                    }

                    leaf sf-threshold {
                        type uint32 {
                            range "1..1000000";
                        }
                        default "1";
                        description "SF threshold";
                    }

                    leaf window {
                        type uint32 {
                            range "1..4294967295";
                        }
                        units "packets";
                        default "1488095";
                        description "Window size";
                    }

                } // container errored-frame-period

                container errored-frame-seconds {
                    description "Enter the errored-frame-seconds context";

                    leaf admin-state {
                        type types-sros:admin-state;
                        default "disable";
                        description "Administrative state of link monitoring on the port";
                    }

                    leaf event-notification {
                        type boolean;
                        default "true";
                        description "Transmit Event Notification OAMPDU with link event TLV";
                    }

                    leaf sd-threshold {
                        type uint32 {
                            range "1..900";
                        }
                        description "SD threshold";
                    }

                    leaf sf-threshold {
                        type uint32 {
                            range "1..900";
                        }
                        default "1";
                        description "SF threshold";
                    }

                    leaf window {
                        type uint32 {
                            range "100..9000";
                        }
                        units "deciseconds";
                        default "600";
                        description "Window size";
                    }

                } // container errored-frame-seconds

                container errored-symbols {
                    description "Enter the errored-symbols context";

                    leaf admin-state {
                        type types-sros:admin-state;
                        default "disable";
                        description "Administrative state of link monitoring on the port";
                    }

                    leaf event-notification {
                        type boolean;
                        default "true";
                        description "Transmit Event Notification OAMPDU with link event TLV";
                    }

                    leaf sd-threshold {
                        type uint32 {
                            range "1..1000000";
                        }
                        description "SD threshold";
                    }

                    leaf sf-threshold {
                        type uint32 {
                            range "1..1000000";
                        }
                        default "1";
                        description "SF threshold";
                    }

                    leaf window {
                        type uint32 {
                            range "10..600";
                        }
                        units "deciseconds";
                        default "10";
                        description "Window size";
                    }

                } // container errored-symbols

                container local-sf-action {
                    description "Enter the local-sf-action context";

                    leaf event-notification-burst {
                        type uint32 {
                            range "1..5";
                        }
                        units "packets";
                        default "1";
                        description "Number of OAMPDUs to send when SF threshold is reached";
                    }

                    leaf local-port-action {
                        type types-port:efm-oam-local-port-action;
                        default "port-out-of-service";
                        description "Local port action when SF threshold is reached";
                    }

                    container info-notification {
                        description "Enter the info-notification context";

                        leaf critical-event {
                            type boolean;
                            default "false";
                            description "Set critical event flag when SF threshold is reached";
                        }

                        leaf dying-gasp {
                            type boolean;
                            default "false";
                            description "Set dying gasp flag when SF threshold is reached";
                        }

                    } // container info-notification

                } // container local-sf-action

            } // container link-monitoring

            container peer-rdi-rx {
                description "Enter the peer-rdi-rx context";

                leaf critical-event {
                    type types-port:efm-oam-local-port-action;
                    default "port-out-of-service";
                    description "Action taken upon receipt of critical event flag";
                }

                leaf dying-gasp {
                    type types-port:efm-oam-local-port-action;
                    default "port-out-of-service";
                    description "Action taken upon receipt of dying gasp flag";
                }

                leaf event-notification {
                    type types-port:efm-oam-local-port-action;
                    default "log-only";
                    description "Action taken upon receipt of event TLVs";
                }

                leaf link-fault {
                    type types-port:efm-oam-local-port-action;
                    default "port-out-of-service";
                    description "Action taken upon receipt of link fault flag";
                }

            } // container peer-rdi-rx

        } // container efm-oam

    } // grouping conf-port-eth-efm-oam

}
