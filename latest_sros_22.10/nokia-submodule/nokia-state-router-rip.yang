submodule nokia-state-router-rip {

    yang-version "1.1";

    belongs-to nokia-state { prefix "state"; }

    import ietf-yang-types                { prefix "yang"; }
    import nokia-sros-yang-extensions     { prefix "sros-ext"; }
    import nokia-types-rip                { prefix "types-rip"; }
    import nokia-types-sros               { prefix "types-sros"; }


    sros-ext:sros-major-release "rel22";

    organization "Nokia";

    contact
        "Nokia SR OS Support
         Web: <http://www.nokia.com>";

    description
        "Nokia YANG Data model with operational state for router rip protocol attributes on SR OS based routers.

         Copyright 2016 Nokia. All rights reserved. Reproduction of this document
         is authorized on the condition that the foregoing copyright notice is included.

         This nokia-state-router-rip YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping state-router-rip {
        container rip {
            description "Enter the rip context";

            leaf oper-state {
                type types-sros:oper-state;
                description "The operational state of this RIP instance.";
            }

            list peer {
                key "interface-name address";
                description "Enter the peer list instance";

                leaf interface-name {
                    type types-sros:interface-name;
                    description "The interface on which this peer was discovered.";
                }

                leaf address {
                    type types-sros:ipv4-address;
                    description "IP Address that the peer is using as its source address.";
                }

                leaf version {
                    type types-rip:peer-version;
                    description "The RIP version in the header of the last packet received from this peer.";
                }

                leaf last-update {
                    type yang:date-and-time;
                    description "Time the most recent RIP update was received from this peer.";
                }

            } // list peer

            list advertised-routes {
                key "destination interface-name interface-address";
                description "Enter the advertised-routes list instance";

                leaf destination {
                    type types-sros:ipv4-address-and-mask;
                    description
                        "Destination IP address and mask of the advertised route.
                         If the mask is zero, then no subnet has been included for this entry.";
                }

                leaf interface-name {
                    type types-sros:interface-name;
                    description "The interface on which the route is advertised.";
                }

                leaf interface-address {
                    type types-sros:ipv4-address;
                    description "The IP address of the subnet to which the route is advertised.";
                }

                leaf next-hop {
                    type types-sros:ipv4-address;
                    description "The IP address which is advertised in the Next Hop field of the RIPv2 updates.";
                }

                leaf metric {
                    type types-rip:metric;
                    description "The metric with which the route is advertised.";
                }

                leaf tag {
                    type uint16;
                    description "The value which is advertised in the Route Tag field for the route.";
                }

                leaf ttl {
                    type uint32;
                    units "seconds";
                    description
                        "The number of seconds till the flush timer expires.
                         The flush timer is active for only those routes which are no longer valid.
                         Such routes will be advertised with a metric of 16 till the flush timer expires
                         after which they will be removed from the database.";
                }

            } // list advertised-routes

            list database {
                key "destination interface-name peer";
                description "Enter the database list instance";

                leaf destination {
                    type types-sros:ipv4-address-and-mask;
                    description
                        "Destination IP address and mask of the RIP route.
                         If the mask is zero, then no subnet has been included for this entry.";
                }

                leaf interface-name {
                    type types-sros:interface-name;
                    description "The interface on which this route was received.";
                }

                leaf peer {
                    type types-sros:ipv4-address;
                    description "The IP address of the peer from whom this route was received.";
                }

                leaf next-hop {
                    type types-sros:ipv4-address;
                    description
                        "The IP address in the Next Hop field of the RIPv2 update received for this route.
                         The Next Hop field is the immediate next hop IP address to which packets to the destination
                         specified by this route entry should be forwarded.
                         Specifying a value of 0.0.0.0 in this field indicates that routing should be via the
                         originator of the RIP advertisement.";
                }

                leaf metric {
                    type types-rip:metric;
                    description "The distance to the destination as advertised by the peer that sent this route.";
                }

                leaf tag {
                    type uint16;
                    description "The value in the Route Tag field of the update received for this route.";
                }

                leaf ttl {
                    type uint32;
                    units "seconds";
                    description "The number of seconds till the timeout timer expires.";
                }

                leaf fc {
                    type types-sros:fc-name;
                    description "The forwarding class associated with the RIP route.";
                }

                leaf priority {
                    type types-sros:priority;
                    description "Specifies the priority to be assigned to the RIP route.";
                }

                leaf active {
                    type boolean;
                    description
                        "Indicates whether or not the route entry is active in the system.
                         It will be true if the route entry has been added to the Route Table Manager(RTM).";
                }

            } // list database

            list group {
                key "group-name";
                description "Enter the group list instance";

                leaf group-name {
                    type types-sros:named-item;
                    description "RIP group name";
                }

                leaf oper-state {
                    type types-sros:oper-state;
                    description "The operational state of this RIP group.";
                }

                list neighbor {
                    key "interface-name";
                    description "Enter the neighbor list instance";

                    leaf interface-name {
                        type types-sros:interface-name;
                        description "Neighbor added through the interface to the RIP group";
                    }

                    leaf oper-state {
                        type types-sros:oper-state;
                        description "The operational state of this RIP neighbor.";
                    }

                    container statistics {
                        description "Enter the statistics context";

                        container updates-sent {
                            description "Enter the updates-sent context";

                            leaf total {
                                type yang:counter32;
                                description
                                    "The number of all RIP updates actually sent on this interface.
                                     This explicitly does include full updates sent containing new information.";
                            }

                            leaf last-5min {
                                type yang:counter32;
                                description
                                    "The number of all RIP updates actually sent on this interface in the last 5 minutes.
                                     This explicitly does include full updates sent containing new information.";
                            }

                            leaf last-1min {
                                type yang:counter32;
                                description
                                    "The number of all RIP updates actually sent on this interface in the last minute.
                                     This explicitly does include full updates sent containing new information.";
                            }

                        } // container updates-sent

                        container triggered-updates {
                            description "Enter the triggered-updates context";

                            leaf total {
                                type yang:counter32;
                                description
                                    "The number of triggered RIP updates actually sent on this interface.
                                     This explicitly does include full updates sent containing new information.";
                            }

                            leaf last-5min {
                                type yang:counter32;
                                description
                                    "The number of triggered RIP updates actually sent on this interface in the last 5 minutes.
                                     This explicitly does include full updates sent containing new information.";
                            }

                            leaf last-1min {
                                type yang:counter32;
                                description
                                    "The number of triggered RIP updates actually sent on this interface in the last minute.
                                     This explicitly does include full updates sent containing new information.";
                            }

                        } // container triggered-updates

                        container bad-packets-received {
                            description "Enter the bad-packets-received context";

                            leaf total {
                                type yang:counter32;
                                description "The number of RIP updates received on this interface that were discarded as invalid.";
                            }

                            leaf last-5min {
                                type yang:counter32;
                                description
                                    "The number of RIP response packets discarded (for any reason e.g. a version 0 packet,
                                     or an unknown command type) in the last 5 minutes.";
                            }

                            leaf last-1min {
                                type yang:counter32;
                                description
                                    "The number of RIP response packets discarded (for any reason e.g. a version 0 packet,
                                     or an unknown command type) in the last minute.";
                            }

                        } // container bad-packets-received

                        container ripv1-updates-received {
                            description "Enter the ripv1-updates-received context";

                            leaf total {
                                type yang:counter32;
                                description "The number of RIPv1 response packets received.";
                            }

                            leaf last-5min {
                                type yang:counter32;
                                description "The number of RIPv1 response packets received in the last 5 minutes.";
                            }

                            leaf last-1min {
                                type yang:counter32;
                                description "The number of RIPv1 response packets received in the last minute.";
                            }

                        } // container ripv1-updates-received

                        container ripv1-updates-ignored {
                            description "Enter the ripv1-updates-ignored context";

                            leaf total {
                                type yang:counter32;
                                description "The number of RIPv1 response packets received which were subsequently discarded for any reason.";
                            }

                            leaf last-5min {
                                type yang:counter32;
                                description "The number of RIPv1 response packets received in the last 5 minutes which were subsequently discarded for any reason.";
                            }

                            leaf last-1min {
                                type yang:counter32;
                                description "The number of RIPv1 response packets received in the last minute which were subsequently discarded for any reason.";
                            }

                        } // container ripv1-updates-ignored

                        container ripv1-bad-routes {
                            description "Enter the ripv1-bad-routes context";

                            leaf total {
                                type yang:counter32;
                                description
                                    "The number of routes, in valid RIPv1 packets, which were ignored for any reason
                                     (e.g. unknown address family, or invalid metric).";
                            }

                            leaf last-5min {
                                type yang:counter32;
                                description
                                    "The number of routes, in valid RIPv1 packets, which were ignored for any reason
                                     (e.g. unknown address family, or invalid metric) in the last 5 minutes.";
                            }

                            leaf last-1min {
                                type yang:counter32;
                                description
                                    "The number of routes, in valid RIPv1 packets, which were ignored for any reason
                                     (e.g. unknown address family, or invalid metric) in the last minute.";
                            }

                        } // container ripv1-bad-routes

                        container ripv1-requests-received {
                            description "Enter the ripv1-requests-received context";

                            leaf total {
                                type yang:counter32;
                                description "The number RIPv1 request packets received.";
                            }

                            leaf last-5min {
                                type yang:counter32;
                                description "The number RIPv1 request packets received in the last 5 minutes.";
                            }

                            leaf last-1min {
                                type yang:counter32;
                                description "The number RIPv1 request packets received in the last minute.";
                            }

                        } // container ripv1-requests-received

                        container ripv1-requests-ignored {
                            description "Enter the ripv1-requests-ignored context";

                            leaf total {
                                type yang:counter32;
                                description "The number of RIPv1 request packets received that were subsequently discarded for any reason.";
                            }

                            leaf last-5min {
                                type yang:counter32;
                                description "The number of RIPv1 request packets received in the last 5 minutes that were subsequently discarded for any reason.";
                            }

                            leaf last-1min {
                                type yang:counter32;
                                description "The number of RIPv1 request packets received in the last minute that were subsequently discarded for any reason.";
                            }

                        } // container ripv1-requests-ignored

                        container ripv2-updates-received {
                            description "Enter the ripv2-updates-received context";

                            leaf total {
                                type yang:counter32;
                                description "The number of RIPv2 response packets received.";
                            }

                            leaf last-5min {
                                type yang:counter32;
                                description "The number of RIPv2 response packets received in the last 5 minutes.";
                            }

                            leaf last-1min {
                                type yang:counter32;
                                description "The number of RIPv2 response packets received in the last minute.";
                            }

                        } // container ripv2-updates-received

                        container ripv2-updates-ignored {
                            description "Enter the ripv2-updates-ignored context";

                            leaf total {
                                type yang:counter32;
                                description "The number of RIPv2 response packets received which were subsequently discarded for any reason.";
                            }

                            leaf last-5min {
                                type yang:counter32;
                                description "The number of RIPv2 response packets received in the last 5 minutes which were subsequently discarded for any reason.";
                            }

                            leaf last-1min {
                                type yang:counter32;
                                description "The number of RIPv2 response packets received in the last minute which were subsequently discarded for any reason.";
                            }

                        } // container ripv2-updates-ignored

                        container ripv2-bad-routes {
                            description "Enter the ripv2-bad-routes context";

                            leaf total {
                                type yang:counter32;
                                description
                                    "The number of routes, in valid RIPv2 packets, which were ignored for any reason
                                     (e.g. unknown address family, or invalid metric).";
                            }

                            leaf last-5min {
                                type yang:counter32;
                                description
                                    "The number of routes, in valid RIPv2 packets, which were ignored for any reason
                                     (e.g. unknown address family, or invalid metric) in the last 5 minutes.";
                            }

                            leaf last-1min {
                                type yang:counter32;
                                description
                                    "The number of routes, in valid RIPv2 packets, which were ignored for any reason
                                     (e.g. unknown address family, or invalid metric) in the last minute.";
                            }

                        } // container ripv2-bad-routes

                        container ripv2-requests-received {
                            description "Enter the ripv2-requests-received context";

                            leaf total {
                                type yang:counter32;
                                description "The number RIPv2 request packets received.";
                            }

                            leaf last-5min {
                                type yang:counter32;
                                description "The number RIPv2 request packets received in the last 5 minutes.";
                            }

                            leaf last-1min {
                                type yang:counter32;
                                description "The number RIPv2 request packets received in the last minute.";
                            }

                        } // container ripv2-requests-received

                        container ripv2-requests-ignored {
                            description "Enter the ripv2-requests-ignored context";

                            leaf total {
                                type yang:counter32;
                                description "The number of RIPv2 request packets received that were subsequently discarded for any reason.";
                            }

                            leaf last-5min {
                                type yang:counter32;
                                description "The number of RIPv2 request packets received in the last 5 minutes that were subsequently discarded for any reason.";
                            }

                            leaf last-1min {
                                type yang:counter32;
                                description "The number of RIPv2 request packets received in the last minute that were subsequently discarded for any reason.";
                            }

                        } // container ripv2-requests-ignored

                        container authentication-errors {
                            description "Enter the authentication-errors context";

                            leaf total {
                                type yang:counter32;
                                description "The number of RIPv2 packets received which were subsequently discarded because of an error authenticating the packet.";
                            }

                            leaf last-5min {
                                type yang:counter32;
                                description "The number of RIPv2 packets received in the last 5 minutes which were subsequently discarded because of an error authenticating the packet.";
                            }

                            leaf last-1min {
                                type yang:counter32;
                                description "The number of RIPv2 packets received in the last minute which were subsequently discarded because of an error authenticating the packet.";
                            }

                        } // container authentication-errors

                    } // container statistics

                } // list neighbor

            } // list group

        } // container rip

    } // grouping state-router-rip

}
