submodule nokia-conf-aps {

    yang-version "1.1";

    belongs-to nokia-conf { prefix "conf"; }

    import nokia-sros-yang-extensions     { prefix "sros-ext"; }
    import nokia-types-sros               { prefix "types-sros"; }

    include nokia-conf-groups;
    include nokia-conf-port;


    sros-ext:sros-major-release "rel22";

    organization "Nokia";

    contact
        "Nokia SR OS Support
         Web: <http://www.nokia.com>";

    description
        "Nokia YANG Data model to configure aps port parameters on SR OS based routers.

         Copyright 2016 Nokia. All rights reserved. Reproduction of this document
         is authorized on the condition that the foregoing copyright notice is included.

         This nokia-conf-aps YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-04-13";

    grouping conf-aps {
        list aps {
            key "group-id";
            description "Enter the aps list instance";

            leaf group-id {
                type uint32 {
                    range "1..128";
                }
                description "APS group ID";
            }

            leaf advertise-interval {
                type uint32 {
                    range "10..650";
                }
                units "deciseconds";
                default "10";
                description "Time between subsequent advertisement messages";
            }

            leaf hold-time {
                type uint32 {
                    range "10..650";
                }
                units "deciseconds";
                default "30";
                description "Time to wait for an advertisement packet";
            }

            leaf switching-mode {
                type enumeration {
                    enum "uni-directional"              { value 1; }
                    enum "bi-directional"               { value 2; }
                }
                default "bi-directional";
                description "Switching mode for the APS port";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            choice annexb-choice {
                default "non-annexb";
                case annexb {

                    container annexb {
                        presence "Enable the annexb context";
                        description "Enable the annexb context";

                        leaf wait-to-restore-time {
                            type uint32 {
                                range "0..3600";
                            }
                            units "seconds";
                            default "300";
                            description "Annex B mode operation wait to restore time";
                        }

                        leaf-list working-circuit {
                            type leafref {
                                path "../../../port/port-id";
                            }
                            max-elements 2;
                            ordered-by user;
                            description "Working circuit port for the APS group";
                        }

                    } // container annexb

                }
                case non-annexb {

                    leaf neighbor {
                        type types-sros:ip-address;
                        description "Neighbor IP address for multi-chassis APS";
                    }

                    leaf protect-circuit {
                        type leafref {
                            path "../../port/port-id";
                        }
                        description "Protection circuit port for the APS group";
                    }

                    leaf working-circuit {
                        type leafref {
                            path "../../port/port-id";
                        }
                        description "Working circuit port for the APS group";
                    }

                    container revert {
                        presence "Enable the revert context";
                        description "Enable the revert context";

                        leaf time {
                            type uint32 {
                                range "0|60..3600";
                            }
                            units "seconds";
                            default "300";
                            description "Wait time before switching back to the working circuit";
                        }

                    } // container revert

                }
            }
        } // list aps

    } // grouping conf-aps

}
