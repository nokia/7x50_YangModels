submodule nokia-state-qos {

    yang-version "1.1";

    belongs-to nokia-state { prefix "state"; }

    import ietf-yang-types                { prefix "yang"; }
    import nokia-sros-yang-extensions     { prefix "sros-ext"; }
    import nokia-types-card               { prefix "types-card"; }
    import nokia-types-qos                { prefix "types-qos"; }
    import nokia-types-sros               { prefix "types-sros"; }


    sros-ext:sros-major-release "rel22";

    organization "Nokia";

    contact
        "Nokia SR OS Support
         Web: <http://www.nokia.com>";

    description
        "Nokia YANG Data model with operational state for QoS policies on SR OS based routers.

         Copyright 2016 Nokia. All rights reserved. Reproduction of this document
         is authorized on the condition that the foregoing copyright notice is included.

         This nokia-state-qos YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-09-13";

    grouping state-qos {
        container qos {
            description "Enter the qos context";

            container overload {
                description "Enter the overload context";

                list card {
                    key "slot-number";
                    description "Enter the card list instance";

                    leaf slot-number {
                        type types-card:iom-card-slot;
                        description "The unique value which identifies the IOM slot within a chassis in the system.";
                    }

                    list fp {
                        key "fp-number";
                        description "Enter the fp list instance";

                        leaf fp-number {
                            type types-card:fp-id;
                            description
                                "The unique value which uniquely identifies the forwarding plane within
                                 a specific IOM card in the system.";
                        }

                        leaf ingress-ip-mac {
                            type types-sros:cam-state;
                            description "Ingress IPv4-MAC Qos CAM state";
                        }

                        leaf egress-ip-mac {
                            type types-sros:cam-state;
                            description "Egress IPv4-MAC Qos CAM state";
                        }

                        leaf ingress-ipv6 {
                            type types-sros:cam-state;
                            description "Ingress IPv6 Qos CAM state";
                        }

                        leaf egress-ipv6 {
                            type types-sros:cam-state;
                            description "Egress IPv6 Qos CAM state";
                        }

                    } // list fp

                } // list card

            } // container overload

            list sap-ingress {
                key "sap-ingress-policy-name";
                description "Enter the sap-ingress list instance";

                leaf sap-ingress-policy-name {
                    type types-qos:qos-policy-name;
                    description "Policy name";
                }

                leaf oper-policy-id {
                    type types-qos:qos-any-policy-id;
                    description "The sap-ingress QoS policy identifier.";
                }

                container subscriber-mgmt {
                    description "Enter the subscriber-mgmt context";

                    leaf num-policies {
                        type uint32;
                        description
                            "Specifies the number of pcc-rule shared policies that are currently created based on
                             this policy.";
                    }

                    container pcc-rule-entry {
                        description "Enter the pcc-rule-entry context";

                        leaf num-inserted {
                            type uint32;
                            description
                                "Specifies the number of pcc-rule IP criteria entries received from
                                 DIAMETER that have been inserted in this policy.";
                        }

                    } // container pcc-rule-entry

                    container dynamic-policer {
                        description "Enter the dynamic-policer context";

                        leaf num-inserted {
                            type uint32;
                            description
                                "Specifies the number of dynamic policers required for pcc-rule IP criteria entries
                                 received from Diameter that have been inserted in this policy.";
                        }

                    } // container dynamic-policer

                } // container subscriber-mgmt

            } // list sap-ingress

            container queue-group-templates {
                description "Enter the queue-group-templates context";

                container ingress {
                    description "Enter the ingress context";

                    list queue-group {
                        key "ingress-queue-group-name";
                        description "Enter the queue-group list instance";

                        leaf ingress-queue-group-name {
                            type types-sros:named-item;
                            description "Ingress queue group template name";
                        }

                        list queue {
                            key "queue-id";
                            description "Enter the queue list instance";

                            leaf queue-id {
                                type types-qos:ingress-queue-id;
                                description "Ingress Queue-Group Queue identifier";
                            }

                        } // list queue

                        list policer {
                            key "policer-id";
                            description "Enter the policer list instance";

                            leaf policer-id {
                                type types-qos:ingress-policer-id {
                                    range "1..32";
                                }
                                description "Ingress Queue-Group Policer identifier";
                            }

                        } // list policer

                    } // list queue-group

                } // container ingress

                container egress {
                    description "Enter the egress context";

                    list queue-group {
                        key "egress-queue-group-name";
                        description "Enter the queue-group list instance";

                        leaf egress-queue-group-name {
                            type types-sros:named-item;
                            description "Egress queue group template name";
                        }

                        list queue {
                            key "queue-id";
                            description "Enter the queue list instance";

                            leaf queue-id {
                                type types-qos:egress-queue-id;
                                description "Egress Queue-Group queue identifier";
                            }

                        } // list queue

                    } // list queue-group

                } // container egress

            } // container queue-group-templates

            list network {
                key "network-policy-name";
                description "Enter the network list instance";

                leaf network-policy-name {
                    type types-qos:network-policy-name;
                    description "QoS network policy name";
                }

                leaf oper-policy-id {
                    type types-qos:qos-any-policy-id;
                    description "Network QoS policy identifier.";
                }

            } // list network

            list vlan-qos-policy {
                key "vlan-qos-policy-name";
                description "Enter the vlan-qos-policy list instance";

                leaf vlan-qos-policy-name {
                    type types-sros:named-item-64;
                    description "VLAN QoS policy name";
                }

            } // list vlan-qos-policy

            list sap-egress {
                key "sap-egress-policy-name";
                description "Enter the sap-egress list instance";

                leaf sap-egress-policy-name {
                    type types-qos:qos-policy-name;
                    description "Policy name";
                }

                leaf oper-policy-id {
                    type types-qos:qos-any-policy-id;
                    description "The sap-egress QoS policy identifier.";
                }

                container subscriber-mgmt {
                    description "Enter the subscriber-mgmt context";

                    leaf num-policies {
                        type uint32;
                        description
                            "Specifies the number of pcc-rule shared policies that are currently created based on
                             this policy.";
                    }

                    container pcc-rule-entry {
                        description "Enter the pcc-rule-entry context";

                        leaf num-inserted {
                            type uint32;
                            description
                                "Specifies the number of pcc-rule IP criteria entries received from
                                 DIAMETER that have been inserted in this policy.";
                        }

                    } // container pcc-rule-entry

                    container dynamic-policer {
                        description "Enter the dynamic-policer context";

                        leaf num-inserted {
                            type uint32;
                            description
                                "Specifies the number of dynamic policers required for pcc-rule IP criteria entries
                                 received from Diameter that have been inserted in this policy.";
                        }

                    } // container dynamic-policer

                } // container subscriber-mgmt

            } // list sap-egress

            container shared-policers {
                description "Enter the shared-policers context";

                list policer {
                    key "shared-policer-name";
                    description "Enter the policer list instance";

                    leaf shared-policer-name {
                        type types-sros:named-item;
                        description "Name of the shared policer";
                    }

                    container statistics {
                        description "Enter the statistics context";

                        choice stat-mode {
                            case offered-profile-with-discards {

                                container offered-profile-with-discards {
                                    description "Enter the offered-profile-with-discards context";

                                    leaf in-profile-forwarded-packets {
                                        type yang:counter64;
                                        description "The number of in-profile packets forwarded.";
                                    }

                                    leaf in-profile-forwarded-octets {
                                        type yang:counter64;
                                        description "The number of in-profile octets forwarded.";
                                    }

                                    leaf out-profile-forwarded-packets {
                                        type yang:counter64;
                                        description "The number of out-of-profile packets forwarded.";
                                    }

                                    leaf out-profile-forwarded-octets {
                                        type yang:counter64;
                                        description "The number of out-of-profile octets forwarded.";
                                    }

                                    leaf dropped-exceed-profile-packets {
                                        type yang:counter64;
                                        description "The number of dropped-exceed-profile packets.";
                                    }

                                    leaf dropped-exceed-profile-octets {
                                        type yang:counter64;
                                        description "The number of dropped-exceed-profile octets.";
                                    }

                                } // container offered-profile-with-discards

                            }
                        }
                    } // container statistics

                } // list policer

            } // container shared-policers

        } // container qos

    } // grouping state-qos

}
