submodule nokia-state-router-segment-routing {

    yang-version "1.1";

    belongs-to nokia-state { prefix "state"; }

    import ietf-yang-types                { prefix "yang"; }
    import nokia-sros-yang-extensions     { prefix "sros-ext"; }
    import nokia-types-igp                { prefix "types-igp"; }
    import nokia-types-sr-mpls            { prefix "types-sr-mpls"; }
    import nokia-types-sros               { prefix "types-sros"; }

    include nokia-state-router;


    sros-ext:sros-major-release "rel22";

    organization "Nokia";

    contact
        "Nokia SR OS Support
         Web: <http://www.nokia.com>";

    description
        "Nokia YANG Data model with operational state for segment routing management on SR OS based routers.

         Copyright 2016 Nokia. All rights reserved. Reproduction of this document
         is authorized on the condition that the foregoing copyright notice is included.

         This nokia-state-router-segment-routing YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2024-02-02";

    grouping state-router-segment-routing {
        container segment-routing {
            description "Enter the segment-routing context";

            container sr-mpls {
                description "Enter the sr-mpls context";

                list prefix-sids {
                    key "interface-name";
                    description "Enter the prefix-sids list instance";

                    leaf interface-name {
                        type leafref {
                            path "../../../../interface/interface-name";
                        }
                        description "Loopback interface name that owns prefix to advertise";
                    }

                    container ipv4-sid {
                        description "Enter the ipv4-sid context";

                        leaf oper-state {
                            type types-sr-mpls:sid-oper-state;
                        }

                    } // container ipv4-sid

                    container ipv6-sid {
                        description "Enter the ipv6-sid context";

                        leaf oper-state {
                            type types-sr-mpls:sid-oper-state;
                        }

                    } // container ipv6-sid

                } // list prefix-sids

            } // container sr-mpls

            container sr-policies {
                description "Enter the sr-policies context";

                leaf ttm-preferences {
                    type uint32;
                    description "Specifies the TTM preferences used for sr-policy tunnels.";
                }

                leaf binding-sids-allocated {
                    type uint32;
                    description "Specifies the binding-sids allocated.";
                }

                leaf static-local-policies {
                    type uint32;
                    description "Specifies the static local policies.";
                }

                leaf active-static-local-policies {
                    type uint32;
                    description "Specifies the active static local policies.";
                }

                leaf static-non-local-policies {
                    type uint32;
                    description "Specifies the static non-local policies.";
                }

                leaf bgp-policies {
                    type uint32;
                    description "Specifies the bgp policies.";
                }

                leaf active-bgp-policies {
                    type uint32;
                    description "Specifies the active bgp policies.";
                }

                list static-policy {
                    key "name";
                    description "Enter the static-policy list instance";

                    leaf name {
                        type types-sros:named-item-64;
                        description "Name for the segment routing static policy";
                    }

                    container segment-routing-v6 {
                        description "Enter the segment-routing-v6 context";

                        list binding-sid {
                            key "index";
                            description "Enter the binding-sid list instance";

                            leaf index {
                                type uint32 {
                                    range "1";
                                }
                                description "Binding SID index";
                            }

                            choice binding-sid-type {
                                case local-binding-sid {

                                    container locator {
                                        description "Enter the locator context";

                                        leaf function-oper-value {
                                            type uint32;
                                            description "SRv6 operational function value.";
                                        }

                                        leaf function-status {
                                            type types-sros:srv6-error-status;
                                            description "State of the function.";
                                        }

                                    } // container locator

                                }
                            }
                        } // list binding-sid

                    } // container segment-routing-v6

                } // list static-policy

                list sr-path {
                    key "head-end color endpoint owner preference distinguisher";
                    description "Enter the sr-path list instance";

                    leaf head-end {
                        type types-sros:ip-address;
                        description "Head end address of the segment route path.";
                    }

                    leaf color {
                        type uint32;
                        description "Determines the set of traffic flows that would be steered by this policy.";
                    }

                    leaf endpoint {
                        type types-sros:ip-address;
                        description "Destination of the source-routed path.";
                    }

                    leaf owner {
                        type enumeration {
                            enum "none"                         { value 0; }
                            enum "bgp"                          { value 1; }
                            enum "static"                       { value 2; }
                            enum "nsp"                          { value 3; }
                        }
                        description "Owner of the segment routing policy instance.";
                    }

                    leaf preference {
                        type uint32;
                        description "Indicates the preference value of this static policy.";
                    }

                    leaf distinguisher {
                        type uint32;
                        description "Is required if the head-end of the policy is not local.";
                    }

                    leaf tunnel-id {
                        type uint32;
                        description "Specifies the tunnel-id used by the segment routing path.";
                    }

                    leaf active {
                        type boolean;
                        description "Indicates whether segment routing path is active.";
                    }

                    leaf path-age {
                        type uint32;
                        description "Specifies the age of the segment routing path.";
                    }

                    leaf re-evaluations {
                        type uint32;
                        description "Specifies the number of re-evaluations for segment routing path.";
                    }

                    leaf active-path-changes {
                        type uint32;
                        description "Specifies the number of active path changes for segment routing path.";
                    }

                    leaf re-evaluation-reason {
                        type enumeration {
                            enum "none"                         { value 0; }
                            enum "route-add"                    { value 1; }
                            enum "route-mod"                    { value 2; }
                            enum "route-del"                    { value 3; }
                            enum "tunnel-down"                  { value 4; }
                            enum "sr-failure"                   { value 5; }
                            enum "route-audit"                  { value 6; }
                            enum "admin-no-shut"                { value 7; }
                            enum "bsid-failure"                 { value 8; }
                        }
                        description "Specifies the reason for the last re-evaluation of the segment routing path.";
                    }

                    leaf binding-sid {
                        type types-sros:mpls-label-or-zero;
                        description "Specifies the number of active path changes for segment routing path.";
                    }

                    leaf origin-address {
                        type types-sros:ip-address;
                        description "Address of the originating bgp router-id.";
                    }

                    leaf origin-asn {
                        type uint32;
                        description
                            "Specifies the ASN of the node/controller signalling the candidate path
                             when it has a BGP session to the head-end.";
                    }

                    leaf maintenance-policy {
                        type types-sros:named-item-or-empty;
                        description "Specifies the maintenance-policy for the sr-path.";
                    }

                    leaf type {
                        type enumeration {
                            enum "sr-mpls"                      { value 1; }
                            enum "srv6"                         { value 2; }
                        }
                        description "Path type.";
                    }

                    list srv6-binding-sid {
                        key "index";
                        description "Enter the srv6-binding-sid list instance";

                        leaf index {
                            type uint32;
                            description "Binding SID index.";
                        }

                        leaf srv6-oper-binding-sid {
                            type types-sros:ipv6-address;
                            description "Operational SRv6 Binding SID IP address";
                        }

                    } // list srv6-binding-sid

                    list sr-path-seg-list {
                        key "seg-list-index";
                        description "Enter the sr-path-seg-list list instance";

                        leaf seg-list-index {
                            type uint32 {
                                range "1..32";
                            }
                            description "Index for identifying a specific segment list";
                        }

                        leaf weight {
                            type uint32;
                            description "Specifies the relative weight of the segment list associated with a static policy.";
                        }

                        leaf segments {
                            type uint32;
                            description "Specifies the number of segments in the routing path.";
                        }

                        leaf sbfd-state {
                            type enumeration {
                                enum "down"                         { value 0; }
                                enum "up"                           { value 1; }
                            }
                            description "Specifies the s-bfd state for the routing path.";
                        }

                        leaf sbfd-transitions {
                            type uint32;
                            description "Specifies the s-bfd transitions for the routing path.";
                        }

                        list segment {
                            key "segment-index";
                            description "Enter the segment list instance";

                            leaf segment-index {
                                type uint32 {
                                    range "1..11";
                                }
                                description "Index for identifying a segment in a segment list";
                            }

                            leaf label {
                                type uint32;
                                description "Specifies the label used by the segment in the segment routing path.";
                            }

                            leaf srv6-sid {
                                type types-sros:ipv6-address;
                                description "SRv6 SID used by the segment in the segment routing path.";
                            }

                            leaf segment-state {
                                type enumeration {
                                    enum "not-applicable"               { value 0; }
                                    enum "resolved-up"                  { value 1; }
                                    enum "resolved-down"                { value 2; }
                                }
                                description "Specifies the state of the segment.";
                            }

                        } // list segment

                    } // list sr-path-seg-list

                } // list sr-path

                list sr-policy-ingress-statistics {
                    key "color endpoint";
                    description "Enter the sr-policy-ingress-statistics list instance";

                    leaf color {
                        type uint32;
                        description "Determines the set of traffic flows that would be steered by this policy.";
                    }

                    leaf endpoint {
                        type types-sros:ip-address;
                        description "Destination of the source-routed path.";
                    }

                    leaf tunnel-id {
                        type uint32;
                        description "Specifies the tunnel-id used by the segment routing path.";
                    }

                    leaf binding-sid {
                        type types-sros:mpls-label-or-zero;
                        description "Specifies the number of active path changes for segment routing path.";
                    }

                    leaf packet-count {
                        type uint64;
                        description "Specifies the packets received.";
                    }

                    leaf byte-count {
                        type uint64;
                        description "Specifies the bytes received.";
                    }

                } // list sr-policy-ingress-statistics

                list sr-policy-egress-statistics {
                    key "color endpoint segment-index";
                    description "Enter the sr-policy-egress-statistics list instance";

                    leaf color {
                        type uint32;
                        description "Determines the set of traffic flows that would be steered by this policy.";
                    }

                    leaf endpoint {
                        type types-sros:ip-address;
                        description "Destination of the source-routed path.";
                    }

                    leaf segment-index {
                        type uint32 {
                            range "1..32";
                        }
                        description "Segment-list index.";
                    }

                    leaf tunnel-id {
                        type uint32;
                        description "Specifies the tunnel-id used by the segment routing path.";
                    }

                    leaf binding-sid {
                        type types-sros:mpls-label-or-zero;
                        description "Specifies the number of active path changes for segment routing path.";
                    }

                    leaf packet-count {
                        type uint64;
                        description "Specifies the packets received.";
                    }

                    leaf byte-count {
                        type uint64;
                        description "Specifies the bytes received.";
                    }

                } // list sr-policy-egress-statistics

            } // container sr-policies

            container segment-routing-v6 {
                description "Enter the segment-routing-v6 context";

                list locator {
                    key "locator-name";
                    description "Enter the locator list instance";

                    leaf locator-name {
                        type types-sros:named-item-64;
                        description "SRv6 locator name";
                    }

                    leaf oper-state {
                        type types-sros:oper-state;
                        description "Locator operational state.";
                    }

                    leaf down-reason {
                        type types-sros:srv6-error-status;
                        description "Locator down reason.";
                    }

                } // list locator

                container micro-segment {
                    description "Enter the micro-segment context";

                    list block {
                        key "block-name";
                        description "Enter the block list instance";

                        leaf block-name {
                            type types-sros:named-item-64;
                            description "Micro-SID block name";
                        }

                    } // list block

                } // container micro-segment

                list micro-segment-locator {
                    key "locator-name";
                    description "Enter the micro-segment-locator list instance";

                    leaf locator-name {
                        type types-sros:named-item-64;
                        description "SRv6 locator name";
                    }

                    leaf oper-state {
                        type types-sros:oper-state;
                        description "Locator operational state.";
                    }

                    leaf down-reason {
                        type types-sros:srv6-error-status;
                        description "Locator down reason.";
                    }

                } // list micro-segment-locator

                container base-routing-instance {
                    description "Enter the base-routing-instance context";

                    list locator {
                        key "locator-name";
                        description "Enter the locator list instance";

                        leaf locator-name {
                            type leafref {
                                path "../../../locator/locator-name";
                            }
                            description "SRv6 locator name";
                        }

                        container function {
                            description "Enter the function context";

                            list end {
                                key "value";
                                description "Enter the end list instance";

                                leaf value {
                                    type uint32 {
                                        range "1..1048575";
                                    }
                                    description "SRv6 SID function value";
                                }

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // list end

                            list end-x {
                                key "value";
                                description "Enter the end-x list instance";

                                leaf value {
                                    type uint32 {
                                        range "1..1048575";
                                    }
                                    description "SRv6 SID function value";
                                }

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // list end-x

                            list end-x-dynamic {
                                key "value";
                                description "Enter the end-x-dynamic list instance";

                                leaf value {
                                    type uint32;
                                    description "SRv6 function value";
                                }

                                leaf segment-identifier {
                                    type types-sros:ipv6-address;
                                    description "address used in the SRv6 packet.";
                                }

                                leaf srh-mode {
                                    type enumeration {
                                        enum "psp"                          { value 1; }
                                        enum "usp"                          { value 2; }
                                    }
                                    description "Indicates the srh-mode.";
                                }

                                leaf protection {
                                    type enumeration {
                                        enum "unprotected"                  { value 0; }
                                        enum "protected"                    { value 1; }
                                    }
                                    description "Indicates whether the adjacency is protected or not.";
                                }

                                leaf interface-name {
                                    type types-sros:named-item;
                                    description "Indicates the interface for the end.x function.";
                                }

                                leaf instance-id {
                                    type uint32;
                                    description "Indicates the instance-id for the end.x function.";
                                }

                                container isis {
                                    description "Enter the isis context";

                                    leaf sid-level {
                                        type enumeration {
                                            enum "isisl1"                       { value 1; }
                                            enum "isisl2"                       { value 2; }
                                            enum "isisl1l2"                     { value 3; }
                                        }
                                        description "Sid level for end-x function";
                                    }

                                    leaf mac-address {
                                        type yang:mac-address;
                                        description "MAC address for end-x function";
                                    }

                                    leaf neighbor-system-id {
                                        type types-igp:system-id;
                                        description "Indicates the neighbor system-id for end.x function";
                                    }

                                } // container isis

                            } // list end-x-dynamic

                            container end-dt4 {
                                description "Enter the end-dt4 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt4

                            container end-dt6 {
                                description "Enter the end-dt6 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt6

                            container end-dt46 {
                                description "Enter the end-dt46 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt46

                        } // container function

                    } // list locator

                    list micro-segment-locator {
                        key "locator-name";
                        description "Enter the micro-segment-locator list instance";

                        leaf locator-name {
                            type leafref {
                                path "../../../../../../router/segment-routing/segment-routing-v6/micro-segment-locator/locator-name";
                            }
                            description "SRv6 micro-segment locator name";
                        }

                        container function {
                            description "Enter the function context";

                            list ua {
                                key "value";
                                description "Enter the ua list instance";

                                leaf value {
                                    type uint32 {
                                        range "1..1048575";
                                    }
                                    description "SRv6 SID function value";
                                }

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // list ua

                            list ua-dynamic {
                                key "value";
                                description "Enter the ua-dynamic list instance";

                                leaf value {
                                    type uint32;
                                    description "SRv6 function value";
                                }

                                leaf segment-identifier {
                                    type types-sros:ipv6-address;
                                    description "address used in the SRv6 packet.";
                                }

                                leaf srh-mode {
                                    type enumeration {
                                        enum "psp"                          { value 1; }
                                        enum "usp"                          { value 2; }
                                    }
                                    description "Indicates the srh-mode.";
                                }

                                leaf protection {
                                    type enumeration {
                                        enum "unprotected"                  { value 0; }
                                        enum "protected"                    { value 1; }
                                    }
                                    description "Indicates whether the adjacency is protected or not.";
                                }

                                leaf interface-name {
                                    type types-sros:named-item;
                                    description "Indicates the interface for the end.x function.";
                                }

                                leaf instance-id {
                                    type uint32;
                                    description "Indicates the instance-id for the end.x function.";
                                }

                                container isis {
                                    description "Enter the isis context";

                                    leaf sid-level {
                                        type enumeration {
                                            enum "isisl1"                       { value 1; }
                                            enum "isisl2"                       { value 2; }
                                            enum "isisl1l2"                     { value 3; }
                                        }
                                        description "Sid level for end-x function";
                                    }

                                    leaf mac-address {
                                        type yang:mac-address;
                                        description "MAC address for end-x function";
                                    }

                                    leaf neighbor-system-id {
                                        type types-igp:system-id;
                                        description "Indicates the neighbor system-id for end.x function";
                                    }

                                } // container isis

                            } // list ua-dynamic

                            container udt4 {
                                description "Enter the udt4 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container udt4

                            container udt6 {
                                description "Enter the udt6 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container udt6

                            container udt46 {
                                description "Enter the udt46 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container udt46

                        } // container function

                    } // list micro-segment-locator

                } // container base-routing-instance

                container events {
                    description "Enter the events context";

                    container last-service-sid-index-threshold-change {
                        description "Enter the last-service-sid-index-threshold-change context";

                        leaf service-sid-index-usage {
                            type uint32 {
                                range "0..100";
                            }
                            units "percent";
                            description
                                "The value indicates percentage of service sid  used
                                 by the system";
                        }

                        leaf change-type {
                            type enumeration {
                                enum "increase"                     { value 1; }
                                enum "decrease"                     { value 2; }
                            }
                            description
                                "The value indicates whether service sid index usage is
                                 increasing or decreasing.";
                        }

                        leaf last-occurrence {
                            type yang:date-and-time;
                            description "Indicates the timestamp of the last time the event was detected.";
                        }

                    } // container last-service-sid-index-threshold-change

                } // container events

            } // container segment-routing-v6

        } // container segment-routing

    } // grouping state-router-segment-routing

}
