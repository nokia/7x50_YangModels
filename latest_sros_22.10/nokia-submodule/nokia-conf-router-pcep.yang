submodule nokia-conf-router-pcep {

    yang-version "1.1";

    belongs-to nokia-conf { prefix "conf"; }

    import nokia-sros-yang-extensions     { prefix "sros-ext"; }
    import nokia-types-sros               { prefix "types-sros"; }

    include nokia-conf-groups;
    include nokia-conf-system;
    include nokia-conf-system-security;
    include nokia-conf-system-security-tls;


    sros-ext:sros-major-release "rel22";

    organization "Nokia";

    contact
        "Nokia SR OS Support
         Web: <http://www.nokia.com>";

    description
        "Nokia YANG Data model to configure pcep protocol on SR OS based routers.

         Copyright 2016 Nokia. All rights reserved. Reproduction of this document
         is authorized on the condition that the foregoing copyright notice is included.

         This nokia-conf-router-pcep YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2024-03-08";

    grouping conf-router-pcep {
        container pcep {
            when "../router-name = 'Base'";
            description "Enter the pcep context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container pcc {
                presence "Enable the pcc context";
                description "Enable the pcc context";

                leaf admin-state {
                    type types-sros:admin-state;
                    default "disable";
                    description "Administrative state of the PCEP session element";
                }

                leaf keepalive {
                    type uint32 {
                        range "1..255";
                    }
                    units "seconds";
                    sros-ext:auto-restart-to-modify;
                    default "30";
                    description "Configure keepalive";
                }

                leaf local-address {
                    type types-sros:ipv4-unicast-address;
                    sros-ext:auto-restart-to-modify;
                    description "Local IPv4 address of the PCEP speaker";
                }

                leaf local-address-ipv6 {
                    type types-sros:ipv6-unicast-address;
                    sros-ext:auto-restart-to-modify;
                    description "Local IPv6 address of the PCEP speaker";
                }

                leaf unknown-message-rate {
                    type uint32 {
                        range "1..255";
                    }
                    default "10";
                    description "Configure unknown message rate";
                }

                leaf report-path-constraints {
                    type boolean;
                    default "true";
                    description "Include LSP path constraints in PCE report messages";
                }

                leaf dead-timer {
                    type uint32 {
                        range "1..255";
                    }
                    units "seconds";
                    sros-ext:auto-restart-to-modify;
                    default "120";
                    description "Configure dead timer";
                }

                leaf redelegation-timer {
                    type uint32 {
                        range "1..3600";
                    }
                    units "seconds";
                    default "90";
                    description "Configure redelegation-timer";
                }

                leaf max-srte-pce-init-lsps {
                    type uint32 {
                        range "0..8191";
                    }
                    sros-ext:auto-restart-to-modify;
                    default "8191";
                    description "Configure max sr te pce init LSP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container state-timer {
                    description "Enter the state-timer context";

                    leaf timer {
                        type uint32 {
                            range "1..3600";
                        }
                        units "seconds";
                        default "180";
                        description "Configure state-timer";
                    }

                    leaf timer-action {
                        type enumeration {
                            enum "none"                         { value 0; }
                            enum "remove"                       { value 1; }
                        }
                        default "remove";
                        description "State timer action remove/none";
                    }

                } // container state-timer

                list peer {
                    key "ip-address";
                    max-elements 2;
                    description "Enter the peer list instance";

                    leaf ip-address {
                        type types-sros:ip-unicast-address;
                        description "Destination IP address of a PCE peer in a PCEP session";
                    }

                    leaf admin-state {
                        type types-sros:admin-state;
                        default "disable";
                        description "Administrative state of the PCC peer";
                    }

                    leaf preference {
                        type uint32 {
                            range "0..100";
                        }
                        sros-ext:immutable;
                        default "0";
                        description "Preference value of the peer";
                    }

                    leaf tls-client-profile {
                        type leafref {
                            path "../../../../../system/security/tls/client-tls-profile/client-profile-name";
                        }
                        sros-ext:auto-restart-to-modify;
                        description "TLS client profile name assigned to this PCC peer";
                    }

                    leaf tls-wait-timer {
                        type uint32 {
                            range "60..255";
                        }
                        units "seconds";
                        sros-ext:auto-restart-to-modify;
                        default "60";
                        description "Time the PCC waits until declaring handshake failure";
                    }

                    leaf route-preference {
                        type enumeration {
                            enum "inband"                       { value 1; }
                            enum "outband"                      { value 2; }
                            enum "both"                         { value 3; }
                        }
                        sros-ext:auto-restart-to-modify;
                        default "both";
                        description "Route preference to reach the PCE server";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list peer

                container pce-associations {
                    description "Enter the pce-associations context";

                    list diversity {
                        key "assoc-name";
                        description "Enter the diversity list instance";

                        leaf assoc-name {
                            type types-sros:named-item;
                            description "Name of the association group";
                        }

                        leaf association-id {
                            type uint32 {
                                range "0..65535";
                            }
                            default "0";
                            description "Association ID for the diversity association group";
                        }

                        leaf association-source {
                            type types-sros:ip-unicast-address;
                            description "Source IP address of the diversity association";
                        }

                        leaf disjointness-reference {
                            type boolean;
                            default "false";
                            description "Configure P-flag in the disjointness configuration TLV";
                        }

                        leaf disjointness-type {
                            type enumeration {
                                enum "strict"                       { value 1; }
                                enum "loose"                        { value 2; }
                            }
                            default "loose";
                            description "Disjointness type for the association group";
                        }

                        leaf diversity-type {
                            type enumeration {
                                enum "none"                         { value 0; }
                                enum "link"                         { value 1; }
                                enum "node"                         { value 2; }
                                enum "srlg-link"                    { value 3; }
                                enum "srlg-node"                    { value 4; }
                            }
                            default "none";
                            description "Diversity type for the association group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list diversity

                    list policy {
                        key "assoc-name";
                        description "Enter the policy list instance";

                        leaf assoc-name {
                            type types-sros:named-item;
                            description "Name of the association group";
                        }

                        leaf association-id {
                            type uint32 {
                                range "0..65535";
                            }
                            default "0";
                            description "Association ID for the policy association group";
                        }

                        leaf association-source {
                            type types-sros:ip-unicast-address;
                            description "Source IP address for the association";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list policy

                } // container pce-associations

            } // container pcc

            container pce {
                presence "Enable the pce context";
                description "Enable the pce context";

                leaf admin-state {
                    type types-sros:admin-state;
                    default "disable";
                    description "Administrative state of the PCEP session element";
                }

                leaf keepalive {
                    type uint32 {
                        range "1..255";
                    }
                    units "seconds";
                    sros-ext:auto-restart-to-modify;
                    default "30";
                    description "Configure keepalive";
                }

                leaf local-address {
                    type types-sros:ipv4-unicast-address;
                    sros-ext:auto-restart-to-modify;
                    description "Local IPv4 address of the PCEP speaker";
                }

                leaf local-address-ipv6 {
                    type types-sros:ipv6-unicast-address;
                    sros-ext:auto-restart-to-modify;
                    description "Local IPv6 address of the PCEP speaker";
                }

                leaf unknown-message-rate {
                    type uint32 {
                        range "1..255";
                    }
                    default "10";
                    description "Configure unknown message rate";
                }

                leaf dead-timer {
                    type uint32 {
                        range "1..255";
                    }
                    units "seconds";
                    sros-ext:auto-restart-to-modify;
                    default "120";
                    description "Configure dead timer";
                }

                leaf tls-server-profile {
                    type leafref {
                        path "../../../../system/security/tls/server-tls-profile/server-profile-name";
                    }
                    sros-ext:auto-restart-to-modify;
                    description "TLS server profile name assigned to this PCE";
                }

                leaf tls-wait-timer {
                    type uint32 {
                        range "60..255";
                    }
                    units "seconds";
                    sros-ext:auto-restart-to-modify;
                    default "60";
                    description "Configure tls-wait-timer";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container pce

        } // container pcep

    } // grouping conf-router-pcep

}
