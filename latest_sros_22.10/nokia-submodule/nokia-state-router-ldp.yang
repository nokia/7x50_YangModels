submodule nokia-state-router-ldp {

    yang-version "1.1";

    belongs-to nokia-state { prefix "state"; }

    import ietf-yang-types                { prefix "yang"; }
    import nokia-sros-yang-extensions     { prefix "sros-ext"; }
    import nokia-types-ldp                { prefix "types-ldp"; }
    import nokia-types-mpls               { prefix "types-mpls"; }
    import nokia-types-services           { prefix "types-services"; }
    import nokia-types-sros               { prefix "types-sros"; }

    include nokia-state-policy-options;
    include nokia-state-router;


    sros-ext:sros-major-release "rel22";

    organization "Nokia";

    contact
        "Nokia SR OS Support
         Web: <http://www.nokia.com>";

    description
        "Nokia YANG Data model with operational state for ldp protocol on SR OS based routers.

         Copyright 2016 Nokia. All rights reserved. Reproduction of this document
         is authorized on the condition that the foregoing copyright notice is included.

         This nokia-state-router-ldp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-04-28";

    grouping state-router-ldp {
        container ldp {
            description "Enter the ldp context";

            leaf backoff-time {
                type types-ldp:backoff-time {
                    range "1..2592000";
                }
                description "The value specifies the initial value for the backoff interval.";
            }

            leaf max-backoff-time {
                type types-ldp:backoff-time;
                description "The value specifies the maximum value for the backoff interval.";
            }

            leaf ipv4-up-time {
                type yang:timeticks {
                    range "0..2147483647";
                }
                description
                    "The value indicates the time, in centiseconds, that
                     the IPv4 LDP instance has been in current operational state.";
            }

            leaf ipv6-up-time {
                type yang:timeticks {
                    range "0..2147483647";
                }
                description
                    "The value indicates the time, in centiseconds,
                     that the IPv6 LDP instance has been in current operational state.";
            }

            leaf ipv4-oper-state {
                type types-sros:oper-state;
                description "The value indicates the current operational state of this IPv4 LDP instance.";
            }

            leaf ipv6-oper-state {
                type types-sros:oper-state;
                description "The value indicates the current operational state of this IPv6 LDP instance.";
            }

            leaf ipv4-down-reason {
                type types-ldp:gen-down-reason-code;
                description
                    "The value indicates the reason
                     that the IPv4 LDP instance is operationally down.";
            }

            leaf ipv6-down-reason {
                type types-ldp:gen-down-reason-code;
                description
                    "The value indicates the reason
                     that the IPv6 LDP instance is operationally down.";
            }

            leaf ipv4-label-switch-router-id {
                type types-sros:ipv4-address;
                description
                    "The value is the IPv4 Label Switch Router
                     (LSR) identifier which is used as the first 4 bytes or the
                     Router Id component of the Label Distribution Protocol (LDP)
                     identifier.";
            }

            leaf ipv6-label-switch-router-id {
                type types-sros:ipv6-address;
                description
                    "The value is the IPv6 Label Switch Router
                     (LSR) identifier which is used as the first 16 bytes or the
                     Router Id component of the Label Distribution Protocol (LDP)
                     identifier.";
            }

            leaf protocol-version {
                type uint32;
                description
                    "The value specifies the version of the LDP protocol. A value of
                     zero (0) indicates that the version of the protocol is unknown.";
            }

            leaf deaggregate-fec {
                type boolean;
                description
                    "When deaggregate-fec has a value of 'false', LDP aggregates
                     multiple prefixes into a single Forwarding Equivalence Class
                     (FEC) and advertises a single label for the FEC. When the
                     value is 'true', LDP deaggregates prefixes into multiple FECs.";
            }

            leaf control-mode {
                type enumeration {
                    enum "ordered"                      { value 1; }
                    enum "independent"                  { value 2; }
                }
                description
                    "The value specifies the mode used for distributing labels
                     in response to label binding requests.";
            }

            leaf distribution-method {
                type types-ldp:distribution-method;
                description "The value specifies the label distribution method used.";
            }

            leaf retention-mode {
                type enumeration {
                    enum "conservative"                 { value 1; }
                    enum "liberal"                      { value 2; }
                }
                description "The value specifies the label retention mode used.";
            }

            leaf propagate-policy {
                type enumeration {
                    enum "system"                       { value 1; }
                    enum "interface"                    { value 2; }
                    enum "all"                          { value 3; }
                    enum "none"                         { value 4; }
                }
                description
                    "The value determines whether the LSR should generate
                     FECs and which FECs it should generate.";
            }

            leaf loop-detection-cap {
                type enumeration {
                    enum "none"                         { value 1; }
                    enum "other"                        { value 2; }
                    enum "hop-count"                    { value 3; }
                    enum "path-vector"                  { value 4; }
                    enum "hop-count-and-path-vector"    { value 5; }
                }
                description
                    "The value indicates whether this LSR supports loop detection
                     and if so, what type of loop detection is supported.";
            }

            leaf hop-limit {
                type uint32 {
                    range "0..255";
                }
                description "The value specifies the maximum allowable value for the hop count.";
            }

            leaf path-vector-limit {
                type uint32 {
                    range "0..255";
                }
                description
                    "The value of path-vector-limit specifies the maximum
                     allowable value for the path vector count.";
            }

            leaf route-preference {
                type uint32 {
                    range "1..255";
                }
                description
                    "The value of route preference assigned to LDP routes. When multiple routes are
                     available to a destination, the route with the lowest preference will be used.";
            }

            leaf oper-ecmp {
                type uint32 {
                    range "1..64";
                }
                description
                    "The operational ECMP value. This value is the smaller of the configured router
                     ECMP value and the configured LDP max-ecmp-routes value.";
            }

            container capability {
                description "Enter the capability context";

                leaf p2mp {
                    type boolean;
                    description
                        "The value indicates whether Point-to-Multipoint (P2MP) FEC capability is
                         supported in the LDP instance or not.";
                }

                leaf multipoint-make-before-break {
                    type boolean;
                    description
                        "The value indicates whether Multipoint Make-Before-Break (MBB) capability
                         is supported in the LDP instance or not.";
                }

                leaf dynamic {
                    type boolean;
                    description
                        "The value indicates whether dynamic capability negotiation is supported
                         or not in LDP sessions associated with the LDP instance.";
                }

                leaf overload {
                    type boolean;
                    description
                        "The value indicates whether LSR Overload is supported or not in LDP
                         sessions associated with the LDP instance.";
                }

                leaf fec128 {
                    type boolean;
                    description
                        "The value indicates whether or not PW (Pseudowire) ID FEC capability is
                         supported in LDP instance.";
                }

                leaf fec129 {
                    type boolean;
                    description
                        "The value indicates whether or not General PW ID FEC capability is
                         supported in LDP instance.";
                }

                leaf ipv4-prefix-fec {
                    type boolean;
                    description
                        "The value indicates whether or not IPv4 Prefix FEC capability is
                         supported in LDP instance.";
                }

                leaf ipv6-prefix-fec {
                    type boolean;
                    description
                        "The value indicates whether or not IPv6 Prefix FEC capability is
                         supported in LDP instance.";
                }

                leaf unrecognized-notification {
                    type boolean;
                    description
                        "The value indicates whether or not Unrecognized Notification
                         capability is supported in LDP instance.";
                }

            } // container capability

            container statistics {
                description "Enter the statistics context";

                container targeted-peer {
                    description "Enter the targeted-peer context";

                    container ipv4 {
                        description "Enter the ipv4 context";

                        leaf active {
                            type uint32;
                            description
                                "The value indicates the number of active (i.e. operationally
                                 up) peers or interfaces associated with the LDP instance.";
                        }

                        leaf inactive {
                            type uint32;
                            description
                                "The value indicates the number of inactive (i.e. operationally
                                 down) peers or interfaces associated with the LDP instance.";
                        }

                        leaf overloaded {
                            type uint32;
                            description
                                "The value indicates the number of overloaded peers or interfaces
                                 in the LDP instance.";
                        }

                    } // container ipv4

                    container ipv6 {
                        description "Enter the ipv6 context";

                        leaf active {
                            type uint32;
                            description
                                "The value indicates the number of active (i.e. operationally
                                 up) peers or interfaces associated with the LDP instance.";
                        }

                        leaf inactive {
                            type uint32;
                            description
                                "The value indicates the number of inactive (i.e. operationally
                                 down) peers or interfaces associated with the LDP instance.";
                        }

                        leaf overloaded {
                            type uint32;
                            description
                                "The value indicates the number of overloaded peers or interfaces
                                 in the LDP instance.";
                        }

                    } // container ipv6

                } // container targeted-peer

                container interface {
                    description "Enter the interface context";

                    container ipv4 {
                        description "Enter the ipv4 context";

                        leaf active {
                            type uint32;
                            description
                                "The value indicates the number of active (i.e. operationally
                                 up) peers or interfaces associated with the LDP instance.";
                        }

                        leaf inactive {
                            type uint32;
                            description
                                "The value indicates the number of inactive (i.e. operationally
                                 down) peers or interfaces associated with the LDP instance.";
                        }

                        leaf overloaded {
                            type uint32;
                            description
                                "The value indicates the number of overloaded peers or interfaces
                                 in the LDP instance.";
                        }

                    } // container ipv4

                    container ipv6 {
                        description "Enter the ipv6 context";

                        leaf active {
                            type uint32;
                            description
                                "The value indicates the number of active (i.e. operationally
                                 up) peers or interfaces associated with the LDP instance.";
                        }

                        leaf inactive {
                            type uint32;
                            description
                                "The value indicates the number of inactive (i.e. operationally
                                 down) peers or interfaces associated with the LDP instance.";
                        }

                        leaf overloaded {
                            type uint32;
                            description
                                "The value indicates the number of overloaded peers or interfaces
                                 in the LDP instance.";
                        }

                    } // container ipv6

                } // container interface

                container adjacency {
                    description "Enter the adjacency context";

                    container ipv4 {
                        description "Enter the ipv4 context";

                        leaf link {
                            type uint32;
                            description
                                "The value indicates the number of active link adjacencies (i.e
                                 established adjacencies) associated with the LDP instance.";
                        }

                        leaf targeted {
                            type uint32;
                            description
                                "The value indicates the number of active targeted adjacencies
                                 (i.e established adjacencies) associated with the LDP instance.";
                        }

                    } // container ipv4

                    container ipv6 {
                        description "Enter the ipv6 context";

                        leaf link {
                            type uint32;
                            description
                                "The value indicates the number of active link adjacencies (i.e
                                 established adjacencies) associated with the LDP instance.";
                        }

                        leaf targeted {
                            type uint32;
                            description
                                "The value indicates the number of active targeted adjacencies
                                 (i.e established adjacencies) associated with the LDP instance.";
                        }

                    } // container ipv6

                } // container adjacency

                container session {
                    description "Enter the session context";

                    container ipv4 {
                        description "Enter the ipv4 context";

                        leaf active {
                            type uint32;
                            description
                                "The value indicates the number of active sessions (i.e. session
                                 in some form of creation) associated with the LDP instance.";
                        }

                        leaf attempted {
                            type uint32;
                            description
                                "The value indicates the number of attempted sessions for LDP
                                 instance.";
                        }

                    } // container ipv4

                    container ipv6 {
                        description "Enter the ipv6 context";

                        leaf active {
                            type uint32;
                            description
                                "The value indicates the number of active sessions (i.e. session
                                 in some form of creation) associated with the LDP instance.";
                        }

                        leaf attempted {
                            type uint32;
                            description
                                "The value indicates the number of attempted sessions for LDP
                                 instance.";
                        }

                    } // container ipv6

                } // container session

                container protocol {
                    description "Enter the protocol context";

                    leaf bad-ldp-id-errors {
                        type uint32;
                        description
                            "The value indicates the number of Bad LDP Identifier
                             Fatal Errors detected for sessions associated with the
                             LDP instance.";
                    }

                    leaf bad-pdu-length-errors {
                        type uint32;
                        description
                            "The value indicates the number of Bad PDU Length Fatal
                             Errors detected for sessions associated with the LDP
                             instance.";
                    }

                    leaf bad-msg-length-errors {
                        type uint32;
                        description
                            "The value indicates the number of Bad Message Length
                             Fatal Errors detected for sessions associated with the
                             LDP instance.";
                    }

                    leaf bad-tlv-length-errors {
                        type uint32;
                        description
                            "The value indicates the number of Bad TLV Length
                             Fatal Errors detected for sessions associated with the
                             LDP instance.";
                    }

                    leaf malformed-tlv-errors {
                        type uint32;
                        description
                            "The value indicates the number of Malformed TLV Value
                             Fatal Errors detected for sessions associated with the
                             LDP instance.";
                    }

                    leaf keepalive-expired-errors {
                        type uint32;
                        description
                            "The value indicates the number of Session Keep Alive
                             Timer Expired Errors detected for sessions associated
                             with the LDP instance.";
                    }

                    leaf unknown-tlv-errors {
                        type uint32;
                        description
                            "The value indicates the number of Unknown TLV Fatal
                             Errors detected for sessions associated with the LDP
                             instance.";
                    }

                    leaf bad-protocol-version-errors {
                        type uint32;
                        description
                            "The value indicates the number of bad protocol version
                             errors detected for sessions associated with the LDP
                             instance.";
                    }

                    container rejected-sessions {
                        description "Enter the rejected-sessions context";

                        leaf hello-errors {
                            type uint32;
                            description
                                "The value indicates the total number of session
                                 rejected/No Hello Error Notification Messages sent
                                 or received by the LDP instance.";
                        }

                        leaf parameters-advertisement-errors {
                            type uint32;
                            description
                                "The value indicates total number of Session
                                 rejected/Parameters Advertisement Mode Error
                                 Notification Messages sent or received by the LDP
                                 instance.";
                        }

                        leaf max-pdu-errors {
                            type uint32;
                            description
                                "The value indicates total number of Session
                                 Rejected/Parameters Advertisement Mode Error
                                 Notifications Messages sent or received by the LDP
                                 instance.";
                        }

                        leaf label-range-errors {
                            type uint32;
                            description
                                "The value indicates total number of Session
                                 Rejected/Parameters Label Range  Error
                                 Notifications Messages sent or received by the LDP
                                 instance.";
                        }

                    } // container rejected-sessions

                    container shutdown-notify {
                        description "Enter the shutdown-notify context";

                        leaf sent {
                            type uint32;
                            description "The value indicates LDP shutdown notify sent count.";
                        }

                        leaf received {
                            type uint32;
                            description
                                "The value indicates LDP shutdown notify receive
                                 count.";
                        }

                    } // container shutdown-notify

                } // container protocol

                container fec-egress-prefixes {
                    description "Enter the fec-egress-prefixes context";

                    leaf ipv4 {
                        type uint32;
                        description
                            "The value indicates the number of IPv4 egress FEC
                             prefixes configured for statistics collection on the LDP instance.";
                    }

                    leaf ipv6 {
                        type uint32;
                        description
                            "The value indicates the number of IPv6 egress FEC
                             prefixes configured for statistics collection on the LDP instance.";
                    }

                } // container fec-egress-prefixes

                container oper-down-events {
                    description "Enter the oper-down-events context";

                    leaf ipv4 {
                        type uint32;
                        description
                            "The value indicates the number of times the IPv4 LDP
                             instance has gone operationally down since the instance
                             was created.";
                    }

                    leaf ipv6 {
                        type uint32;
                        description
                            "The value indicates the number of times the IPv6 LDP
                             instance has gone operationally down since the instance
                             was created.";
                    }

                } // container oper-down-events

                container fec-type {
                    description "Enter the fec-type context";

                    container prefixes {
                        description "Enter the prefixes context";

                        container ipv4 {
                            description "Enter the ipv4 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container ipv4

                        container ipv6 {
                            description "Enter the ipv6 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container ipv6

                    } // container prefixes

                    container p2mp {
                        description "Enter the p2mp context";

                        container ipv4 {
                            description "Enter the ipv4 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container ipv4

                        container ipv6 {
                            description "Enter the ipv6 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container ipv6

                    } // container p2mp

                    container services {
                        description "Enter the services context";

                        container fec128 {
                            description "Enter the fec128 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container fec128

                        container fec129 {
                            description "Enter the fec129 context";

                            leaf sent {
                                type uint32;
                                description
                                    "The value indicates the number of FECs sent by the LDP instance
                                     to its neighbors.";
                            }

                            leaf received {
                                type uint32;
                                description
                                    "The value indicates the number of FECs received by the LDP
                                     instance from its neighbors.";
                            }

                            leaf session-overload-sent {
                                type uint32;
                                description
                                    "The value indicates the number of Overload Notifications sent
                                     over sessions in the LDP instance.";
                            }

                            leaf session-overload-received {
                                type uint32;
                                description
                                    "The value indicates the number of Overload Notifications
                                     received over sessions in the LDP instance.";
                            }

                            leaf current-fecs-overloaded {
                                type uint32;
                                description
                                    "The value indicates the number of FEC in overload state in the
                                     LDP instance.";
                            }

                        } // container fec129

                    } // container services

                } // container fec-type

            } // container statistics

            list fec-originate {
                key "fec-prefix";
                description "Enter the fec-originate list instance";

                leaf fec-prefix {
                    type types-sros:ip-prefix;
                    description "Static FEC IP prefix";
                }

                leaf oper-in-label {
                    type uint32;
                    description
                        "The value indicates the operational value of the label that was
                         advertised to the upstream peer.";
                }

            } // list fec-originate

            container egress-statistics {
                description "Enter the egress-statistics context";

                list fec-prefix {
                    key "ip-prefix";
                    description "Enter the fec-prefix list instance";

                    leaf ip-prefix {
                        type types-sros:ip-prefix;
                        description "IP prefix";
                    }

                    container statistics {
                        description "Enter the statistics context";

                        container forwarding-class {
                            description "Enter the forwarding-class context";

                            container best-effort {
                                description "Enter the best-effort context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container best-effort

                            container low2 {
                                description "Enter the low2 context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container low2

                            container assured {
                                description "Enter the assured context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container assured

                            container low1 {
                                description "Enter the low1 context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container low1

                            container high2 {
                                description "Enter the high2 context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container high2

                            container expedited {
                                description "Enter the expedited context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container expedited

                            container high1 {
                                description "Enter the high1 context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container high1

                            container network-control {
                                description "Enter the network-control context";

                                container in-profile {
                                    description "Enter the in-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container in-profile

                                container out-profile {
                                    description "Enter the out-profile context";

                                    leaf packets {
                                        type yang:counter64;
                                        description
                                            "The value indicates the number of profile packets received for
                                             given forwarding class.";
                                    }

                                    leaf octets {
                                        type yang:counter64;
                                        description
                                            "The value indicates the number of profile octets received for
                                             given forwarding class.";
                                    }

                                } // container out-profile

                            } // container network-control

                        } // container forwarding-class

                        container aggregate {
                            description "Enter the aggregate context";

                            leaf packets {
                                type yang:counter64;
                                description
                                    "The value indicates the number of packets received for
                                     given FEC.";
                            }

                            leaf octets {
                                type yang:counter64;
                                description
                                    "The value indicates the number of octets received for
                                     given FEC.";
                            }

                        } // container aggregate

                    } // container statistics

                } // list fec-prefix

            } // container egress-statistics

            list lsp-bfd {
                key "prefix-list";
                description "Enter the lsp-bfd list instance";

                leaf prefix-list {
                    type leafref {
                        path "../../../../policy-options/prefix-list/name";
                    }
                    description "Name of a router policy options prefix list";
                }

                list prefix {
                    key "ip-prefix";
                    description "Enter the prefix list instance";

                    leaf ip-prefix {
                        type types-sros:ip-prefix;
                        description "A BFD on LDP LSP prefix.";
                    }

                    leaf bfd-state {
                        type enumeration {
                            enum "invalid"                      { value 0; description "Invalid state (unexpected)."; }
                            enum "no-match"                     { value 1; description "The prefix has not been matched to a prefix list."; }
                            enum "disabled"                     { value 2; description "The LSP BFD configuration is not enabled, or there is no tunnel for the prefix."; }
                            enum "src-addr-missing"             { value 3; description "There is no LDP LSRID for the address family."; }
                            enum "src-addr-mismatch"            { value 4; description "The address family of the prefix doesn't match the address family of the source address configured in the matched LSP-BFD prefix list."; }
                            enum "up"                           { value 5; description "LSP BFD is operationally up for the prefix."; }
                            enum "down"                         { value 6; description "LSP BFD is operationally down for the prefix, and the configured failure-action is 'down(1)'."; }
                            enum "down-trap-only"               { value 7; description "LSP BFD is operationally down for the prefix, and the configured failure-action is 'none(0)'."; }
                            enum "src-dst-addr-same"            { value 8; description "The address of the prefix is the same as the source address."; }
                        }
                        description
                            "Operational state of LDP LSP BFD on the associated prefix.
                             invalid - ";
                    }

                } // list prefix

            } // list lsp-bfd

            container interface-parameters {
                description "Enter the interface-parameters context";

                list interface {
                    key "ip-int-name";
                    description "Enter the interface list instance";

                    leaf ip-int-name {
                        type leafref {
                            path "../../../../interface/interface-name";
                        }
                        description "Interface name";
                    }

                    leaf oper-state {
                        type types-sros:oper-state;
                        description "Current operational status of this interface.";
                    }

                    leaf oper-down-reason {
                        type types-ldp:targ-oper-down-reason-code;
                        description "Reason why this interface is operationally down.";
                    }

                    container ipv4 {
                        description "Enter the ipv4 context";

                        leaf time-since-last-oper-change {
                            type yang:timeticks;
                            description
                                "Time, in centiseconds that the interface has been in current
                                 operational state.";
                        }

                        leaf oper-state {
                            type types-sros:oper-state;
                            description "Current operational status of this interface.";
                        }

                        leaf oper-down-reason {
                            type types-ldp:targ-oper-down-reason-code;
                            description "Reason why this interface is operationally down.";
                        }

                        leaf oper-hello-timeout {
                            type types-sros:time-duration {
                                range "3..65535";
                            }
                            units "seconds";
                            description "Operational hello time (hold time) used by the operational interface.";
                        }

                        leaf backoff-time {
                            type types-ldp:backoff-time {
                                range "1..2592000";
                            }
                            units "seconds";
                            description "Initial value for the backoff interval.";
                        }

                        leaf maximum-backoff-time {
                            type types-ldp:backoff-time;
                            units "seconds";
                            description "Maximum value for the backoff interval.";
                        }

                        leaf local-ip-address {
                            type types-sros:ip-address;
                            description "Local IP address used for Hellos sending.";
                        }

                        container statistics {
                            description "Enter the statistics context";

                            leaf existing-adjacencies {
                                type uint32;
                                description
                                    "The value indicates a count of the total
                                     active adjacencies.";
                            }

                            leaf bad-pdu-length {
                                type uint32;
                                description
                                    "The value indicates the number of bad PDU
                                     length errors detected.";
                            }

                            leaf bad-msg-length {
                                type uint32;
                                description
                                    "The value indicates the number of bad
                                     message length errors detected.";
                            }

                            leaf malform-tlv {
                                type uint32;
                                description
                                    "The value indicates the number of malformed
                                     TLV value errors detected.";
                            }

                            leaf bad-protocol-version {
                                type uint32;
                                description
                                    "The value indicates the number of bad
                                     protocol version errors detected.";
                            }

                            container hello {
                                description "Enter the hello context";

                                leaf received {
                                    type uint32;
                                    description
                                        "The value indicates number of Hello
                                         messages received.";
                                }

                                leaf sent {
                                    type uint32;
                                    description
                                        "The value indicates number of Hello
                                         messages sent.";
                                }

                            } // container hello

                        } // container statistics

                        list hello-adjacency {
                            key "peer-lsr-id";
                            description "Enter the hello-adjacency list instance";

                            leaf peer-lsr-id {
                                type types-ldp:lsr-id;
                                description "Peer LSR-ID";
                            }

                            leaf up-time {
                                type types-sros:time-interval;
                                units "centiseconds";
                                description "The value indicates the time that this adjacency has been up.";
                            }

                            leaf hold-time-remaining {
                                type uint32;
                                units "seconds";
                                description
                                    "The value indicates the hold time remaining for this Hello
                                     Adjacency. This interval will change when the next Hello
                                     message which corresponds to this Hello Adjacency is received.";
                            }

                            leaf peer-capability-received {
                                type bits {
                                    bit ipv4-prefix-fec                { position 0; }
                                    bit ipv6-prefix-fec                { position 1; }
                                    bit ipv4-p2mp-fec                  { position 2; }
                                    bit ipv6-p2mp-fec                  { position 3; }
                                }
                                description
                                    "The value indicates various capabilities signaled by the peer
                                     LSR in a hello message. A particular capability bit will be
                                     set to 1 when the peer sends capability info in at least one
                                     of its hello message.";
                            }

                            leaf hello-adjacency-index {
                                type uint32 {
                                    range "1..max";
                                }
                                description "The value indicates the Hello Adjacency index.";
                            }

                            leaf entity-index {
                                type uint32 {
                                    range "1..max";
                                }
                                description "The value indicates the Entity index.";
                            }

                            leaf bfd-status {
                                type enumeration {
                                    enum "no-service"                   { value 1; }
                                    enum "in-service"                   { value 2; }
                                    enum "out-of-service"               { value 3; }
                                }
                                description
                                    "The value indicates the BFD operational status for LDP Hello Adjacency/Session.

                                     If the value is 'no-service', BFD is not enabled for LDP Hello Adjacency/Session.
                                     If the value of the object is 'out-of-service', BFD is enabled but it is
                                     down and not running.  If the value of object is 'in-service', BFD is
                                     enabled and it is running.";
                            }

                            container local {
                                description "Enter the local context";

                                leaf lsr-id {
                                    type types-ldp:lsr-id;
                                    description "The value indicates LDP identifier for a specific adjacency";
                                }

                                leaf configuration-sequence-number {
                                    type uint32;
                                    description
                                        "The value indicates the Configuration sequence number that was sent or
                                         received on the Hello when this adjacency started up. This configuration
                                         sequence number changes when there is a change of configuration.";
                                }

                                leaf ip-address {
                                    type types-sros:ip-address;
                                    description "The value indicates the source IP address of the hello.";
                                }

                                leaf timeout {
                                    type uint32;
                                    description
                                        "The value indicates the hello timeout used in the Hellos
                                         sent or received for this specific adjacency.";
                                }

                                container capabilities {
                                    description "Enter the capabilities context";

                                    container ipv4 {
                                        description "Enter the ipv4 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv4

                                    container ipv6 {
                                        description "Enter the ipv6 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv6

                                } // container capabilities

                            } // container local

                            container peer {
                                description "Enter the peer context";

                                leaf configuration-sequence-number {
                                    type uint32;
                                    description
                                        "The value indicates the Configuration sequence number that was sent or
                                         received on the Hello when this adjacency started up. This configuration
                                         sequence number changes when there is a change of configuration.";
                                }

                                leaf ip-address {
                                    type types-sros:ip-address;
                                    description "The value indicates the source IP address of the hello.";
                                }

                                leaf timeout {
                                    type uint32;
                                    description
                                        "The value indicates the hello timeout used in the Hellos
                                         sent or received for this specific adjacency.";
                                }

                                container capabilities {
                                    description "Enter the capabilities context";

                                    container ipv4 {
                                        description "Enter the ipv4 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv4

                                    container ipv6 {
                                        description "Enter the ipv6 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv6

                                } // container capabilities

                            } // container peer

                            container statistics {
                                description "Enter the statistics context";

                                leaf hello-messages-in {
                                    type yang:counter32;
                                    description
                                        "The value indicates the number of Hello messages that
                                         have been received for this adjacency.";
                                }

                                leaf hello-messages-out {
                                    type yang:counter32;
                                    description
                                        "The value  indicates the number of Hello messages that
                                         have been sent for this adjacency.";
                                }

                            } // container statistics

                        } // list hello-adjacency

                    } // container ipv4

                    container ipv6 {
                        description "Enter the ipv6 context";

                        leaf time-since-last-oper-change {
                            type yang:timeticks;
                            description
                                "Time, in centiseconds that the interface has been in current
                                 operational state.";
                        }

                        leaf oper-state {
                            type types-sros:oper-state;
                            description "Current operational status of this interface.";
                        }

                        leaf oper-down-reason {
                            type types-ldp:targ-oper-down-reason-code;
                            description "Reason why this interface is operationally down.";
                        }

                        leaf oper-hello-timeout {
                            type types-sros:time-duration {
                                range "3..65535";
                            }
                            units "seconds";
                            description "Operational hello time (hold time) used by the operational interface.";
                        }

                        leaf backoff-time {
                            type types-ldp:backoff-time {
                                range "1..2592000";
                            }
                            units "seconds";
                            description "Initial value for the backoff interval.";
                        }

                        leaf maximum-backoff-time {
                            type types-ldp:backoff-time;
                            units "seconds";
                            description "Maximum value for the backoff interval.";
                        }

                        leaf local-ip-address {
                            type types-sros:ip-address;
                            description "Local IP address used for Hellos sending.";
                        }

                        container statistics {
                            description "Enter the statistics context";

                            leaf existing-adjacencies {
                                type uint32;
                                description
                                    "The value indicates a count of the total
                                     active adjacencies.";
                            }

                            leaf bad-pdu-length {
                                type uint32;
                                description
                                    "The value indicates the number of bad PDU
                                     length errors detected.";
                            }

                            leaf bad-msg-length {
                                type uint32;
                                description
                                    "The value indicates the number of bad
                                     message length errors detected.";
                            }

                            leaf malform-tlv {
                                type uint32;
                                description
                                    "The value indicates the number of malformed
                                     TLV value errors detected.";
                            }

                            leaf bad-protocol-version {
                                type uint32;
                                description
                                    "The value indicates the number of bad
                                     protocol version errors detected.";
                            }

                            container hello {
                                description "Enter the hello context";

                                leaf received {
                                    type uint32;
                                    description
                                        "The value indicates number of Hello
                                         messages received.";
                                }

                                leaf sent {
                                    type uint32;
                                    description
                                        "The value indicates number of Hello
                                         messages sent.";
                                }

                            } // container hello

                        } // container statistics

                        list hello-adjacency {
                            key "peer-lsr-id";
                            description "Enter the hello-adjacency list instance";

                            leaf peer-lsr-id {
                                type types-ldp:lsr-id;
                                description "Peer LSR-ID";
                            }

                            leaf up-time {
                                type types-sros:time-interval;
                                units "centiseconds";
                                description "The value indicates the time that this adjacency has been up.";
                            }

                            leaf hold-time-remaining {
                                type uint32;
                                units "seconds";
                                description
                                    "The value indicates the hold time remaining for this Hello
                                     Adjacency. This interval will change when the next Hello
                                     message which corresponds to this Hello Adjacency is received.";
                            }

                            leaf peer-capability-received {
                                type bits {
                                    bit ipv4-prefix-fec                { position 0; }
                                    bit ipv6-prefix-fec                { position 1; }
                                    bit ipv4-p2mp-fec                  { position 2; }
                                    bit ipv6-p2mp-fec                  { position 3; }
                                }
                                description
                                    "The value indicates various capabilities signaled by the peer
                                     LSR in a hello message. A particular capability bit will be
                                     set to 1 when the peer sends capability info in at least one
                                     of its hello message.";
                            }

                            leaf hello-adjacency-index {
                                type uint32 {
                                    range "1..max";
                                }
                                description "The value indicates the Hello Adjacency index.";
                            }

                            leaf entity-index {
                                type uint32 {
                                    range "1..max";
                                }
                                description "The value indicates the Entity index.";
                            }

                            leaf bfd-status {
                                type enumeration {
                                    enum "no-service"                   { value 1; }
                                    enum "in-service"                   { value 2; }
                                    enum "out-of-service"               { value 3; }
                                }
                                description
                                    "The value indicates the BFD operational status for LDP Hello Adjacency/Session.

                                     If the value is 'no-service', BFD is not enabled for LDP Hello Adjacency/Session.
                                     If the value of the object is 'out-of-service', BFD is enabled but it is
                                     down and not running.  If the value of object is 'in-service', BFD is
                                     enabled and it is running.";
                            }

                            container local {
                                description "Enter the local context";

                                leaf lsr-id {
                                    type types-ldp:lsr-id;
                                    description "The value indicates LDP identifier for a specific adjacency";
                                }

                                leaf configuration-sequence-number {
                                    type uint32;
                                    description
                                        "The value indicates the Configuration sequence number that was sent or
                                         received on the Hello when this adjacency started up. This configuration
                                         sequence number changes when there is a change of configuration.";
                                }

                                leaf ip-address {
                                    type types-sros:ip-address;
                                    description "The value indicates the source IP address of the hello.";
                                }

                                leaf timeout {
                                    type uint32;
                                    description
                                        "The value indicates the hello timeout used in the Hellos
                                         sent or received for this specific adjacency.";
                                }

                                container capabilities {
                                    description "Enter the capabilities context";

                                    container ipv4 {
                                        description "Enter the ipv4 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv4

                                    container ipv6 {
                                        description "Enter the ipv6 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv6

                                } // container capabilities

                            } // container local

                            container peer {
                                description "Enter the peer context";

                                leaf configuration-sequence-number {
                                    type uint32;
                                    description
                                        "The value indicates the Configuration sequence number that was sent or
                                         received on the Hello when this adjacency started up. This configuration
                                         sequence number changes when there is a change of configuration.";
                                }

                                leaf ip-address {
                                    type types-sros:ip-address;
                                    description "The value indicates the source IP address of the hello.";
                                }

                                leaf timeout {
                                    type uint32;
                                    description
                                        "The value indicates the hello timeout used in the Hellos
                                         sent or received for this specific adjacency.";
                                }

                                container capabilities {
                                    description "Enter the capabilities context";

                                    container ipv4 {
                                        description "Enter the ipv4 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv4

                                    container ipv6 {
                                        description "Enter the ipv6 context";

                                        leaf p2mp {
                                            type boolean;
                                            description
                                                "The value  indicates whether the local peer or remote
                                                 peer supports traffic exchange for IPv4 or IPv6 P2MP FECs.";
                                        }

                                        leaf prefix {
                                            type boolean;
                                            description
                                                "The value of indicates whether the local peer or remote
                                                 peer supports traffic exchange for IPv4  or IPv6 Prefix FECs.";
                                        }

                                    } // container ipv6

                                } // container capabilities

                            } // container peer

                            container statistics {
                                description "Enter the statistics context";

                                leaf hello-messages-in {
                                    type yang:counter32;
                                    description
                                        "The value indicates the number of Hello messages that
                                         have been received for this adjacency.";
                                }

                                leaf hello-messages-out {
                                    type yang:counter32;
                                    description
                                        "The value  indicates the number of Hello messages that
                                         have been sent for this adjacency.";
                                }

                            } // container statistics

                        } // list hello-adjacency

                    } // container ipv6

                } // list interface

            } // container interface-parameters

            container targeted-session {
                description "Enter the targeted-session context";

                list peer {
                    key "ip-address";
                    description "Enter the peer list instance";

                    leaf ip-address {
                        type types-sros:ip-address;
                        description "IP address of the LDP peer";
                    }

                    leaf creator {
                        type enumeration {
                            enum "manual"                       { value 1; }
                            enum "template"                     { value 2; }
                            enum "sdp"                          { value 3; }
                            enum "autotx"                       { value 4; }
                            enum "autorx"                       { value 5; }
                        }
                        description "The value indicates the creator of this peer entry.";
                    }

                    leaf backoff-time {
                        type types-ldp:backoff-time {
                            range "1..2592000";
                        }
                        description "The value specifies the initial value for the backoff interval.";
                    }

                    leaf max-backoff-time {
                        type types-ldp:backoff-time;
                        description "The value specifies the maximum value for the backoff interval.";
                    }

                    leaf auto-create {
                        type boolean;
                        description "The value indicates whether or not the peer entry was automatically created.";
                    }

                    leaf local-ip-address {
                        type types-sros:ip-address;
                        description "The value indicates the local IP address used in Hellos sent.";
                    }

                    leaf oper-down-reason {
                        type types-ldp:targ-oper-down-reason-code;
                        description "The value indicates the operational down reason for the peer entry.";
                    }

                    leaf oper-hello-timeout {
                        type uint32 {
                            range "3..65535";
                        }
                        units "seconds";
                        description
                            "The value indicates the operational hello time also known as hold time used by the operational targeted
                             peer. It is the time interval that LDP waits before declaring a neighbor to be down.";
                    }

                    leaf oper-state {
                        type types-sros:oper-state;
                        description "The value indicates the current operational state of this peer instance.";
                    }

                    leaf template-name {
                        type types-sros:named-item-or-empty;
                        description
                            "The value specifies the template name that created this row. This object has valid value when
                             creator has value of template.";
                    }

                    leaf time-since-last-oper-change {
                        type types-sros:time-interval;
                        description "The value indicates the time, in centiseconds, that the targeted peer has been in current operational state.";
                    }

                    container statistics {
                        description "Enter the statistics context";

                        leaf existing-adjacencies {
                            type uint32;
                            description
                                "The value indicates a count of the total
                                 active adjacencies.";
                        }

                        leaf bad-pdu-length {
                            type uint32;
                            description
                                "The value indicates the number of bad PDU
                                 length errors detected.";
                        }

                        leaf bad-msg-length {
                            type uint32;
                            description
                                "The value indicates the number of bad
                                 message length errors detected.";
                        }

                        leaf malform-tlv {
                            type uint32;
                            description
                                "The value indicates the number of malformed
                                 TLV value errors detected.";
                        }

                        leaf bad-protocol-version {
                            type uint32;
                            description
                                "The value indicates the number of bad
                                 protocol version errors detected.";
                        }

                        container hello {
                            description "Enter the hello context";

                            leaf received {
                                type uint32;
                                description
                                    "The value indicates number of Hello
                                     messages received.";
                            }

                            leaf sent {
                                type uint32;
                                description
                                    "The value indicates number of Hello
                                     messages sent.";
                            }

                        } // container hello

                    } // container statistics

                    container hello-adjacency {
                        description "Enter the hello-adjacency context";

                        leaf peer-lsr-id {
                            type types-ldp:lsr-id;
                            description "Peer LSR-ID";
                        }

                        leaf up-time {
                            type types-sros:time-interval;
                            units "centiseconds";
                            description "The value indicates the time that this adjacency has been up.";
                        }

                        leaf hold-time-remaining {
                            type uint32;
                            units "seconds";
                            description
                                "The value indicates the hold time remaining for this Hello
                                 Adjacency. This interval will change when the next Hello
                                 message which corresponds to this Hello Adjacency is received.";
                        }

                        leaf peer-capability-received {
                            type bits {
                                bit ipv4-prefix-fec                { position 0; }
                                bit ipv6-prefix-fec                { position 1; }
                                bit ipv4-p2mp-fec                  { position 2; }
                                bit ipv6-p2mp-fec                  { position 3; }
                            }
                            description
                                "The value indicates various capabilities signaled by the peer
                                 LSR in a hello message. A particular capability bit will be
                                 set to 1 when the peer sends capability info in at least one
                                 of its hello message.";
                        }

                        leaf hello-adjacency-index {
                            type uint32 {
                                range "1..max";
                            }
                            description "The value indicates the Hello Adjacency index.";
                        }

                        leaf entity-index {
                            type uint32 {
                                range "1..max";
                            }
                            description "The value indicates the Entity index.";
                        }

                        container local {
                            description "Enter the local context";

                            leaf lsr-id {
                                type types-ldp:lsr-id;
                                description "The value indicates LDP identifier for a specific adjacency";
                            }

                            leaf configuration-sequence-number {
                                type uint32;
                                description
                                    "The value indicates the Configuration sequence number that was sent or
                                     received on the Hello when this adjacency started up. This configuration
                                     sequence number changes when there is a change of configuration.";
                            }

                            leaf ip-address {
                                type types-sros:ip-address;
                                description "The value indicates the source IP address of the hello.";
                            }

                            leaf timeout {
                                type uint32;
                                description
                                    "The value indicates the hello timeout used in the Hellos
                                     sent or received for this specific adjacency.";
                            }

                            container capabilities {
                                description "Enter the capabilities context";

                                container ipv4 {
                                    description "Enter the ipv4 context";

                                    leaf p2mp {
                                        type boolean;
                                        description
                                            "The value  indicates whether the local peer or remote
                                             peer supports traffic exchange for IPv4 or IPv6 P2MP FECs.";
                                    }

                                    leaf prefix {
                                        type boolean;
                                        description
                                            "The value of indicates whether the local peer or remote
                                             peer supports traffic exchange for IPv4  or IPv6 Prefix FECs.";
                                    }

                                } // container ipv4

                                container ipv6 {
                                    description "Enter the ipv6 context";

                                    leaf p2mp {
                                        type boolean;
                                        description
                                            "The value  indicates whether the local peer or remote
                                             peer supports traffic exchange for IPv4 or IPv6 P2MP FECs.";
                                    }

                                    leaf prefix {
                                        type boolean;
                                        description
                                            "The value of indicates whether the local peer or remote
                                             peer supports traffic exchange for IPv4  or IPv6 Prefix FECs.";
                                    }

                                } // container ipv6

                            } // container capabilities

                        } // container local

                        container peer {
                            description "Enter the peer context";

                            leaf configuration-sequence-number {
                                type uint32;
                                description
                                    "The value indicates the Configuration sequence number that was sent or
                                     received on the Hello when this adjacency started up. This configuration
                                     sequence number changes when there is a change of configuration.";
                            }

                            leaf ip-address {
                                type types-sros:ip-address;
                                description "The value indicates the source IP address of the hello.";
                            }

                            leaf timeout {
                                type uint32;
                                description
                                    "The value indicates the hello timeout used in the Hellos
                                     sent or received for this specific adjacency.";
                            }

                            container capabilities {
                                description "Enter the capabilities context";

                                container ipv4 {
                                    description "Enter the ipv4 context";

                                    leaf p2mp {
                                        type boolean;
                                        description
                                            "The value  indicates whether the local peer or remote
                                             peer supports traffic exchange for IPv4 or IPv6 P2MP FECs.";
                                    }

                                    leaf prefix {
                                        type boolean;
                                        description
                                            "The value of indicates whether the local peer or remote
                                             peer supports traffic exchange for IPv4  or IPv6 Prefix FECs.";
                                    }

                                } // container ipv4

                                container ipv6 {
                                    description "Enter the ipv6 context";

                                    leaf p2mp {
                                        type boolean;
                                        description
                                            "The value  indicates whether the local peer or remote
                                             peer supports traffic exchange for IPv4 or IPv6 P2MP FECs.";
                                    }

                                    leaf prefix {
                                        type boolean;
                                        description
                                            "The value of indicates whether the local peer or remote
                                             peer supports traffic exchange for IPv4  or IPv6 Prefix FECs.";
                                    }

                                } // container ipv6

                            } // container capabilities

                        } // container peer

                        container statistics {
                            description "Enter the statistics context";

                            leaf hello-messages-in {
                                type yang:counter32;
                                description
                                    "The value indicates the number of Hello messages that
                                     have been received for this adjacency.";
                            }

                            leaf hello-messages-out {
                                type yang:counter32;
                                description
                                    "The value  indicates the number of Hello messages that
                                     have been sent for this adjacency.";
                            }

                        } // container statistics

                    } // container hello-adjacency

                } // list peer

                list peer-template {
                    key "template-name";
                    description "Enter the peer-template list instance";

                    leaf template-name {
                        type types-sros:named-item;
                        description "Name for the targeted peer template";
                    }

                    leaf create-time {
                        type types-sros:time-interval;
                        description
                            "The value indicates the sysUpTime when this LDP peer
                             template was created.";
                    }

                    leaf template-index {
                        type yang:counter64;
                        description
                            "The value of template-index indicates a unique value greater
                             than zero which identifies this template for this virtual router in the
                             Nokia SROS system. It is a unique value among entries within
                             the same value of vRtrID.

                             The value of template-index represents the order in which the
                             templates are created. This is also the order in which configuration
                             will be saved. In the running system, this value may have gaps as
                             templates are added and deleted. This is volatile object hence, it is
                             not persistent across reboot.
                             ";
                    }

                } // list peer-template

                list peer-template-map {
                    key "template-map-name";
                    description "Enter the peer-template-map list instance";

                    leaf template-map-name {
                        type leafref {
                            path "../../peer-template/template-name";
                        }
                        description "Name to identify the targeted peer template";
                    }

                    leaf create-time {
                        type types-sros:time-interval;
                        description
                            "The value indicates the sysUpTime when this LDP peer
                             template was created.";
                    }

                    leaf template-index {
                        type yang:counter64;
                        description
                            "The value of template-index indicates a unique value greater
                             than zero which identifies this template for this virtual router in the
                             Nokia SROS system. It is a unique value among entries within
                             the same value of vRtrID.

                             The value of template-index represents the order in which the
                             templates are created. This is also the order in which configuration
                             will be saved. In the running system, this value may have gaps as
                             templates are added and deleted. This is volatile object hence, it is
                             not persistent across reboot.
                             ";
                    }

                } // list peer-template-map

            } // container targeted-session

            list session {
                key "peer-lsr-id";
                description "Enter the session list instance";

                leaf peer-lsr-id {
                    type types-ldp:lsr-id;
                    description "Peer LSR-ID";
                }

                leaf local-lsr-id {
                    type types-ldp:lsr-id;
                    description "The value indicates the local LDP identifier for the LDP Session.";
                }

                leaf up-time {
                    type yang:timeticks {
                        range "0..2147483647";
                    }
                    units "centiseconds";
                    description "The value indicates the time since the Session was established.";
                }

                leaf adjacency-type {
                    type enumeration {
                        enum "link"                         { value 1; }
                        enum "targeted"                     { value 2; }
                        enum "both"                         { value 3; }
                    }
                    description "The value indicates the adjacency type supporting this LDP Session.";
                }

                leaf state {
                    type enumeration {
                        enum "nonexistent"                  { value 1; }
                        enum "initialized"                  { value 2; }
                        enum "openrec"                      { value 3; }
                        enum "opensent"                     { value 4; }
                        enum "operational"                  { value 5; }
                    }
                    description
                        "The value indicates the current state of the LDP Session.  All of the
                         states 1 - 5 are based on the state machine for Session negotiation
                         behavior.";
                }

                leaf entity-index {
                    type uint32 {
                        range "1..4294967295";
                    }
                    description "The value indicates the Entity index for the LDP entity represented in this Session.";
                }

                leaf loop-detect-for-pv {
                    type boolean;
                    description
                        "The value indicates whether loop detection based on path vectors is disabled or enabled
                         for this LDP session.

                         If this object has a value of false, then loop detection is disabled.
                         Otherwise, if this object has a value of true, then loop detection based on
                         path vectors is enabled.";
                }

                leaf path-vector-limit {
                    type uint32 {
                        range "0..255";
                    }
                    description
                        "If the value of loop-detect-for-pv for this entry is 'true', then this
                         value represents the Path Vector Limit for this LDP Session.

                         If the value of loop-detect-for-pv for this entry is 'disabled', then the 
                         value of path-vector-limit will be 0 (zero).";
                }

                leaf protocol-version {
                    type uint32;
                    description
                        "The value specifies the version of the LDP protocol. A value of
                         zero (0) indicates that the version of the protocol is unknown.";
                }

                leaf max-pdu-length {
                    type uint32 {
                        range "1..65535";
                    }
                    description
                        "The value indicates the maximum allowable length for LDP PDUs for this Session.
                         This value may have been negotiated during Session Initialization.";
                }

                leaf label-distribution-method {
                    type types-ldp:distribution-method;
                    description "The value indicates the label distribution method used for this LDP Session.";
                }

                leaf oper-max-fec-threshold {
                    type uint32;
                    description "The value indicates the operational percentage of session-parameters/fec-limit/threshold. ";
                }

                leaf advertise {
                    type enumeration {
                        enum "address"                      { value 1; }
                        enum "service"                      { value 2; }
                        enum "address-and-service"          { value 3; }
                    }
                    description "The value indicates the type of FECs that will be transported by the Session.";
                }

                leaf bfd-status {
                    type enumeration {
                        enum "no-service"                   { value 1; }
                        enum "in-service"                   { value 2; }
                        enum "out-of-service"               { value 3; }
                    }
                    description
                        "The value indicates the BFD operational status for LDP Hello Adjacency/Session.

                         If the value is 'no-service', BFD is not enabled for LDP Hello Adjacency/Session.
                         If the value of the object is 'out-of-service', BFD is enabled but it is
                         down and not running.  If the value of object is 'in-service', BFD is
                         enabled and it is running.";
                }

                leaf community {
                    type types-sros:named-item-or-empty;
                    description "Oper community string associated with a session to a given peer.";
                }

                leaf local-capabilities {
                    type types-ldp:capabilities;
                    description "The value indicates various capabilities supported by the local entity of this Session";
                }

                leaf peer-capabilities {
                    type types-ldp:capabilities;
                    description "The value indicates various capabilities supported by the peer entity of this Session";
                }

                leaf peer-capabilities-received {
                    type types-ldp:capabilities;
                    description
                        "The value indicates various capabilities signaled by the peer LSR. A capability bit
                         for ipv4-prefix-fec, ipv6-prefix-fec, fec-128 and fec-129 will be set to 1
                         when there is at least one capability message sent by peer LSR for a given capability
                         type.  For rest of the other capabilities, the bit will not be set to 1 even if
                         the peer LSR has sent capability message for a particular capability type.";
                }

                leaf overload-sent {
                    type types-ldp:fec-type-bits;
                    description
                        "The value indicates various FEC types for which LSR Overload Notification has been
                         sent to the LDP peer.";
                }

                leaf overload-received {
                    type types-ldp:fec-type-bits;
                    description
                        "The value indicates various FEC types for which LSR Overload Notification has been
                         received from the LDP peer.";
                }

                leaf end-of-lib-sent {
                    type types-ldp:fec-type-bits;
                    description
                        "The value indicates whether end of Label Information Base (LIB) notification has
                         been sent to the LDP peer. A particular FEC type bit will be set to 1 when there is
                         at least one end of LIB notification sent to the LDP peer for a given FEC types.";
                }

                leaf end-of-lib-received {
                    type types-ldp:fec-type-bits;
                    description
                        "The value indicates whether end of Label Information Base (LIB) notification has
                         been received from the LDP peer. A particular bit will be set to 1 when there is
                         at least one end of LIB notification received from the LDP peer for a given FEC types.";
                }

                container keepalive {
                    description "Enter the keepalive context";

                    leaf time-remaining {
                        type uint32;
                        units "seconds";
                        description "The value indicates the keep-alive hold time remaining for this LDP Session.";
                    }

                    leaf local-timeout {
                        type types-sros:time-duration {
                            range "3..65535";
                        }
                        description "The value indicates the keep-alive timeout used locally for the LDP Session.";
                    }

                    leaf peer-timeout {
                        type types-sros:time-duration {
                            range "3..65535";
                        }
                        description "The value indicates the keep-alive timeout used at the remote end of the LDP Session.";
                    }

                } // container keepalive

                container connection {
                    description "Enter the connection context";

                    container local {
                        description "Enter the local context";

                        leaf ip-address {
                            type types-sros:ip-address;
                            description "The value indicates the IP address used for the LDP Session.";
                        }

                        leaf udp-port {
                            type uint32 {
                                range "0..65535";
                            }
                            description "The value indicates the UDP port used for the LDP discovery.";
                        }

                        leaf tcp-port {
                            type uint32 {
                                range "0..65535";
                            }
                            description "The value indicates the TCP port used for the LDP Session.";
                        }

                    } // container local

                    container peer {
                        description "Enter the peer context";

                        leaf ip-address {
                            type types-sros:ip-address;
                            description "The value indicates the IP address used for the LDP Session.";
                        }

                        leaf udp-port {
                            type uint32 {
                                range "0..65535";
                            }
                            description "The value indicates the UDP port used for the LDP discovery.";
                        }

                        leaf tcp-port {
                            type uint32 {
                                range "0..65535";
                            }
                            description "The value indicates the TCP port used for the LDP Session.";
                        }

                    } // container peer

                } // container connection

                container graceful-restart {
                    description "Enter the graceful-restart context";

                    leaf number-of-restart {
                        type yang:counter32;
                        description
                            "The value indicates the number of times graceful restart helper was initiated
                             for this Session.";
                    }

                    leaf last-restart-time {
                        type yang:date-and-time;
                        description "The value indicates the last time graceful restart helper was initiated.";
                    }

                    leaf ft-reconnect-time-remaining {
                        type uint32;
                        units "seconds";
                        description
                            "The value indicates the amount of time left before Session's Fault Tolerant(FT)
                             reconnect timeout expires. This value is set to lesser of the neighbor advertised
                             FT reconnect timeout and the local reconnect timeout.";
                    }

                    leaf ft-recovery-time-remaining {
                        type uint32;
                        units "seconds";
                        description
                            "The value indicates the amount of time left before Session's Fault Tolerant(FT)
                             recovery timeout expires. This value is set to lesser of the neighbor advertised FT
                             recovery timeout and the local recovery timeout.";
                    }

                    container local {
                        description "Enter the local context";

                        leaf helper-state {
                            type boolean;
                            description
                                "The value indicates whether the local entity of this Session is graceful
                                 restart helper capable or not.";
                        }

                        leaf reconnect-time {
                            type uint32;
                            units "seconds";
                            description "The value indicates the Session's local Fault Tolerant(FT) Reconnect Timeout.";
                        }

                        leaf recovery-time {
                            type uint32;
                            units "seconds";
                            description "The value indicates the Session's local Fault Tolerant(FT) recovery timeout.";
                        }

                    } // container local

                    container peer {
                        description "Enter the peer context";

                        leaf state {
                            type boolean;
                            description
                                "The value indicates whether the peer entity of this Session is capable of
                                 supporting graceful restart.";
                        }

                        leaf reconnect-time {
                            type uint32;
                            units "seconds";
                            description "The value indicates the Session's peer Fault Tolerant(FT) Reconnect Timeout.";
                        }

                        leaf recovery-time {
                            type uint32;
                            units "seconds";
                            description "The value indicates the Session's peer Fault Tolerant(FT) recovery timeout.";
                        }

                    } // container peer

                } // container graceful-restart

                container statistics {
                    description "Enter the statistics context";

                    leaf targeted-adjacencies {
                        type yang:counter32;
                        description "The value indicates the number of targeted adjacencies on this Session.";
                    }

                    leaf link-adjacencies {
                        type yang:counter32;
                        description "The value indicates the number of link adjacencies on this Session.";
                    }

                    container messages {
                        description "Enter the messages context";

                        container sent {
                            description "Enter the sent context";

                            leaf hello {
                                type yang:counter32;
                                description
                                    "The value indicates the number of Hello Messages that have been sent/received on
                                     this Session.";
                            }

                            leaf keepalive {
                                type yang:counter32;
                                description
                                    "The value indicates the number of Keepalive Messages that have been sent/received
                                     on this Session.";
                            }

                            leaf initialization {
                                type yang:counter32;
                                description
                                    "The value indicates the number of Initialization Messages that have been
                                     sent/received on this Session.";
                            }

                            leaf address {
                                type yang:counter32;
                                description
                                    "The value indicates the number of Address Messages that have been sent/received
                                     on this Session.";
                            }

                            leaf address-withdraw {
                                type yang:counter32;
                                description
                                    "The value indicates the number of Address Withdraw Messages that have been
                                     sent/received on this Session.";
                            }

                            leaf notification {
                                type yang:counter32;
                                description
                                    "The value indicates the number of Notification Messages that have been
                                     sent/received on this Session.";
                            }

                            leaf capability {
                                type yang:counter32;
                                description
                                    "The value indicates the number of Capability Messages that have been sent/received
                                     on this Session.";
                            }

                            container label {
                                description "Enter the label context";

                                leaf mapping {
                                    type yang:counter32;
                                    description
                                        "The value indicates the number of Label Mapping Messages that have been
                                         sent/received on this Session.";
                                }

                                leaf request {
                                    type yang:counter32;
                                    description
                                        "The value indicates the number of Label Request Messages that have been
                                         sent/received on this Session.";
                                }

                                leaf release {
                                    type yang:counter32;
                                    description
                                        "The value indicates the number of Label Release Messages that have been
                                         sent/received on this Session.";
                                }

                                leaf withdraw {
                                    type yang:counter32;
                                    description
                                        "The value indicates the number of Label Withdraw Messages that have been
                                         sent/received on this Session.";
                                }

                                leaf abort {
                                    type yang:counter32;
                                    description
                                        "The value indicates the number of Label Abort Messages that have been
                                         sent/received on this Session.";
                                }

                            } // container label

                        } // container sent

                        container received {
                            description "Enter the received context";

                            leaf hello {
                                type yang:counter32;
                                description
                                    "The value indicates the number of Hello Messages that have been sent/received on
                                     this Session.";
                            }

                            leaf keepalive {
                                type yang:counter32;
                                description
                                    "The value indicates the number of Keepalive Messages that have been sent/received
                                     on this Session.";
                            }

                            leaf initialization {
                                type yang:counter32;
                                description
                                    "The value indicates the number of Initialization Messages that have been
                                     sent/received on this Session.";
                            }

                            leaf address {
                                type yang:counter32;
                                description
                                    "The value indicates the number of Address Messages that have been sent/received
                                     on this Session.";
                            }

                            leaf address-withdraw {
                                type yang:counter32;
                                description
                                    "The value indicates the number of Address Withdraw Messages that have been
                                     sent/received on this Session.";
                            }

                            leaf notification {
                                type yang:counter32;
                                description
                                    "The value indicates the number of Notification Messages that have been
                                     sent/received on this Session.";
                            }

                            leaf capability {
                                type yang:counter32;
                                description
                                    "The value indicates the number of Capability Messages that have been sent/received
                                     on this Session.";
                            }

                            container label {
                                description "Enter the label context";

                                leaf mapping {
                                    type yang:counter32;
                                    description
                                        "The value indicates the number of Label Mapping Messages that have been
                                         sent/received on this Session.";
                                }

                                leaf request {
                                    type yang:counter32;
                                    description
                                        "The value indicates the number of Label Request Messages that have been
                                         sent/received on this Session.";
                                }

                                leaf release {
                                    type yang:counter32;
                                    description
                                        "The value indicates the number of Label Release Messages that have been
                                         sent/received on this Session.";
                                }

                                leaf withdraw {
                                    type yang:counter32;
                                    description
                                        "The value indicates the number of Label Withdraw Messages that have been
                                         sent/received on this Session.";
                                }

                                leaf abort {
                                    type yang:counter32;
                                    description
                                        "The value indicates the number of Label Abort Messages that have been
                                         sent/received on this Session.";
                                }

                            } // container label

                        } // container received

                    } // container messages

                    container number-of-addresses {
                        description "Enter the number-of-addresses context";

                        container sent {
                            description "Enter the sent context";

                            leaf ipv4 {
                                type yang:counter32;
                                description "The value indicates the number of IPv4 local addresses sent/received on this Session.";
                            }

                            leaf ipv6 {
                                type yang:counter32;
                                description "The value indicates the number of IPv6 local addresses sent/received on this Session.";
                            }

                        } // container sent

                        container received {
                            description "Enter the received context";

                            leaf ipv4 {
                                type yang:counter32;
                                description "The value indicates the number of IPv4 local addresses sent/received on this Session.";
                            }

                            leaf ipv6 {
                                type yang:counter32;
                                description "The value indicates the number of IPv6 local addresses sent/received on this Session.";
                            }

                        } // container received

                    } // container number-of-addresses

                    container fecs {
                        description "Enter the fecs context";

                        container sent {
                            description "Enter the sent context";

                            leaf ipv4-prefix {
                                type yang:counter32;
                                description "The value indicates the number of IPv4 prefix FECs sent/received on this Session.";
                            }

                            leaf ipv6-prefix {
                                type yang:counter32;
                                description "The value indicates the number of IPv6 prefix FECs sent/received on this Session.";
                            }

                            leaf ipv4-p2mp {
                                type yang:counter32;
                                description "The value indicates the number of IPv4 P2MP FECs sent/received on this Session.";
                            }

                            leaf ipv6-p2mp {
                                type yang:counter32;
                                description "The value indicates the number of IPv6 P2MP FECs sent/received on this Session.";
                            }

                            leaf fec128 {
                                type yang:counter32;
                                description "The value indicates the number of service FEC 128 sent/received on this Session.";
                            }

                            leaf fec129 {
                                type yang:counter32;
                                description "The value indicates the number of service FEC 129 sent/received on this Session.";
                            }

                        } // container sent

                        container received {
                            description "Enter the received context";

                            leaf ipv4-prefix {
                                type yang:counter32;
                                description "The value indicates the number of IPv4 prefix FECs sent/received on this Session.";
                            }

                            leaf ipv6-prefix {
                                type yang:counter32;
                                description "The value indicates the number of IPv6 prefix FECs sent/received on this Session.";
                            }

                            leaf ipv4-p2mp {
                                type yang:counter32;
                                description "The value indicates the number of IPv4 P2MP FECs sent/received on this Session.";
                            }

                            leaf ipv6-p2mp {
                                type yang:counter32;
                                description "The value indicates the number of IPv6 P2MP FECs sent/received on this Session.";
                            }

                            leaf fec128 {
                                type yang:counter32;
                                description "The value indicates the number of service FEC 128 sent/received on this Session.";
                            }

                            leaf fec129 {
                                type yang:counter32;
                                description "The value indicates the number of service FEC 129 sent/received on this Session.";
                            }

                        } // container received

                    } // container fecs

                } // container statistics

                container local-addresses {
                    description "Enter the local-addresses context";

                    list sent-addresses {
                        key "ip-address";
                        description "Enter the sent-addresses list instance";

                        leaf ip-address {
                            type types-sros:ip-address;
                            description "Session IP address.";
                        }

                    } // list sent-addresses

                    list received-addresses {
                        key "ip-address";
                        description "Enter the received-addresses list instance";

                        leaf ip-address {
                            type types-sros:ip-address;
                            description "Session IP address.";
                        }

                    } // list received-addresses

                } // container local-addresses

            } // list session

            container bindings {
                description "Enter the bindings context";

                list prefixes {
                    key "fec-type ip-prefix peer-lsr-id";
                    description "Enter the prefixes list instance";

                    leaf fec-type {
                        type types-ldp:fec-type;
                        description "The value specifies the FEC type of this address FEC.";
                    }

                    leaf ip-prefix {
                        type types-sros:ip-prefix;
                        description "The value specifies the FEC IP Prefix.";
                    }

                    leaf peer-lsr-id {
                        type types-ldp:lsr-id;
                        description "Peer LSR-ID";
                    }

                    leaf flags {
                        type types-ldp:fec-flags;
                        description "The bit flags indicate the characteristics of the FEC.";
                    }

                    leaf community {
                        type types-sros:named-item-or-empty;
                        description "Oper community string associated with a session to a given peer.";
                    }

                    list in-label {
                        key "id";
                        description "Enter the in-label list instance";

                        leaf id {
                            type uint32;
                            description "The value indicates the label number of the exchanged label.";
                        }

                        leaf label {
                            type uint32;
                            description "The value indicates the label exchanged.";
                        }

                        leaf status {
                            type types-ldp:label-status;
                            description "The value indicates the status of the label.";
                        }

                    } // list in-label

                    list out-label {
                        key "id";
                        description "Enter the out-label list instance";

                        leaf id {
                            type uint32;
                            description "The value indicates the label number of the exchanged label.";
                        }

                        leaf label {
                            type uint32;
                            description "The value indicates the label exchanged.";
                        }

                        leaf status {
                            type types-ldp:label-status;
                            description "The value indicates the status of the label.";
                        }

                    } // list out-label

                } // list prefixes

                list p2mp {
                    key "root-address opaque-type opaque-len opaque-value peer-lsr-id";
                    description "Enter the p2mp list instance";

                    leaf root-address {
                        type types-sros:ip-address;
                        description "The value indicates the ip address of the root for this P2MP FEC.";
                    }

                    leaf opaque-type {
                        type uint32;
                        description "The value indicates the type of a Point-Multi-Point Opaque Value Element.";
                    }

                    leaf opaque-len {
                        type uint32;
                        description "The value indicates the length of a Point-Multi-Point Opaque Value Element.";
                    }

                    leaf opaque-value {
                        type string;
                        description "The value indicates the value of a Point-Multi-Point Opaque Value Element.";
                    }

                    leaf peer-lsr-id {
                        type types-ldp:lsr-id;
                        description "Peer LSR-ID";
                    }

                    leaf decoded-opaque-type {
                        type enumeration {
                            enum "unknown"                      { value 0; }
                            enum "generic"                      { value 1; }
                            enum "ssm"                          { value 2; }
                            enum "vpn-ssm"                      { value 3; }
                            enum "ssm-recursive"                { value 4; }
                            enum "generic-vpn-recursive"        { value 5; }
                            enum "generic-grt-recursive"        { value 6; }
                        }
                        description "Decoded opaque type.";
                    }

                    leaf flags {
                        type types-ldp:fec-flags;
                        description "The bit flags indicate the characteristics of the FEC.";
                    }

                    leaf tunnel-interface-id {
                        type uint32;
                        description "The value indicates the tunnel interface identifier for this P2MP FEC.";
                    }

                    leaf mtu {
                        type uint32;
                        description
                            "The value indicates the maximum transfer unit for payloads represented by
                             this FEC";
                    }

                    leaf metric {
                        type uint32;
                        description
                            "The value indicates the relative cost of the tunnel represented by this
                             FEC";
                    }

                    container decoded-opaque-value {
                        description "Enter the decoded-opaque-value context";

                        leaf p2mp-id {
                            type uint32;
                            description "P2MP-Id";
                        }

                        leaf source {
                            type types-sros:ip-address;
                            description "Source IP address.";
                        }

                        leaf group {
                            type types-sros:ip-address;
                            description "Group IP address.";
                        }

                        leaf route-distinguisher {
                            type types-services:vpn-route-distinguisher;
                            description "VPN Route Distinguisher.";
                        }

                        leaf inner-root {
                            type types-sros:ip-address;
                            description "Inner root IP address";
                        }

                    } // container decoded-opaque-value

                    list in-label {
                        key "id";
                        description "Enter the in-label list instance";

                        leaf id {
                            type uint32;
                            description "The value indicates the label number of the exchanged label.";
                        }

                        leaf label {
                            type uint32;
                            description "The value indicates the label exchanged.";
                        }

                        leaf status {
                            type types-ldp:label-status;
                            description "The value indicates the status of the label.";
                        }

                    } // list in-label

                    list out-label {
                        key "id";
                        description "Enter the out-label list instance";

                        leaf id {
                            type uint32;
                            description "The value indicates the label number of the exchanged label.";
                        }

                        leaf interface-name {
                            type types-sros:named-item-or-empty;
                            description "The value specifies the interface name for egress label.";
                        }

                        leaf next-hop {
                            type types-sros:ip-address;
                            description "The value specifies the next hop IP address for egress label.";
                        }

                        leaf lsp-name {
                            type types-sros:named-item-64-or-empty;
                            description "The value specifies the LSP name associated with egress label.";
                        }

                        leaf label {
                            type uint32;
                            description "The value indicates the label exchanged.";
                        }

                        leaf status {
                            type types-ldp:label-status;
                            description "The value indicates the status of the label.";
                        }

                    } // list out-label

                } // list p2mp

                list p2mp-stitching {
                    key "root-address opaque-type opaque-len opaque-value stitch-type";
                    description "Enter the p2mp-stitching list instance";

                    leaf root-address {
                        type types-sros:ip-address;
                        description "The value indicates the ip address of the root for this P2MP FEC.";
                    }

                    leaf opaque-type {
                        type uint32;
                        description "The value indicates the type of a Point-Multi-Point Opaque Value Element.";
                    }

                    leaf opaque-len {
                        type uint32;
                        description "The value indicates the length of a Point-Multi-Point Opaque Value Element.";
                    }

                    leaf opaque-value {
                        type string;
                        description "The value indicates the value of a Point-Multi-Point Opaque Value Element.";
                    }

                    leaf stitch-type {
                        type enumeration {
                            enum "lower-fec"                    { value 1; }
                            enum "primary-upper-fec"            { value 2; }
                            enum "mbb-upper-fec"                { value 3; }
                            enum "backup-upper-fec"             { value 4; }
                        }
                        description "The value specifies the P2MP bindings stitch type.";
                    }

                    leaf decoded-opaque-type {
                        type enumeration {
                            enum "unknown"                      { value 0; }
                            enum "generic"                      { value 1; }
                            enum "ssm"                          { value 2; }
                            enum "vpn-ssm"                      { value 3; }
                            enum "ssm-recursive"                { value 4; }
                            enum "generic-vpn-recursive"        { value 5; }
                            enum "generic-grt-recursive"        { value 6; }
                        }
                        description "Decoded opaque type.";
                    }

                    container decoded-opaque-value {
                        description "Enter the decoded-opaque-value context";

                        leaf p2mp-id {
                            type uint32;
                            description "P2MP-Id";
                        }

                        leaf source {
                            type types-sros:ip-address;
                            description "Source IP address.";
                        }

                        leaf group {
                            type types-sros:ip-address;
                            description "Group IP address.";
                        }

                        leaf route-distinguisher {
                            type types-services:vpn-route-distinguisher;
                            description "VPN Route Distinguisher.";
                        }

                        leaf inner-root {
                            type types-sros:ip-address;
                            description "Inner root IP address";
                        }

                    } // container decoded-opaque-value

                    container stitch-fec {
                        description "Enter the stitch-fec context";

                        leaf root-address {
                            type types-sros:ip-address;
                            description "The value indicates the ip address of the root for this P2MP FEC.";
                        }

                        leaf opaque-type {
                            type uint32;
                            description "The value indicates the type of a Point-Multi-Point Opaque Value Element.";
                        }

                        leaf opaque-len {
                            type uint32;
                            description "The value indicates the length of a Point-Multi-Point Opaque Value Element.";
                        }

                        leaf opaque-value {
                            type string;
                            description "The value indicates the value of a Point-Multi-Point Opaque Value Element.";
                        }

                        leaf decoded-opaque-type {
                            type enumeration {
                                enum "unknown"                      { value 0; }
                                enum "generic"                      { value 1; }
                                enum "ssm"                          { value 2; }
                                enum "vpn-ssm"                      { value 3; }
                                enum "ssm-recursive"                { value 4; }
                                enum "generic-vpn-recursive"        { value 5; }
                                enum "generic-grt-recursive"        { value 6; }
                            }
                            description "Decoded opaque type.";
                        }

                        container decoded-opaque-value {
                            description "Enter the decoded-opaque-value context";

                            leaf p2mp-id {
                                type uint32;
                                description "P2MP-Id";
                            }

                            leaf source {
                                type types-sros:ip-address;
                                description "Source IP address.";
                            }

                            leaf group {
                                type types-sros:ip-address;
                                description "Group IP address.";
                            }

                            leaf route-distinguisher {
                                type types-services:vpn-route-distinguisher;
                                description "VPN Route Distinguisher.";
                            }

                            leaf inner-root {
                                type types-sros:ip-address;
                                description "Inner root IP address";
                            }

                        } // container decoded-opaque-value

                    } // container stitch-fec

                } // list p2mp-stitching

                list service-fec128 {
                    key "vc-type vc-id peer-lsr-id";
                    description "Enter the service-fec128 list instance";

                    leaf vc-type {
                        type types-ldp:vc-type;
                        description "The value specifies the VC type associated with this service FEC.";
                    }

                    leaf vc-id {
                        type types-services:vc-id;
                        description "The value specifies the VC identifier associated with this service FEC.";
                    }

                    leaf peer-lsr-id {
                        type types-ldp:lsr-id;
                        description "Peer LSR-ID";
                    }

                    leaf service-type {
                        type types-services:oper-service-type;
                        description "The value indicates the Service type associated with this service FEC.";
                    }

                    leaf service-id {
                        type types-services:service-id-or-zero;
                        description
                            "The value indicates the Service identifier associated with this service
                             FEC.";
                    }

                    leaf vpn-id {
                        type string;
                        description
                            "vpn-id specifies the value of a VPN (Virtual Private Network)
                             identifier. This is a 10 byte value - the VPN 'type' is stored
                             in the first two bytes the vpn-id. The next four bytes store
                             an 'AS (Autonomous System) number'. A 'local identifier' for the
                             VPN is stored as the last four bytes.";
                    }

                    leaf flags {
                        type types-ldp:fec-flags;
                        description "The bit flags indicate the characteristics of the FEC.";
                    }

                    leaf sdp-id {
                        type types-services:sdp-id-or-zero;
                        description "The value identifies the SDP associated with this peer.";
                    }

                    container mate-endpoint {
                        description "Enter the mate-endpoint context";

                        leaf vc-id {
                            type types-services:vc-id-or-zero;
                            description
                                "The value indicates the VC identifier associated with this
                                 service FEC mate endpoint for vc-switching.";
                        }

                        leaf sdp-id {
                            type types-services:sdp-id-or-zero;
                            description "The value identifies the SDP associated with this peer.";
                        }

                    } // container mate-endpoint

                    container in-label {
                        description "Enter the in-label context";

                        leaf withdraw-reason {
                            type types-ldp:in-label-withdraw-reason;
                            description "The value indicates the reason of withdrawal of ingress label.";
                        }

                        leaf label {
                            type uint32;
                            description "The value indicates the label exchanged.";
                        }

                        leaf status {
                            type types-ldp:label-status;
                            description "The value indicates the status of the label.";
                        }

                        leaf signaling-status {
                            type types-ldp:label-signaling-status;
                            description "The value indicates the signaling status for the label.";
                        }

                        leaf max-cell-concatenate {
                            type uint32;
                            description
                                "The value indicates the maximum number of ATM cells to concatenate
                                 on a ATM cell-mode VC type SDP binding.";
                        }

                        leaf flow-label-transmit-capability {
                            type boolean;
                            description
                                "The value indicates whether or not the local or the remote LDP peer is
                                 capable of sending Flow Label in its pseudowire (PW) packet.";
                        }

                        leaf flow-label-receive-capability {
                            type boolean;
                            description
                                "The value indicates whether or not the local or the remote LDP peer is
                                 capable of receiving Flow Label in its pseudowire packet.";
                        }

                        leaf mtu {
                            type uint32;
                            description
                                "The value indicates the maximum transfer unit for payloads represented by
                                 this FEC";
                        }

                        leaf vlan-tag {
                            type uint32;
                            description "The value indicates the tag on a VLAN VC type SDP binding.";
                        }

                        leaf vccv-cv {
                            type bits {
                                bit icmp-ping                      { position 0; }
                                bit lsp-ping                       { position 1; }
                                bit bfd-fault-detect               { position 2; }
                                bit bfd-fault-detect-signalling    { position 3; }
                            }
                            description
                                "The value indicates the CV (Connectivity Verification) types supported by
                                 local or peer LSR if it supports VCCV (Circuit Connectivity Verification) on
                                 pseudowire. If VCCV is not supported, vccv-cv will be set to 0.";
                        }

                        leaf vccv-cc {
                            type bits {
                                bit pwe3-control-word              { position 0; }
                                bit router-alert-label             { position 1; }
                                bit mpls-demux-label-tl1           { position 2; }
                            }
                            description
                                "The value indicates the CC (Control Channel) types supported by local or peer LSR
                                 if it supports VCCV on pseudowire.  If VCCV is not supported, vccv-cc will be set
                                 to 0.";
                        }

                        leaf pw-status {
                            type boolean;
                            description
                                "The value indicates whether or not the router advertising the associated label
                                 (local or far-end) supports pseudowire status signaling..";
                        }

                        container ce-discovery {
                            description "Enter the ce-discovery context";

                            leaf ipv4-ce-address {
                                type types-sros:ip-address;
                                description "The value indicates the ipv4 CE Address.";
                            }

                            leaf ipv4-capability {
                                type boolean;
                                description
                                    "The value indicates whether or not ipv4 stack capability is supported
                                     for this LDP peer.";
                            }

                            leaf ipv6-capability {
                                type boolean;
                                description
                                    "The value indicates whether or not  ipv6 stack capability is supported
                                     for this LDP peer.";
                            }

                        } // container ce-discovery

                        container cep-tdm {
                            description "Enter the cep-tdm context";

                            leaf payload-size {
                                type uint32;
                                units "bytes";
                                description "The value indicates the payload size.";
                            }

                            leaf bitrate {
                                type uint32;
                                units "sixty-four kilobps";
                                description "The value indicates the bitrate.";
                            }

                            leaf rtp-header {
                                type boolean;
                                description "The value indicates the RTP header usage bit.";
                            }

                            leaf differential-timestamping {
                                type boolean;
                                description "The value indicates the differential (or dynamic) timestamping mode bit.";
                            }

                            leaf signalling-packets-mode {
                                type types-services:tdm-options-sig-pkts;
                                description "The value indicates the CE application signalling packets mode.";
                            }

                            leaf cas-trunk-framing-type {
                                type types-services:tdm-options-cas-trunk-framing;
                                description "The value indicates the CAS trunk framing mode.";
                            }

                            leaf timestamping-frequency {
                                type uint32;
                                units "kilohertz";
                                description "The value indicates the value of the differential timestamp frequency.";
                            }

                            leaf payload-type {
                                type uint32;
                                description "The value indicates the local or the remote payload type.";
                            }

                            leaf ssrc-id {
                                type uint32;
                                description "The value indicates the local or the remote value of SSRC ID.";
                            }

                        } // container cep-tdm

                    } // container in-label

                    container out-label {
                        description "Enter the out-label context";

                        leaf label {
                            type uint32;
                            description "The value indicates the label exchanged.";
                        }

                        leaf status {
                            type types-ldp:label-status;
                            description "The value indicates the status of the label.";
                        }

                        leaf signaling-status {
                            type types-ldp:label-signaling-status;
                            description "The value indicates the signaling status for the label.";
                        }

                        leaf max-cell-concatenate {
                            type uint32;
                            description
                                "The value indicates the maximum number of ATM cells to concatenate
                                 on a ATM cell-mode VC type SDP binding.";
                        }

                        leaf flow-label-transmit-capability {
                            type boolean;
                            description
                                "The value indicates whether or not the local or the remote LDP peer is
                                 capable of sending Flow Label in its pseudowire (PW) packet.";
                        }

                        leaf flow-label-receive-capability {
                            type boolean;
                            description
                                "The value indicates whether or not the local or the remote LDP peer is
                                 capable of receiving Flow Label in its pseudowire packet.";
                        }

                        leaf mtu {
                            type uint32;
                            description
                                "The value indicates the maximum transfer unit for payloads represented by
                                 this FEC";
                        }

                        leaf vlan-tag {
                            type uint32;
                            description "The value indicates the tag on a VLAN VC type SDP binding.";
                        }

                        leaf vccv-cv {
                            type bits {
                                bit icmp-ping                      { position 0; }
                                bit lsp-ping                       { position 1; }
                                bit bfd-fault-detect               { position 2; }
                                bit bfd-fault-detect-signalling    { position 3; }
                            }
                            description
                                "The value indicates the CV (Connectivity Verification) types supported by
                                 local or peer LSR if it supports VCCV (Circuit Connectivity Verification) on
                                 pseudowire. If VCCV is not supported, vccv-cv will be set to 0.";
                        }

                        leaf vccv-cc {
                            type bits {
                                bit pwe3-control-word              { position 0; }
                                bit router-alert-label             { position 1; }
                                bit mpls-demux-label-tl1           { position 2; }
                            }
                            description
                                "The value indicates the CC (Control Channel) types supported by local or peer LSR
                                 if it supports VCCV on pseudowire.  If VCCV is not supported, vccv-cc will be set
                                 to 0.";
                        }

                        leaf pw-status {
                            type boolean;
                            description
                                "The value indicates whether or not the router advertising the associated label
                                 (local or far-end) supports pseudowire status signaling..";
                        }

                        container ce-discovery {
                            description "Enter the ce-discovery context";

                            leaf ipv4-ce-address {
                                type types-sros:ip-address;
                                description "The value indicates the ipv4 CE Address.";
                            }

                            leaf ipv4-capability {
                                type boolean;
                                description
                                    "The value indicates whether or not ipv4 stack capability is supported
                                     for this LDP peer.";
                            }

                            leaf ipv6-capability {
                                type boolean;
                                description
                                    "The value indicates whether or not  ipv6 stack capability is supported
                                     for this LDP peer.";
                            }

                        } // container ce-discovery

                        container cep-tdm {
                            description "Enter the cep-tdm context";

                            leaf payload-size {
                                type uint32;
                                units "bytes";
                                description "The value indicates the payload size.";
                            }

                            leaf bitrate {
                                type uint32;
                                units "sixty-four kilobps";
                                description "The value indicates the bitrate.";
                            }

                            leaf rtp-header {
                                type boolean;
                                description "The value indicates the RTP header usage bit.";
                            }

                            leaf differential-timestamping {
                                type boolean;
                                description "The value indicates the differential (or dynamic) timestamping mode bit.";
                            }

                            leaf signalling-packets-mode {
                                type types-services:tdm-options-sig-pkts;
                                description "The value indicates the CE application signalling packets mode.";
                            }

                            leaf cas-trunk-framing-type {
                                type types-services:tdm-options-cas-trunk-framing;
                                description "The value indicates the CAS trunk framing mode.";
                            }

                            leaf timestamping-frequency {
                                type uint32;
                                units "kilohertz";
                                description "The value indicates the value of the differential timestamp frequency.";
                            }

                            leaf payload-type {
                                type uint32;
                                description "The value indicates the local or the remote payload type.";
                            }

                            leaf ssrc-id {
                                type uint32;
                                description "The value indicates the local or the remote value of SSRC ID.";
                            }

                        } // container cep-tdm

                    } // container out-label

                } // list service-fec128

                list service-fec129 {
                    key "vc-type agi saii taii peer-lsr-id";
                    description "Enter the service-fec129 list instance";

                    leaf vc-type {
                        type types-ldp:vc-type;
                        description "The value specifies the VC type associated with this service FEC.";
                    }

                    leaf agi {
                        type types-services:state-vpn-rd;
                        description
                            "The value specifies the value of the Attachment Group Identifier associated with
                             this service FEC.";
                    }

                    leaf saii {
                        type types-services:aii-all-types-string;
                        description
                            "The value specifies the value of the Source Attachment Individual Identifier
                             associated with this service FEC.";
                    }

                    leaf taii {
                        type types-services:aii-all-types-string;
                        description
                            "The value specifies the value of the Target Attachment Individual Identifier
                             associated with this service FEC.";
                    }

                    leaf peer-lsr-id {
                        type types-ldp:lsr-id;
                        description "Peer LSR-ID";
                    }

                    leaf service-type {
                        type types-services:oper-service-type;
                        description "The value indicates the Service type associated with this service FEC.";
                    }

                    leaf service-id {
                        type types-services:service-id-or-zero;
                        description
                            "The value indicates the Service identifier associated with this service
                             FEC.";
                    }

                    leaf vpn-id {
                        type string;
                        description
                            "vpn-id specifies the value of a VPN (Virtual Private Network)
                             identifier. This is a 10 byte value - the VPN 'type' is stored
                             in the first two bytes the vpn-id. The next four bytes store
                             an 'AS (Autonomous System) number'. A 'local identifier' for the
                             VPN is stored as the last four bytes.";
                    }

                    leaf flags {
                        type types-ldp:fec-flags;
                        description "The bit flags indicate the characteristics of the FEC.";
                    }

                    leaf sdp-id {
                        type types-services:sdp-id-or-zero;
                        description "The value identifies the SDP associated with this peer.";
                    }

                    container mate-endpoint {
                        description "Enter the mate-endpoint context";

                        leaf agi {
                            type types-services:state-vpn-rd;
                            description
                                "The value specifies the value of the Attachment Group Identifier associated with
                                 this service FEC.";
                        }

                        leaf saii {
                            type types-services:aii-all-types-string;
                            description
                                "The value specifies the value of the Source Attachment Individual Identifier
                                 associated with this service FEC.";
                        }

                        leaf taii {
                            type types-services:aii-all-types-string;
                            description
                                "The value specifies the value of the Target Attachment Individual Identifier
                                 associated with this service FEC.";
                        }

                        leaf sdp-id {
                            type types-services:sdp-id-or-zero;
                            description "The value identifies the SDP associated with this peer.";
                        }

                    } // container mate-endpoint

                    container in-label {
                        description "Enter the in-label context";

                        leaf withdraw-reason {
                            type types-ldp:in-label-withdraw-reason;
                            description "The value indicates the reason of withdrawal of ingress label.";
                        }

                        leaf label {
                            type uint32;
                            description "The value indicates the label exchanged.";
                        }

                        leaf status {
                            type types-ldp:label-status;
                            description "The value indicates the status of the label.";
                        }

                        leaf signaling-status {
                            type types-ldp:label-signaling-status;
                            description "The value indicates the signaling status for the label.";
                        }

                        leaf max-cell-concatenate {
                            type uint32;
                            description
                                "The value indicates the maximum number of ATM cells to concatenate
                                 on a ATM cell-mode VC type SDP binding.";
                        }

                        leaf flow-label-transmit-capability {
                            type boolean;
                            description
                                "The value indicates whether or not the local or the remote LDP peer is
                                 capable of sending Flow Label in its pseudowire (PW) packet.";
                        }

                        leaf flow-label-receive-capability {
                            type boolean;
                            description
                                "The value indicates whether or not the local or the remote LDP peer is
                                 capable of receiving Flow Label in its pseudowire packet.";
                        }

                        leaf mtu {
                            type uint32;
                            description
                                "The value indicates the maximum transfer unit for payloads represented by
                                 this FEC";
                        }

                        leaf vlan-tag {
                            type uint32;
                            description "The value indicates the tag on a VLAN VC type SDP binding.";
                        }

                        leaf vccv-cv {
                            type bits {
                                bit icmp-ping                      { position 0; }
                                bit lsp-ping                       { position 1; }
                                bit bfd-fault-detect               { position 2; }
                                bit bfd-fault-detect-signalling    { position 3; }
                            }
                            description
                                "The value indicates the CV (Connectivity Verification) types supported by
                                 local or peer LSR if it supports VCCV (Circuit Connectivity Verification) on
                                 pseudowire. If VCCV is not supported, vccv-cv will be set to 0.";
                        }

                        leaf vccv-cc {
                            type bits {
                                bit pwe3-control-word              { position 0; }
                                bit router-alert-label             { position 1; }
                                bit mpls-demux-label-tl1           { position 2; }
                            }
                            description
                                "The value indicates the CC (Control Channel) types supported by local or peer LSR
                                 if it supports VCCV on pseudowire.  If VCCV is not supported, vccv-cc will be set
                                 to 0.";
                        }

                        leaf pw-status {
                            type boolean;
                            description
                                "The value indicates whether or not the router advertising the associated label
                                 (local or far-end) supports pseudowire status signaling..";
                        }

                        container ce-discovery {
                            description "Enter the ce-discovery context";

                            leaf ipv4-ce-address {
                                type types-sros:ip-address;
                                description "The value indicates the ipv4 CE Address.";
                            }

                            leaf ipv4-capability {
                                type boolean;
                                description
                                    "The value indicates whether or not ipv4 stack capability is supported
                                     for this LDP peer.";
                            }

                            leaf ipv6-capability {
                                type boolean;
                                description
                                    "The value indicates whether or not  ipv6 stack capability is supported
                                     for this LDP peer.";
                            }

                        } // container ce-discovery

                        container cep-tdm {
                            description "Enter the cep-tdm context";

                            leaf payload-size {
                                type uint32;
                                units "bytes";
                                description "The value indicates the payload size.";
                            }

                            leaf bitrate {
                                type uint32;
                                units "sixty-four kilobps";
                                description "The value indicates the bitrate.";
                            }

                            leaf rtp-header {
                                type boolean;
                                description "The value indicates the RTP header usage bit.";
                            }

                            leaf differential-timestamping {
                                type boolean;
                                description "The value indicates the differential (or dynamic) timestamping mode bit.";
                            }

                            leaf signalling-packets-mode {
                                type types-services:tdm-options-sig-pkts;
                                description "The value indicates the CE application signalling packets mode.";
                            }

                            leaf cas-trunk-framing-type {
                                type types-services:tdm-options-cas-trunk-framing;
                                description "The value indicates the CAS trunk framing mode.";
                            }

                            leaf timestamping-frequency {
                                type uint32;
                                units "kilohertz";
                                description "The value indicates the value of the differential timestamp frequency.";
                            }

                            leaf payload-type {
                                type uint32;
                                description "The value indicates the local or the remote payload type.";
                            }

                            leaf ssrc-id {
                                type uint32;
                                description "The value indicates the local or the remote value of SSRC ID.";
                            }

                        } // container cep-tdm

                    } // container in-label

                    container out-label {
                        description "Enter the out-label context";

                        leaf label {
                            type uint32;
                            description "The value indicates the label exchanged.";
                        }

                        leaf status {
                            type types-ldp:label-status;
                            description "The value indicates the status of the label.";
                        }

                        leaf signaling-status {
                            type types-ldp:label-signaling-status;
                            description "The value indicates the signaling status for the label.";
                        }

                        leaf max-cell-concatenate {
                            type uint32;
                            description
                                "The value indicates the maximum number of ATM cells to concatenate
                                 on a ATM cell-mode VC type SDP binding.";
                        }

                        leaf flow-label-transmit-capability {
                            type boolean;
                            description
                                "The value indicates whether or not the local or the remote LDP peer is
                                 capable of sending Flow Label in its pseudowire (PW) packet.";
                        }

                        leaf flow-label-receive-capability {
                            type boolean;
                            description
                                "The value indicates whether or not the local or the remote LDP peer is
                                 capable of receiving Flow Label in its pseudowire packet.";
                        }

                        leaf mtu {
                            type uint32;
                            description
                                "The value indicates the maximum transfer unit for payloads represented by
                                 this FEC";
                        }

                        leaf vlan-tag {
                            type uint32;
                            description "The value indicates the tag on a VLAN VC type SDP binding.";
                        }

                        leaf vccv-cv {
                            type bits {
                                bit icmp-ping                      { position 0; }
                                bit lsp-ping                       { position 1; }
                                bit bfd-fault-detect               { position 2; }
                                bit bfd-fault-detect-signalling    { position 3; }
                            }
                            description
                                "The value indicates the CV (Connectivity Verification) types supported by
                                 local or peer LSR if it supports VCCV (Circuit Connectivity Verification) on
                                 pseudowire. If VCCV is not supported, vccv-cv will be set to 0.";
                        }

                        leaf vccv-cc {
                            type bits {
                                bit pwe3-control-word              { position 0; }
                                bit router-alert-label             { position 1; }
                                bit mpls-demux-label-tl1           { position 2; }
                            }
                            description
                                "The value indicates the CC (Control Channel) types supported by local or peer LSR
                                 if it supports VCCV on pseudowire.  If VCCV is not supported, vccv-cc will be set
                                 to 0.";
                        }

                        leaf pw-status {
                            type boolean;
                            description
                                "The value indicates whether or not the router advertising the associated label
                                 (local or far-end) supports pseudowire status signaling..";
                        }

                        container ce-discovery {
                            description "Enter the ce-discovery context";

                            leaf ipv4-ce-address {
                                type types-sros:ip-address;
                                description "The value indicates the ipv4 CE Address.";
                            }

                            leaf ipv4-capability {
                                type boolean;
                                description
                                    "The value indicates whether or not ipv4 stack capability is supported
                                     for this LDP peer.";
                            }

                            leaf ipv6-capability {
                                type boolean;
                                description
                                    "The value indicates whether or not  ipv6 stack capability is supported
                                     for this LDP peer.";
                            }

                        } // container ce-discovery

                        container cep-tdm {
                            description "Enter the cep-tdm context";

                            leaf payload-size {
                                type uint32;
                                units "bytes";
                                description "The value indicates the payload size.";
                            }

                            leaf bitrate {
                                type uint32;
                                units "sixty-four kilobps";
                                description "The value indicates the bitrate.";
                            }

                            leaf rtp-header {
                                type boolean;
                                description "The value indicates the RTP header usage bit.";
                            }

                            leaf differential-timestamping {
                                type boolean;
                                description "The value indicates the differential (or dynamic) timestamping mode bit.";
                            }

                            leaf signalling-packets-mode {
                                type types-services:tdm-options-sig-pkts;
                                description "The value indicates the CE application signalling packets mode.";
                            }

                            leaf cas-trunk-framing-type {
                                type types-services:tdm-options-cas-trunk-framing;
                                description "The value indicates the CAS trunk framing mode.";
                            }

                            leaf timestamping-frequency {
                                type uint32;
                                units "kilohertz";
                                description "The value indicates the value of the differential timestamp frequency.";
                            }

                            leaf payload-type {
                                type uint32;
                                description "The value indicates the local or the remote payload type.";
                            }

                            leaf ssrc-id {
                                type uint32;
                                description "The value indicates the local or the remote value of SSRC ID.";
                            }

                        } // container cep-tdm

                    } // container out-label

                } // list service-fec129

                container active {
                    description "Enter the active context";

                    list prefixes {
                        key "fec-type ip-prefix operation-type";
                        description "Enter the prefixes list instance";

                        leaf fec-type {
                            type types-ldp:fec-type;
                            description "The value specifies the FEC type of this address FEC.";
                        }

                        leaf ip-prefix {
                            type types-sros:ip-prefix;
                            description "The value specifies the FEC IP Prefix.";
                        }

                        leaf operation-type {
                            type enumeration {
                                enum "pop"                          { value 1; }
                                enum "push"                         { value 2; }
                                enum "swap"                         { value 3; }
                            }
                            description "The value indicates operation type of this FEC.";
                        }

                        leaf flags {
                            type types-ldp:fec-flags;
                            description "The bit flags indicate the characteristics of the FEC.";
                        }

                        list in-label {
                            key "id";
                            description "Enter the in-label list instance";

                            leaf id {
                                type uint32;
                                description "The value indicates the label number of the exchanged label.";
                            }

                            leaf label {
                                type uint32;
                                description "The value indicates the label exchanged.";
                            }

                        } // list in-label

                        list out-label {
                            key "id";
                            description "Enter the out-label list instance";

                            leaf id {
                                type uint32;
                                description "The value indicates the label number of the exchanged label.";
                            }

                            leaf interface-name {
                                type types-sros:named-item-or-empty;
                                description "The value specifies the interface name for egress label.";
                            }

                            leaf next-hop {
                                type types-sros:ip-address;
                                description "The value specifies the next hop IP address for egress label.";
                            }

                            leaf lsp-name {
                                type types-sros:named-item-64-or-empty;
                                description "The value specifies the LSP name associated with egress label.";
                            }

                            leaf label {
                                type uint32;
                                description "The value indicates the label exchanged.";
                            }

                            leaf status {
                                type types-ldp:label-status;
                                description "The value indicates the status of the label.";
                            }

                            leaf mtu {
                                type uint32;
                                description
                                    "The value indicates the maximum transfer unit for payloads represented by
                                     this FEC";
                            }

                            leaf metric {
                                type uint32;
                                description
                                    "The value indicates the relative cost of the tunnel represented by this
                                     FEC";
                            }

                            leaf class-based-forwarding {
                                type types-mpls:lsp-fc-bits;
                                description
                                    "The value specifies (if lsp-name has value) the forwarding classes
                                     installed for the RSVP tunnel used by LDP in LDP over RSVP
                                     associated with egress label.

                                     If the 'default-lsp' bit is set, it indicates if the LSP for the RSVP
                                     tunnel used by LDP in LDP over RSVP associated with egress label is
                                     used as the class-based-forwarding default.";
                            }

                        } // list out-label

                    } // list prefixes

                } // container active

            } // container bindings

        } // container ldp

    } // grouping state-router-ldp

}
