submodule nokia-conf-router-p2mp-sr-tree {

    yang-version "1.1";

    belongs-to nokia-conf { prefix "conf"; }

    import nokia-sros-yang-extensions     { prefix "sros-ext"; }
    import nokia-types-sros               { prefix "types-sros"; }

    include nokia-conf-groups;
    include nokia-conf-router;


    sros-ext:sros-major-release "rel22";

    organization "Nokia";

    contact
        "Nokia SR OS Support
         Web: <http://www.nokia.com>";

    description
        "Nokia YANG Data model to configure Base router p2mp-sr-tree on SR OS based routers.

         Copyright 2016 Nokia. All rights reserved. Reproduction of this document
         is authorized on the condition that the foregoing copyright notice is included.

         This nokia-conf-router-p2mp-sr-tree YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-03-22";

    grouping conf-router-p2mp-sr-tree {
        container p2mp-sr-tree {
            when "../router-name = 'Base'";
            presence "Enable the p2mp-sr-tree context";
            description "Enable the p2mp-sr-tree context";

            leaf admin-state {
                type types-sros:admin-state;
                default "disable";
                description "Administrative state of the P2MP SR tree";
            }

            leaf reserved-label-block {
                type leafref {
                    path "../../mpls-labels/reserved-label-block/label-block-name";
                }
                description "Reserved label block name for the P2MP SR tree";
            }

            leaf-list bfd-liveness {
                type enumeration {
                    enum "ipv4"                         { value 1; }
                    enum "ipv6"                         { value 2; }
                }
                max-elements 2;
                description "BFD-liveness for P2MP SR tree status entry";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list p2mp-policy {
                key "p2mp-policy-name";
                description "Enter the p2mp-policy list instance";

                leaf p2mp-policy-name {
                    type types-sros:named-item;
                    description "P2MP policy name";
                }

                leaf root-address {
                    type types-sros:ip-address;
                    default "0.0.0.0";
                    description "Root address for the P2MP policy";
                }

                leaf tree-id {
                    type uint32 {
                        range "0|8193..16286";
                    }
                    default "0";
                    description "Tree ID for the P2MP policy";
                }

                leaf admin-state {
                    type types-sros:admin-state;
                    default "disable";
                    description "Administrative state of the P2MP policy";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list candidate-path {
                    key "candidate-path-name";
                    description "Enter the candidate-path list instance";

                    leaf candidate-path-name {
                        type types-sros:named-item;
                        description "Candidate path name";
                    }

                    leaf active-instance {
                        type leafref {
                            path "../path-instances/index";
                        }
                        description "Candidate path active instance";
                    }

                    leaf preference {
                        type uint32 {
                            range "0..1024";
                        }
                        default "100";
                        description "Candidate-path preference";
                    }

                    leaf admin-state {
                        type types-sros:admin-state;
                        default "disable";
                        description "Administrative state of the P2MP SR tree";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list path-instances {
                        key "index";
                        description "Enter the path-instances list instance";

                        leaf index {
                            type uint32 {
                                range "1..2";
                            }
                            description "Instance index";
                        }

                        leaf instance-id {
                            type uint32;
                            description "Instance value";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list path-instances

                } // list candidate-path

            } // list p2mp-policy

            list replication-segment {
                key "policy-name";
                description "Enter the replication-segment list instance";

                leaf policy-name {
                    type types-sros:named-item;
                    description "P2MP policy name";
                }

                leaf replication-sid {
                    type uint32;
                    sros-ext:auto-restart-to-modify;
                    default "0";
                    description "Segment ID of the replication segment";
                }

                leaf instance-id {
                    type uint32;
                    default "0";
                    description "Instance ID for replication segment entries";
                }

                leaf root-address {
                    type types-sros:ip-address;
                    description "Root address for replication segment entries";
                }

                leaf tree-id {
                    type uint32 {
                        range "0|8193..16286";
                    }
                    default "0";
                    description "Tree ID for the replication segment of the P2MP SR tree";
                }

                leaf admin-state {
                    type types-sros:admin-state;
                    default "disable";
                    description "Administrative state of the replication segment";
                }

                leaf sid-action {
                    type enumeration {
                        enum "none"                         { value 0; }
                        enum "push"                         { value 1; }
                        enum "pop"                          { value 2; }
                        enum "swap"                         { value 3; }
                    }
                    default "none";
                    description "SID action for replication segment entries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list downstream-nodes {
                    key "downstream-index";
                    description "Enter the downstream-nodes list instance";

                    leaf downstream-index {
                        type int32 {
                            range "1..4096";
                        }
                        description "Downstream index";
                    }

                    leaf next-hop-address {
                        type types-sros:ip-address-with-zone;
                        default "0.0.0.0";
                        description "Next-hop address for replication segment next hops";
                    }

                    leaf next-hop-interface-name {
                        type types-sros:interface-name;
                        description "Interface name for replication segment next-hops";
                    }

                    leaf protect-nexthop-id {
                        type leafref {
                            path "../../downstream-nodes/downstream-index";
                        }
                        description "ID of the protection next hop used for FRR";
                    }

                    leaf admin-state {
                        type types-sros:admin-state;
                        default "disable";
                        description "Administrative state of next-hop entries";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container label {
                        description "Enter the label context";

                        choice label {
                            default "replication-sid-list";
                            case replication-sid-list {

                                list sid-list {
                                    key "index";
                                    description "Enter the sid-list list instance";

                                    leaf index {
                                        type uint32 {
                                            range "1..11";
                                        }
                                        description "SID list index";
                                    }

                                    leaf replication-sid {
                                        type uint32 {
                                            range "3|16..1048575|4294967295";
                                        }
                                        mandatory true;
                                        description "Segment ID for the SID list entry";
                                    }

                                    leaf-list apply-groups {
                                        type leafref {
                                            path "../../../../../../../groups/group/name";
                                        }
                                        max-elements 8;
                                        ordered-by user;
                                        description "Apply a configuration group at this level";
                                    }

                                    leaf-list apply-groups-exclude {
                                        type leafref {
                                            path "../../../../../../../groups/group/name";
                                        }
                                        max-elements 8;
                                        ordered-by user;
                                        description "Exclude a configuration group at this level";
                                    }

                                } // list sid-list

                            }
                        }
                    } // container label

                } // list downstream-nodes

            } // list replication-segment

        } // container p2mp-sr-tree

    } // grouping conf-router-p2mp-sr-tree

}
