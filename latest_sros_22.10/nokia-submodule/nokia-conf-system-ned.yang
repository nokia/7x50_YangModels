submodule nokia-conf-system-ned {

    yang-version "1.1";

    belongs-to nokia-conf { prefix "conf"; }

    import nokia-sros-yang-extensions     { prefix "sros-ext"; }
    import nokia-types-sros               { prefix "types-sros"; }

    include nokia-conf-groups;


    sros-ext:sros-major-release "rel22";

    organization "Nokia";

    contact
        "Nokia SR OS Support
         Web: <http://www.nokia.com>";

    description
        "Nokia YANG Data model to configure system network-element-discovery on SR OS based routers.

         Copyright 2016 Nokia. All rights reserved. Reproduction of this document
         is authorized on the condition that the foregoing copyright notice is included.

         This nokia-conf-system-ned YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-10-27";

    grouping conf-system-ned-network-element-discovery {
        container network-element-discovery {
            description "Enter the network-element-discovery context";

            leaf generate-traps {
                type boolean;
                default "false";
                description "Generate NE discovery traps";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list profile {
                key "name";
                max-elements 1;
                description "Enter the profile list instance";

                leaf name {
                    type types-sros:named-item;
                    description "Profile name";
                }

                leaf neid {
                    type string {
                        length "7..8";
                    }
                    description "Network element ID of the advertised node";
                }

                leaf platform-type {
                    type types-sros:named-item-255;
                    description "Platform name and chassis type to be advertised";
                }

                leaf vendor-id {
                    type types-sros:named-item-255;
                    default "Nokia";
                    description "Vendor ID to be advertised";
                }

                leaf system-mac {
                    type types-sros:mac-unicast-address-no-zero;
                    description "MAC address of the advertised node";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container neip {
                    description "Enable the neip context";

                    leaf ipv4 {
                        type types-sros:ipv4-unicast-address;
                        description "NEIP IPv4 address";
                    }

                    leaf ipv6 {
                        type types-sros:ipv6-address;
                        description "NEIP IPv6 address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container auto-generate {
                        description "Enter the auto-generate context";

                        container ipv4 {
                            presence "Enable the ipv4 context";
                            description "Enter the ipv4 context";

                            leaf vendor-id-value {
                                type uint32 {
                                    range "1..255";
                                }
                                default "140";
                                description "Most significant byte if the NE IPv4 address";
                            }

                        } // container ipv4

                        container ipv6 {
                            presence "Enable the ipv6 context";
                            description "Enter the ipv6 context";

                            leaf vendor-id-value {
                                type uint32 {
                                    range "1..255";
                                }
                                default "140";
                                description "Most significant byte of the NE IPv6 address";
                            }

                        } // container ipv6

                    } // container auto-generate

                } // container neip

            } // list profile

        } // container network-element-discovery

    } // grouping conf-system-ned-network-element-discovery

}
