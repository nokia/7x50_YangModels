submodule nokia-state-filter {

    yang-version "1.1";

    belongs-to nokia-state { prefix "state"; }

    import ietf-yang-types                { prefix "yang"; }
    import nokia-sros-yang-extensions     { prefix "sros-ext"; }
    import nokia-types-card               { prefix "types-card"; }
    import nokia-types-filter             { prefix "types-filter"; }
    import nokia-types-services           { prefix "types-services"; }
    import nokia-types-sros               { prefix "types-sros"; }

    include nokia-state-filter-ip-exception;
    include nokia-state-openflow;
    include nokia-state-service;
    include nokia-state-svc-vpls;
    include nokia-state-svc-vprn;


    sros-ext:sros-major-release "rel22";

    organization "Nokia";

    contact
        "Nokia SR OS Support
         Web: <http://www.nokia.com>";

    description
        "Nokia YANG Data model with operational state for line card ACL filters on SR OS based routers.

         Copyright 2016 Nokia. All rights reserved. Reproduction of this document
         is authorized on the condition that the foregoing copyright notice is included.

         This nokia-state-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-11-29";

    grouping state-filter {
        container filter {
            description "Enter the filter context";

            list redirect-policy {
                key "redirect-policy-name";
                description "Enter the redirect-policy list instance";

                leaf redirect-policy-name {
                    type types-sros:named-item;
                    description "Redirect policy name";
                }

                leaf active-destination {
                    type types-sros:ip-address;
                    description
                        "The value indicates the IP address of the active
                         destination. A value of 0 indicates that there is currently
                         no active destination.
                         The value must be consistent with the IP version value of
                         the associated act-dest-ip-address type object.";
                }

                leaf best-destination {
                    type types-sros:ip-address;
                    description
                        "The value of the object indicates the IP address of available destination
                         with the highest priority.";
                }

                leaf sticky-dest-hold-remain {
                    type int32 {
                        range "0..65535";
                    }
                    units "seconds";
                    description "Hold-remain for stickiness to take effect.";
                }

                leaf applied {
                    type boolean;
                    description "Indicates whether the redirect-policy is applied.";
                }

                list destination {
                    key "destination-address";
                    description "Enter the destination list instance";

                    leaf destination-address {
                        type types-sros:ip-unicast-address;
                        description "IP address and type of destination";
                    }

                    leaf oper-priority {
                        type uint32 {
                            range "0..255";
                        }
                        description
                            "The value of the this object indicates the current dynamic
                             priority of this destination.

                             It is derived from the base priority indicated by the value
                             of the object priority and results of tests assigned
                             to the destination.

                             A destination with the highest operational priority across multiple
                             destinations in a Redirect Policy is used as the preferred
                             destination.

                             If operational state of the destination is 'out-of-service'
                             then the value of this leaf is '0'. ";
                    }

                    leaf oper-state {
                        type types-sros:oper-state;
                        description
                            "The value of the this object indicates the operational
                             state of the destination.";
                    }

                    container ping-test {
                        description "Enter the ping-test context";

                        leaf hold-down-remain {
                            type uint32 {
                                range "0..86400";
                            }
                            units "seconds";
                            description
                                "The value of this object indicates the amount of time in seconds that the system
                                 will remain in held down state before being used again.";
                        }

                        leaf last-action {
                            type types-filter:redirect-policy-test-last-action;
                            description
                                "The value of this object maintains impact that the last test probe made on the
                                 operational status of the destination as maintained in 'redirect-policy destination
                                 shutdown'.

                                 If the last action was 'disable-destination', the destination may not be used for
                                 hold-down seconds.";
                        }

                        leaf last-action-time {
                            type types-sros:date-time;
                            description
                                "The value of this object maintains the time stamp when this test received
                                 a response for a probe sent out.";
                        }

                    } // container ping-test

                    container unicast-rt-test {
                        description "Enter the unicast-rt-test context";

                        leaf last-action {
                            type types-filter:redirect-policy-test-last-action;
                            description
                                "The value of this object indicates an impact that the
                                 last message from RTM module had on the value of the
                                 object 'redirect-policy destination oper-state'.";
                        }

                        leaf last-action-time {
                            type types-sros:date-time;
                            description
                                "The value of this object indicates the time stamp
                                 when the last update from RTM module for this
                                 destination was received.";
                        }

                    } // container unicast-rt-test

                } // list destination

            } // list redirect-policy

            list redirect-policy-binding {
                key "binding-name";
                description "Enter the redirect-policy-binding list instance";

                leaf binding-name {
                    type types-sros:named-item;
                    description "Binding name";
                }

                leaf oper-state {
                    type types-sros:oper-state;
                    description
                        "The value of the this object indicates the operational state of the redirect policy
                         binding.";
                }

                list redirect-policy {
                    key "redirect-policy-name";
                    description "Enter the redirect-policy list instance";

                    leaf redirect-policy-name {
                        type leafref {
                            path "../../../redirect-policy/redirect-policy-name";
                        }
                        description "Redirect policy name";
                    }

                    list destination {
                        key "destination-address";
                        description "Enter the destination list instance";

                        leaf destination-address {
                            type leafref {
                                path "../../../../redirect-policy[redirect-policy-name=current()/../../redirect-policy-name]/destination/destination-address";
                            }
                            description "IP address of redirect policy destination to binding";
                        }

                        leaf own-oper-state {
                            type types-sros:oper-state;
                            description
                                "The value of the this object indicates the operational state of the redirect policy
                                 binding destination (based on its own tests only).";
                        }

                    } // list destination

                } // list redirect-policy

            } // list redirect-policy-binding

            list log {
                key "log-id";
                description "Enter the log list instance";

                leaf log-id {
                    type types-filter:filter-log-id;
                    description "Filter log identifier";
                }

                container destination {
                    description "Enter the destination context";

                    choice destination {
                        case memory {

                            container memory {
                                description "Enter the memory context";

                                leaf num-entries {
                                    type uint32;
                                    description "Indicates the actual number of logged entries.";
                                }

                                leaf wrapped {
                                    type boolean;
                                    description "The sequence-number for this log has wrapped.";
                                }

                                list entry {
                                    key "id";
                                    description "Enter the entry list instance";

                                    leaf id {
                                        type uint32;
                                        description "Message identifier.";
                                    }

                                    leaf message {
                                        type string {
                                            length "0..661";
                                        }
                                        description "Message content.";
                                    }

                                } // list entry

                            } // container memory

                        }
                        case syslog {

                            container syslog {
                                description "Enter the syslog context";

                                container summary {
                                    description "Enter the summary context";

                                    leaf num-entries {
                                        type uint32;
                                        description "Indicates the number of log messages received.";
                                    }

                                    leaf num-entries-arp {
                                        type uint32;
                                        description "Indicates the number of only ARP frames among filter logs.";
                                    }

                                    list entry {
                                        key "filter-type id";
                                        description "Enter the entry list instance";

                                        leaf filter-type {
                                            type enumeration {
                                                enum "ip"                           { value 0; }
                                                enum "ipv6"                         { value 1; }
                                                enum "mac"                          { value 2; }
                                            }
                                            description "Filter type.";
                                        }

                                        leaf id {
                                            type uint32 {
                                                range "0..4";
                                            }
                                            description "Entry identifier.";
                                        }

                                        leaf address {
                                            type union {
                                                type types-sros:ip-address;
                                                type types-sros:ipv6-address;
                                                type yang:mac-address;
                                            }
                                            description "Source or destination address.";
                                        }

                                        leaf count {
                                            type uint32;
                                            description "Number of logs for the source/destination address.";
                                        }

                                    } // list entry

                                } // container summary

                            } // container syslog

                        }
                    }
                } // container destination

            } // list log

            container log-instance {
                description "Enter the log-instance context";

                leaf max-instances {
                    type uint32;
                    description "Indicates the maximum allowed filter log instances on the system.";
                }

                leaf num-instances {
                    type uint32;
                    description "Indicates the actual number of filter log instances on the system.";
                }

            } // container log-instance

            container match-list {
                description "Enter the match-list context";

                list ip-prefix-list {
                    key "prefix-list-name";
                    description "Enter the ip-prefix-list list instance";

                    leaf prefix-list-name {
                        type types-sros:named-item;
                        description "IP prefix list name";
                    }

                    container apply-path {
                        description "Enter the apply-path context";

                        list bgp-peers {
                            key "criterion-index";
                            description "Enter the bgp-peers list instance";

                            leaf criterion-index {
                                type uint32 {
                                    range "1..255";
                                }
                                description "BGP peers auto-generation configuration index";
                            }

                            list prefix {
                                key "prefix";
                                description "Enter the prefix list instance";

                                leaf prefix {
                                    type types-sros:ipv4-prefix;
                                    description "prefix.";
                                }

                            } // list prefix

                        } // list bgp-peers

                    } // container apply-path

                } // list ip-prefix-list

                list ipv6-prefix-list {
                    key "prefix-list-name";
                    description "Enter the ipv6-prefix-list list instance";

                    leaf prefix-list-name {
                        type types-sros:named-item;
                        description "IP prefix list name";
                    }

                    container apply-path {
                        description "Enter the apply-path context";

                        list bgp-peers {
                            key "criterion-index";
                            description "Enter the bgp-peers list instance";

                            leaf criterion-index {
                                type uint32 {
                                    range "1..255";
                                }
                                description "BGP peers auto-generation configuration index";
                            }

                            list prefix {
                                key "prefix";
                                description "Enter the prefix list instance";

                                leaf prefix {
                                    type types-sros:ipv6-prefix;
                                    description "prefix.";
                                }

                            } // list prefix

                        } // list bgp-peers

                    } // container apply-path

                } // list ipv6-prefix-list

            } // container match-list

            list ip-filter {
                key "filter-name";
                description "Enter the ip-filter list instance";

                leaf filter-name {
                    type types-filter:filter-name;
                    description "Filter name";
                }

                leaf origin {
                    type enumeration {
                        enum "config"                       { value 0; }
                        enum "flowspec"                     { value 1; }
                        enum "subscriber-mgmt"              { value 2; }
                        enum "openflow"                     { value 4; }
                        enum "vsd"                          { value 5; }
                        enum "tli"                          { value 6; }
                        enum "dynamic-services"             { value 7; }
                    }
                    description "The protocol or mechanism that created this filter.";
                }

                leaf applied {
                    type boolean;
                    description "Indicates whether the filter is applied.";
                }

                leaf num-entries {
                    type uint32;
                    description "Number of entries in this filter.";
                }

                leaf oper-filter-id {
                    type uint32;
                    description
                        "The value of this object uniquely identifies a filter.
                         User-configured filters have values between (1..65535).
                         Other values are reserved for filters that are created
                         (auto-generated) by the system.";
                }

                leaf num-sub-entries {
                    type uint32;
                    description "Number of sub-entries.";
                }

                leaf num-cam-entries-fp2 {
                    type uint32;
                    description "Number of CAM entries required on FP2 or FP3 based line cards";
                }

                leaf num-cam-entries-fp4 {
                    type uint32;
                    description "Number of CAM entries required on FP4 (or higher) based line cards";
                }

                container subscriber-mgmt {
                    description "Enter the subscriber-mgmt context";

                    container host-specific-entry {
                        description "Enter the host-specific-entry context";

                        container filter-rule {
                            description "Enter the filter-rule context";

                            leaf num-inserted {
                                type uint32;
                                description
                                    "Indicates how many host specific filter-rule entries are
                                     currently inserted in the filter on request of RADIUS/DIAMETER.";
                            }

                        } // container filter-rule

                        container credit-control {
                            description "Enter the credit-control context";

                            leaf num-inserted {
                                type uint32;
                                description
                                    "Indicates how many filter entries are currently inserted
                                     in the filter on request of credit control.";
                            }

                        } // container credit-control

                    } // container host-specific-entry

                    container shared-entry {
                        description "Enter the shared-entry context";

                        leaf num-filters {
                            type uint32;
                            description
                                "Indicates how many filters are currently created based on
                                 subscriber management shared entries of this filter.";
                        }

                        container filter-rule {
                            description "Enter the filter-rule context";

                            leaf num-inserted {
                                type uint32;
                                description
                                    "The value of this object indicates how many host common filter-rule entries are
                                     currently inserted in the filter on request of RADIUS.";
                            }

                        } // container filter-rule

                        container pcc-rule {
                            description "Enter the pcc-rule context";

                            leaf num-inserted {
                                type uint32;
                                description
                                    "The value of this object indicates how many pcc-rule filter entries received from
                                     DIAMETER have been inserted in this filter.";
                            }

                        } // container pcc-rule

                    } // container shared-entry

                } // container subscriber-mgmt

                list entry {
                    key "entry-id";
                    description "Enter the entry list instance";

                    leaf entry-id {
                        type types-filter:entry-id;
                        description "ID for a match criteria and the corresponding action";
                    }

                    leaf inserted-by {
                        type enumeration {
                            enum "fixed"                        { value 0; }
                            enum "filter-rule"                  { value 1; }
                            enum "credit-control"               { value 2; }
                            enum "flowspec"                     { value 3; }
                            enum "li"                           { value 4; }
                            enum "embedded"                     { value 5; }
                            enum "shared-filter-rule"           { value 6; }
                            enum "openflow"                     { value 7; }
                            enum "pcc"                          { value 8; }
                            enum "vsd"                          { value 9; }
                            enum "tli"                          { value 10; }
                            enum "dynamic-services"             { value 11; }
                        }
                        description "The protocol or mechanism that inserted this entry.";
                    }

                    leaf num-sub-entries {
                        type uint32;
                        description "Number of sub-entries.";
                    }

                    leaf num-cam-entries-fp2 {
                        type uint32;
                        description "Number of CAM entries required on FP2 or FP3 based line cards";
                    }

                    leaf num-cam-entries-fp4 {
                        type uint32;
                        description "Number of CAM entries required on FP4 (or higher) based line cards";
                    }

                    leaf log-instantiated {
                        type boolean;
                        description
                            "This object indicates if the filter log for this filter
                             entry has been instantiated or not.";
                    }

                    leaf downloaded-action {
                        type types-filter:filter-downloaded-action;
                        description
                            "The value of this object indicates the filter entry
                             action downloaded to IOM.";
                    }

                    leaf pbr-down-action {
                        type enumeration {
                            enum "drop"                         { value 1; }
                            enum "forward"                      { value 2; }
                        }
                        description
                            "Estimation of action performed if PBR target is down. This takes into
                             account configuration of PBR down action override, filter default action, and default
                             behavior of a filter action. But does not take into account where filter is applied
                             therefore performed action may differ at the end.";
                    }

                    leaf pbr-down-action-reason {
                        type enumeration {
                            enum "entry-default"                { value 1; }
                            enum "filter-default"               { value 2; }
                            enum "pbr-down-override"            { value 3; }
                        }
                        description "The source of the estimated value of PBR down action.";
                    }

                    leaf sticky-dest-hold-remain {
                        type int32 {
                            range "0..65535";
                        }
                        units "seconds";
                        description
                            "The value of this object indicates the remaining
                             time in seconds, until the best action will become
                             active and will be fixed.

                             Best action is:
                             - primary action if PBR target status of primary
                             action is up.
                             - secondary action if PBR target status of secondary
                             action is up and PBR target status of primary action
                             is down.
                             - none if both PBR targets are down.";
                    }

                    leaf inserted-by-direction {
                        type enumeration {
                            enum "ingress"                      { value 0; }
                            enum "egress"                       { value 1; }
                        }
                        description "The direction specified in shared filter rule causing creation of the entry.";
                    }

                    container embedding {
                        description "Enter the embedding context";

                        leaf origin {
                            type enumeration {
                                enum "fixed"                        { value 0; }
                                enum "flowspec"                     { value 3; }
                                enum "openflow"                     { value 7; }
                                enum "vsd"                          { value 9; }
                            }
                            description "Indicates the origin of the embedded filter which is the source of the entry embedded at this position.";
                        }

                        leaf filter-name {
                            type types-filter:filter-name;
                            description "Indicates the name of the embedded filter which is the source of the entry embedded at this position.";
                        }

                        leaf entry-id {
                            type types-filter:entry-id;
                            description "Indicates entry-id of embedded filter which was inserted at this position.";
                        }

                    } // container embedding

                    container statistics {
                        description "Enter the statistics context";

                        leaf ingress-hit-pkt {
                            type yang:zero-based-counter64;
                            description
                                "This object indicates the number of times an ingress packet
                                 matched this entry.";
                        }

                        leaf ingress-hit-byte {
                            type yang:zero-based-counter64;
                            description
                                "The value of this object indicates the number of bytes of
                                 all ingress packets that matched this entry.";
                        }

                        leaf egress-hit-pkt {
                            type yang:zero-based-counter64;
                            description
                                "This object indicates the number of times an egress packet
                                 matched this entry.";
                        }

                        leaf egress-hit-byte {
                            type yang:zero-based-counter64;
                            description
                                "This object indicates the number of bytes of all egress
                                 packets that matched this entry.";
                        }

                        container ingress-rate-limiter {
                            description "Enter the ingress-rate-limiter context";

                            leaf offered-pkt {
                                type yang:zero-based-counter64;
                                description
                                    "Indicates how many ingress packets were subjected to rate-limiting filter
                                     action.";
                            }

                            leaf offered-byte {
                                type yang:zero-based-counter64;
                                description
                                    "Indicates the number of bytes of all ingress packets that were subjected to
                                     rate-limiting filter action.";
                            }

                            leaf forwarded-pkt {
                                type yang:zero-based-counter64;
                                description
                                    "Indicates how many ingress packets which were subjected to rate-limiting
                                     filter action were forwarded.";
                            }

                            leaf forwarded-byte {
                                type yang:zero-based-counter64;
                                description
                                    "Indicates the number of bytes of all ingress packets which were subjected
                                     to rate-limiting filter action were forwarded.";
                            }

                            leaf dropped-pkt {
                                type yang:zero-based-counter64;
                                description
                                    "Indicates how many ingress packets which were subjected to rate-limiting
                                     filter action were dropped.";
                            }

                            leaf dropped-byte {
                                type yang:zero-based-counter64;
                                description
                                    "Indicates the number of bytes of all ingress packets which were subjected
                                     to rate-limiting filter action were dropped.";
                            }

                        } // container ingress-rate-limiter

                        container egress-rate-limiter {
                            description "Enter the egress-rate-limiter context";

                            leaf offered-pkt {
                                type yang:zero-based-counter64;
                                description
                                    "Indicates how many egress packets were subjected to rate-limiting filter
                                     action.";
                            }

                            leaf offered-byte {
                                type yang:zero-based-counter64;
                                description
                                    "Indicates the number of bytes of all egress packets that were subjected to
                                     rate-limiting filter action.";
                            }

                            leaf forwarded-pkt {
                                type yang:zero-based-counter64;
                                description
                                    "Indicates how many egress packets which were subjected to rate-limiting
                                     filter action were forwarded.";
                            }

                            leaf forwarded-byte {
                                type yang:zero-based-counter64;
                                description
                                    "Indicates the number of bytes of all egress packets which were subjected
                                     to rate-limiting filter action were forwarded.";
                            }

                            leaf dropped-pkt {
                                type yang:zero-based-counter64;
                                description
                                    "Indicates how many egress packets which were subjected to rate-limiting
                                     filter action were dropped.";
                            }

                            leaf dropped-byte {
                                type yang:zero-based-counter64;
                                description
                                    "Indicates the number of bytes of all egress packets which were subjected
                                     to rate-limiting filter action were dropped.";
                            }

                        } // container egress-rate-limiter

                        list card {
                            key "slot-number";
                            description "Enter the card list instance";

                            leaf slot-number {
                                type types-card:iom-card-slot;
                                description "The unique value which identifies the IOM slot within a chassis in the system.";
                            }

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                            container ingress-rate-limiter {
                                description "Enter the ingress-rate-limiter context";

                                leaf offered-pkt {
                                    type yang:zero-based-counter64;
                                    description
                                        "This object indicates the number of times an ingress packet
                                         matched this entry.";
                                }

                                leaf offered-byte {
                                    type yang:zero-based-counter64;
                                    description
                                        "The value of this object indicates the number of bytes of
                                         all ingress packets that matched this entry.";
                                }

                                leaf forwarded-pkt {
                                    type yang:zero-based-counter64;
                                    description
                                        "This object indicates the number of times an ingress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container ingress-rate-limiter

                            container egress-rate-limiter {
                                description "Enter the egress-rate-limiter context";

                                leaf offered-pkt {
                                    type yang:zero-based-counter64;
                                    description
                                        "This object indicates the number of times an egress packet
                                         matched this entry.";
                                }

                                leaf offered-byte {
                                    type yang:zero-based-counter64;
                                    description
                                        "This object indicates the number of bytes of all egress
                                         packets that matched this entry.";
                                }

                                leaf forwarded-pkt {
                                    type yang:zero-based-counter64;
                                    description
                                        "This object indicates the number of times an egress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container egress-rate-limiter

                        } // list card

                    } // container statistics

                    container action {
                        description "Enter the action context";

                        leaf pbr-target-status {
                            type types-filter:pbr-target-status;
                            description "Indicates the PBR target status.";
                        }

                        container secondary {
                            description "Enter the secondary context";

                            leaf pbr-target-status {
                                type types-filter:pbr-target-status;
                                description "Indicates the PBR target status.";
                            }

                        } // container secondary

                    } // container action

                } // list entry

                container embed {
                    description "Enter the embed context";

                    list filter {
                        key "name offset";
                        description "Enter the filter list instance";

                        leaf name {
                            type leafref {
                                path "../../../../ip-filter/filter-name";
                            }
                            description "IPv4 policy to be embedded in the filter";
                        }

                        leaf offset {
                            type types-filter:embed-offset {
                                range "0..2097150";
                            }
                            description "Offset of the embedded filter policy";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list filter

                    list flowspec {
                        key "offset";
                        description "Enter the flowspec list instance";

                        leaf offset {
                            type types-filter:embed-offset;
                            description "Offset of the inserted entries";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list flowspec

                    list openflow {
                        key "of-switch offset";
                        description "Enter the openflow list instance";

                        leaf of-switch {
                            type leafref {
                                path "../../../../../openflow/of-switch/name";
                            }
                            description "Referenced Hybrid OpenFlow Switch (OFS) name";
                        }

                        leaf offset {
                            type types-filter:embed-offset {
                                range "0..2097150";
                            }
                            description "Offset of the embedded filter policy";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list openflow

                } // container embed

                container association {
                    description "Enter the association context";

                    leaf active-system-filter {
                        type boolean;
                        description "Indicates whether the filter is the active system filter";
                    }

                    leaf-list card {
                        type types-card:iom-card-slot;
                        description "Cards associated with the filter.";
                    }

                    list router {
                        key "router-name";
                        description "Enter the router list instance";

                        leaf router-name {
                            type types-sros:named-item-64;
                            description "The administrative name of a virtual router";
                        }

                        leaf nat-outside-upstream {
                            type boolean;
                            description "Indicates if filter is configured as NAT outside upstream filter.";
                        }

                        leaf nat-outside-downstream {
                            type boolean;
                            description "Indicates if filter is configured as NAT outside downstream filter.";
                        }

                        list interface {
                            key "interface-name";
                            description "Enter the interface list instance";

                            leaf interface-name {
                                type types-sros:interface-name;
                                description "Filter is associated with the Router interface.";
                            }

                            leaf ingress {
                                type boolean;
                                description "Indicates if filter is configured on ingress.";
                            }

                            leaf egress {
                                type boolean;
                                description "Indicates if filter is configured on egress.";
                            }

                        } // list interface

                    } // list router

                    list service {
                        key "service-name";
                        description "Enter the service list instance";

                        leaf service-name {
                            type types-sros:named-item-64;
                            description "Service name.";
                        }

                        leaf service-type {
                            type types-services:service-type;
                            description "Service type.";
                        }

                        leaf nat-inside-downstream {
                            type boolean;
                            description "Indicates if filter is configured as NAT inside downstream filter.";
                        }

                        leaf nat-outside-upstream {
                            type boolean;
                            description "Indicates if filter is configured as NAT outside upstream filter.";
                        }

                        leaf nat-outside-downstream {
                            type boolean;
                            description "Indicates if filter is configured as NAT outside downstream filter.";
                        }

                        leaf network-ingress {
                            type boolean;
                            description "Filter is associated with network ingress";
                        }

                        list sap {
                            key "sap-id";
                            description "Enter the sap list instance";

                            leaf sap-id {
                                type types-sros:sap;
                                description "Filter is associated with the SAP ID.";
                            }

                            leaf ingress {
                                type boolean;
                                description "Indicates if filter is configured on ingress.";
                            }

                            leaf egress {
                                type boolean;
                                description "Indicates if filter is configured on egress.";
                            }

                        } // list sap

                        list sdp-bind {
                            key "sdp-bind-id";
                            description "Enter the sdp-bind list instance";

                            leaf sdp-bind-id {
                                type types-services:sdp-bind-id;
                                description "Filter is associated with the SDP bind ID.";
                            }

                            leaf ingress {
                                type boolean;
                                description "Indicates if filter is configured on ingress.";
                            }

                            leaf egress {
                                type boolean;
                                description "Indicates if filter is configured on egress.";
                            }

                        } // list sdp-bind

                        list router-interface {
                            key "interface-name";
                            description "Enter the router-interface list instance";

                            leaf interface-name {
                                type types-sros:interface-name;
                                description "Filter is associated with the Router interface.";
                            }

                            leaf ingress {
                                type boolean;
                                description "Indicates if filter is configured on ingress.";
                            }

                            leaf egress {
                                type boolean;
                                description "Indicates if filter is configured on egress.";
                            }

                        } // list router-interface

                    } // list service

                    list sla-profile {
                        key "sla-profile-name";
                        description "Enter the sla-profile list instance";

                        leaf sla-profile-name {
                            type types-sros:named-item;
                            description "SLA profile name.";
                        }

                        leaf ingress {
                            type boolean;
                            description "Indicates if filter is configured on ingress.";
                        }

                        leaf egress {
                            type boolean;
                            description "Indicates if filter is configured on egress.";
                        }

                        leaf one-time-http-redirect {
                            type boolean;
                            description "Filter is used for one-time HTTP redirect.";
                        }

                    } // list sla-profile

                    list epipe-sap-template {
                        key "name";
                        description "Enter the epipe-sap-template list instance";

                        leaf name {
                            type types-sros:named-item;
                            description "SAP template name";
                        }

                        leaf ingress {
                            type boolean;
                            description "Indicates if filter is configured on ingress.";
                        }

                        leaf egress {
                            type boolean;
                            description "Indicates if filter is configured on egress.";
                        }

                    } // list epipe-sap-template

                    list embedding {
                        key "filter";
                        description "Enter the embedding list instance";

                        leaf filter {
                            type types-filter:filter-name;
                            description "The name of the filter policy that embeds this filter";
                        }

                    } // list embedding

                } // container association

            } // list ip-filter

            list ipv6-filter {
                key "filter-name";
                description "Enter the ipv6-filter list instance";

                leaf filter-name {
                    type types-filter:filter-name;
                    description "Filter name";
                }

                leaf origin {
                    type enumeration {
                        enum "config"                       { value 0; }
                        enum "flowspec"                     { value 1; }
                        enum "subscriber-mgmt"              { value 2; }
                        enum "openflow"                     { value 4; }
                        enum "vsd"                          { value 5; }
                        enum "tli"                          { value 6; }
                        enum "dynamic-services"             { value 7; }
                    }
                    description "The protocol or mechanism that created this filter.";
                }

                leaf applied {
                    type boolean;
                    description "Indicates whether the filter is applied.";
                }

                leaf num-entries {
                    type uint32;
                    description "Number of entries in this filter.";
                }

                leaf oper-filter-id {
                    type uint32;
                    description
                        "The value of this object uniquely identifies a filter.
                         User-configured filters have values between (1..65535).
                         Other values are reserved for filters that are created
                         (auto-generated) by the system.";
                }

                leaf num-sub-entries {
                    type uint32;
                    description "Number of sub-entries.";
                }

                leaf num-cam-entries-fp2 {
                    type uint32;
                    description "Number of CAM entries required on FP2 or FP3 based line cards";
                }

                leaf num-cam-entries-fp4 {
                    type uint32;
                    description "Number of CAM entries required on FP4 (or higher) based line cards";
                }

                container subscriber-mgmt {
                    description "Enter the subscriber-mgmt context";

                    container host-specific-entry {
                        description "Enter the host-specific-entry context";

                        container filter-rule {
                            description "Enter the filter-rule context";

                            leaf num-inserted {
                                type uint32;
                                description
                                    "Indicates how many host specific filter-rule entries are
                                     currently inserted in the filter on request of RADIUS/DIAMETER.";
                            }

                        } // container filter-rule

                        container credit-control {
                            description "Enter the credit-control context";

                            leaf num-inserted {
                                type uint32;
                                description
                                    "Indicates how many filter entries are currently inserted
                                     in the filter on request of credit control.";
                            }

                        } // container credit-control

                    } // container host-specific-entry

                    container shared-entry {
                        description "Enter the shared-entry context";

                        leaf num-filters {
                            type uint32;
                            description
                                "Indicates how many filters are currently created based on
                                 subscriber management shared entries of this filter.";
                        }

                        container filter-rule {
                            description "Enter the filter-rule context";

                            leaf num-inserted {
                                type uint32;
                                description
                                    "The value of this object indicates how many host common filter-rule entries are
                                     currently inserted in the filter on request of RADIUS.";
                            }

                        } // container filter-rule

                        container pcc-rule {
                            description "Enter the pcc-rule context";

                            leaf num-inserted {
                                type uint32;
                                description
                                    "The value of this object indicates how many pcc-rule filter entries received from
                                     DIAMETER have been inserted in this filter.";
                            }

                        } // container pcc-rule

                    } // container shared-entry

                } // container subscriber-mgmt

                list entry {
                    key "entry-id";
                    description "Enter the entry list instance";

                    leaf entry-id {
                        type types-filter:entry-id;
                        description "ID for a match criteria and the corresponding action";
                    }

                    leaf inserted-by {
                        type enumeration {
                            enum "fixed"                        { value 0; }
                            enum "filter-rule"                  { value 1; }
                            enum "credit-control"               { value 2; }
                            enum "flowspec"                     { value 3; }
                            enum "li"                           { value 4; }
                            enum "embedded"                     { value 5; }
                            enum "shared-filter-rule"           { value 6; }
                            enum "openflow"                     { value 7; }
                            enum "pcc"                          { value 8; }
                            enum "vsd"                          { value 9; }
                            enum "tli"                          { value 10; }
                            enum "dynamic-services"             { value 11; }
                        }
                        description "The protocol or mechanism that inserted this entry.";
                    }

                    leaf num-sub-entries {
                        type uint32;
                        description "Number of sub-entries.";
                    }

                    leaf num-cam-entries-fp2 {
                        type uint32;
                        description "Number of CAM entries required on FP2 or FP3 based line cards";
                    }

                    leaf num-cam-entries-fp4 {
                        type uint32;
                        description "Number of CAM entries required on FP4 (or higher) based line cards";
                    }

                    leaf log-instantiated {
                        type boolean;
                        description
                            "This object indicates if the filter log for this filter
                             entry has been instantiated or not.";
                    }

                    leaf downloaded-action {
                        type types-filter:filter-downloaded-action;
                        description
                            "The value of this object indicates the filter entry
                             action downloaded to IOM.";
                    }

                    leaf pbr-down-action {
                        type enumeration {
                            enum "drop"                         { value 1; }
                            enum "forward"                      { value 2; }
                        }
                        description
                            "Estimation of action performed if PBR target is down. This takes into
                             account configuration of PBR down action override, filter default action, and default
                             behavior of a filter action. But does not take into account where filter is applied
                             therefore performed action may differ at the end.";
                    }

                    leaf pbr-down-action-reason {
                        type enumeration {
                            enum "entry-default"                { value 1; }
                            enum "filter-default"               { value 2; }
                            enum "pbr-down-override"            { value 3; }
                        }
                        description "The source of the estimated value of PBR down action.";
                    }

                    leaf sticky-dest-hold-remain {
                        type int32 {
                            range "0..65535";
                        }
                        units "seconds";
                        description
                            "The value of this object indicates the remaining
                             time in seconds, until the best action will become
                             active and will be fixed.

                             Best action is:
                             - primary action if PBR target status of primary
                             action is up.
                             - secondary action if PBR target status of secondary
                             action is up and PBR target status of primary action
                             is down.
                             - none if both PBR targets are down.";
                    }

                    leaf inserted-by-direction {
                        type enumeration {
                            enum "ingress"                      { value 0; }
                            enum "egress"                       { value 1; }
                        }
                        description "The direction specified in shared filter rule causing creation of the entry.";
                    }

                    container embedding {
                        description "Enter the embedding context";

                        leaf origin {
                            type enumeration {
                                enum "fixed"                        { value 0; }
                                enum "flowspec"                     { value 3; }
                                enum "openflow"                     { value 7; }
                                enum "vsd"                          { value 9; }
                            }
                            description "Indicates the origin of the embedded filter which is the source of the entry embedded at this position.";
                        }

                        leaf filter-name {
                            type types-filter:filter-name;
                            description "Indicates the name of the embedded filter which is the source of the entry embedded at this position.";
                        }

                        leaf entry-id {
                            type types-filter:entry-id;
                            description "Indicates entry-id of embedded filter which was inserted at this position.";
                        }

                    } // container embedding

                    container statistics {
                        description "Enter the statistics context";

                        leaf ingress-hit-pkt {
                            type yang:zero-based-counter64;
                            description
                                "This object indicates the number of times an ingress packet
                                 matched this entry.";
                        }

                        leaf ingress-hit-byte {
                            type yang:zero-based-counter64;
                            description
                                "The value of this object indicates the number of bytes of
                                 all ingress packets that matched this entry.";
                        }

                        leaf egress-hit-pkt {
                            type yang:zero-based-counter64;
                            description
                                "This object indicates the number of times an egress packet
                                 matched this entry.";
                        }

                        leaf egress-hit-byte {
                            type yang:zero-based-counter64;
                            description
                                "This object indicates the number of bytes of all egress
                                 packets that matched this entry.";
                        }

                        container ingress-rate-limiter {
                            description "Enter the ingress-rate-limiter context";

                            leaf offered-pkt {
                                type yang:zero-based-counter64;
                                description
                                    "Indicates how many ingress packets were subjected to rate-limiting filter
                                     action.";
                            }

                            leaf offered-byte {
                                type yang:zero-based-counter64;
                                description
                                    "Indicates the number of bytes of all ingress packets that were subjected to
                                     rate-limiting filter action.";
                            }

                            leaf forwarded-pkt {
                                type yang:zero-based-counter64;
                                description
                                    "Indicates how many ingress packets which were subjected to rate-limiting
                                     filter action were forwarded.";
                            }

                            leaf forwarded-byte {
                                type yang:zero-based-counter64;
                                description
                                    "Indicates the number of bytes of all ingress packets which were subjected
                                     to rate-limiting filter action were forwarded.";
                            }

                            leaf dropped-pkt {
                                type yang:zero-based-counter64;
                                description
                                    "Indicates how many ingress packets which were subjected to rate-limiting
                                     filter action were dropped.";
                            }

                            leaf dropped-byte {
                                type yang:zero-based-counter64;
                                description
                                    "Indicates the number of bytes of all ingress packets which were subjected
                                     to rate-limiting filter action were dropped.";
                            }

                        } // container ingress-rate-limiter

                        container egress-rate-limiter {
                            description "Enter the egress-rate-limiter context";

                            leaf offered-pkt {
                                type yang:zero-based-counter64;
                                description
                                    "Indicates how many egress packets were subjected to rate-limiting filter
                                     action.";
                            }

                            leaf offered-byte {
                                type yang:zero-based-counter64;
                                description
                                    "Indicates the number of bytes of all egress packets that were subjected to
                                     rate-limiting filter action.";
                            }

                            leaf forwarded-pkt {
                                type yang:zero-based-counter64;
                                description
                                    "Indicates how many egress packets which were subjected to rate-limiting
                                     filter action were forwarded.";
                            }

                            leaf forwarded-byte {
                                type yang:zero-based-counter64;
                                description
                                    "Indicates the number of bytes of all egress packets which were subjected
                                     to rate-limiting filter action were forwarded.";
                            }

                            leaf dropped-pkt {
                                type yang:zero-based-counter64;
                                description
                                    "Indicates how many egress packets which were subjected to rate-limiting
                                     filter action were dropped.";
                            }

                            leaf dropped-byte {
                                type yang:zero-based-counter64;
                                description
                                    "Indicates the number of bytes of all egress packets which were subjected
                                     to rate-limiting filter action were dropped.";
                            }

                        } // container egress-rate-limiter

                        list card {
                            key "slot-number";
                            description "Enter the card list instance";

                            leaf slot-number {
                                type types-card:iom-card-slot;
                                description "The unique value which identifies the IOM slot within a chassis in the system.";
                            }

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                            container ingress-rate-limiter {
                                description "Enter the ingress-rate-limiter context";

                                leaf offered-pkt {
                                    type yang:zero-based-counter64;
                                    description
                                        "This object indicates the number of times an ingress packet
                                         matched this entry.";
                                }

                                leaf offered-byte {
                                    type yang:zero-based-counter64;
                                    description
                                        "The value of this object indicates the number of bytes of
                                         all ingress packets that matched this entry.";
                                }

                                leaf forwarded-pkt {
                                    type yang:zero-based-counter64;
                                    description
                                        "This object indicates the number of times an ingress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container ingress-rate-limiter

                            container egress-rate-limiter {
                                description "Enter the egress-rate-limiter context";

                                leaf offered-pkt {
                                    type yang:zero-based-counter64;
                                    description
                                        "This object indicates the number of times an egress packet
                                         matched this entry.";
                                }

                                leaf offered-byte {
                                    type yang:zero-based-counter64;
                                    description
                                        "This object indicates the number of bytes of all egress
                                         packets that matched this entry.";
                                }

                                leaf forwarded-pkt {
                                    type yang:zero-based-counter64;
                                    description
                                        "This object indicates the number of times an egress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container egress-rate-limiter

                        } // list card

                    } // container statistics

                    container action {
                        description "Enter the action context";

                        leaf pbr-target-status {
                            type types-filter:pbr-target-status;
                            description "Indicates the PBR target status.";
                        }

                        container secondary {
                            description "Enter the secondary context";

                            leaf pbr-target-status {
                                type types-filter:pbr-target-status;
                                description "Indicates the PBR target status.";
                            }

                        } // container secondary

                    } // container action

                } // list entry

                container embed {
                    description "Enter the embed context";

                    list filter {
                        key "name offset";
                        description "Enter the filter list instance";

                        leaf name {
                            type leafref {
                                path "../../../../ipv6-filter/filter-name";
                            }
                            description "IPv6 policy to be embedded in the filter";
                        }

                        leaf offset {
                            type types-filter:embed-offset {
                                range "0..2097150";
                            }
                            description "Offset of the embedded filter policy";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list filter

                    list flowspec {
                        key "offset";
                        description "Enter the flowspec list instance";

                        leaf offset {
                            type types-filter:embed-offset;
                            description "Offset of the inserted entries";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list flowspec

                    list openflow {
                        key "of-switch offset";
                        description "Enter the openflow list instance";

                        leaf of-switch {
                            type leafref {
                                path "../../../../../openflow/of-switch/name";
                            }
                            description "Referenced Hybrid OpenFlow Switch (OFS) name";
                        }

                        leaf offset {
                            type types-filter:embed-offset {
                                range "0..2097150";
                            }
                            description "Offset of the embedded filter policy";
                        }

                        leaf oper-state {
                            type types-filter:embed-oper-state;
                            description "Indicates the operational state of this embedding.";
                        }

                        leaf num-entries {
                            type uint32;
                            description "Indicates the total number of entries in the embedded filter.";
                        }

                        leaf num-inserted {
                            type uint32;
                            description "Indicates the number of successfully embedded entries.";
                        }

                    } // list openflow

                } // container embed

                container association {
                    description "Enter the association context";

                    leaf active-system-filter {
                        type boolean;
                        description "Indicates whether the filter is the active system filter";
                    }

                    leaf-list card {
                        type types-card:iom-card-slot;
                        description "Cards associated with the filter.";
                    }

                    list router {
                        key "router-name";
                        description "Enter the router list instance";

                        leaf router-name {
                            type types-sros:named-item-64;
                            description "The administrative name of a virtual router";
                        }

                        leaf nat-outside-upstream {
                            type boolean;
                            description "Indicates if filter is configured as NAT outside upstream filter.";
                        }

                        leaf nat-outside-downstream {
                            type boolean;
                            description "Indicates if filter is configured as NAT outside downstream filter.";
                        }

                        list interface {
                            key "interface-name";
                            description "Enter the interface list instance";

                            leaf interface-name {
                                type types-sros:interface-name;
                                description "Filter is associated with the Router interface.";
                            }

                            leaf ingress {
                                type boolean;
                                description "Indicates if filter is configured on ingress.";
                            }

                            leaf egress {
                                type boolean;
                                description "Indicates if filter is configured on egress.";
                            }

                        } // list interface

                    } // list router

                    list service {
                        key "service-name";
                        description "Enter the service list instance";

                        leaf service-name {
                            type types-sros:named-item-64;
                            description "Service name.";
                        }

                        leaf service-type {
                            type types-services:service-type;
                            description "Service type.";
                        }

                        leaf nat-inside-downstream {
                            type boolean;
                            description "Indicates if filter is configured as NAT inside downstream filter.";
                        }

                        leaf nat-outside-upstream {
                            type boolean;
                            description "Indicates if filter is configured as NAT outside upstream filter.";
                        }

                        leaf nat-outside-downstream {
                            type boolean;
                            description "Indicates if filter is configured as NAT outside downstream filter.";
                        }

                        leaf network-ingress {
                            type boolean;
                            description "Filter is associated with network ingress";
                        }

                        list sap {
                            key "sap-id";
                            description "Enter the sap list instance";

                            leaf sap-id {
                                type types-sros:sap;
                                description "Filter is associated with the SAP ID.";
                            }

                            leaf ingress {
                                type boolean;
                                description "Indicates if filter is configured on ingress.";
                            }

                            leaf egress {
                                type boolean;
                                description "Indicates if filter is configured on egress.";
                            }

                        } // list sap

                        list sdp-bind {
                            key "sdp-bind-id";
                            description "Enter the sdp-bind list instance";

                            leaf sdp-bind-id {
                                type types-services:sdp-bind-id;
                                description "Filter is associated with the SDP bind ID.";
                            }

                            leaf ingress {
                                type boolean;
                                description "Indicates if filter is configured on ingress.";
                            }

                            leaf egress {
                                type boolean;
                                description "Indicates if filter is configured on egress.";
                            }

                        } // list sdp-bind

                        list router-interface {
                            key "interface-name";
                            description "Enter the router-interface list instance";

                            leaf interface-name {
                                type types-sros:interface-name;
                                description "Filter is associated with the Router interface.";
                            }

                            leaf ingress {
                                type boolean;
                                description "Indicates if filter is configured on ingress.";
                            }

                            leaf egress {
                                type boolean;
                                description "Indicates if filter is configured on egress.";
                            }

                        } // list router-interface

                    } // list service

                    list sla-profile {
                        key "sla-profile-name";
                        description "Enter the sla-profile list instance";

                        leaf sla-profile-name {
                            type types-sros:named-item;
                            description "SLA profile name.";
                        }

                        leaf ingress {
                            type boolean;
                            description "Indicates if filter is configured on ingress.";
                        }

                        leaf egress {
                            type boolean;
                            description "Indicates if filter is configured on egress.";
                        }

                    } // list sla-profile

                    list epipe-sap-template {
                        key "name";
                        description "Enter the epipe-sap-template list instance";

                        leaf name {
                            type types-sros:named-item;
                            description "SAP template name";
                        }

                        leaf ingress {
                            type boolean;
                            description "Indicates if filter is configured on ingress.";
                        }

                        leaf egress {
                            type boolean;
                            description "Indicates if filter is configured on egress.";
                        }

                    } // list epipe-sap-template

                    list embedding {
                        key "filter";
                        description "Enter the embedding list instance";

                        leaf filter {
                            type types-filter:filter-name;
                            description "The name of the filter policy that embeds this filter";
                        }

                    } // list embedding

                } // container association

            } // list ipv6-filter

            list mac-filter {
                key "filter-name";
                description "Enter the mac-filter list instance";

                leaf filter-name {
                    type types-filter:filter-name;
                    description "Filter name";
                }

                leaf origin {
                    type enumeration {
                        enum "config"                       { value 0; }
                        enum "flowspec"                     { value 1; }
                        enum "subscriber-mgmt"              { value 2; }
                        enum "openflow"                     { value 4; }
                        enum "vsd"                          { value 5; }
                        enum "tli"                          { value 6; }
                        enum "dynamic-services"             { value 7; }
                    }
                    description "The protocol or mechanism that created this filter.";
                }

                leaf applied {
                    type boolean;
                    description "Indicates whether the filter is applied.";
                }

                leaf num-entries {
                    type uint32;
                    description "Number of entries in this filter.";
                }

                leaf oper-filter-id {
                    type uint32;
                    description
                        "The value of this object uniquely identifies a filter.
                         User-configured filters have values between (1..65535).
                         Other values are reserved for filters that are created
                         (auto-generated) by the system.";
                }

                leaf num-sub-entries {
                    type uint32;
                    description "Number of sub-entries.";
                }

                leaf num-cam-entries-fp2 {
                    type uint32;
                    description "Number of CAM entries required on FP2 or FP3 based line cards";
                }

                leaf num-cam-entries-fp4 {
                    type uint32;
                    description "Number of CAM entries required on FP4 (or higher) based line cards";
                }

                list entry {
                    key "entry-id";
                    description "Enter the entry list instance";

                    leaf entry-id {
                        type types-filter:entry-id;
                        description "ID for a match criteria and the corresponding action";
                    }

                    leaf inserted-by {
                        type enumeration {
                            enum "fixed"                        { value 0; }
                            enum "filter-rule"                  { value 1; }
                            enum "credit-control"               { value 2; }
                            enum "flowspec"                     { value 3; }
                            enum "li"                           { value 4; }
                            enum "embedded"                     { value 5; }
                            enum "shared-filter-rule"           { value 6; }
                            enum "openflow"                     { value 7; }
                            enum "pcc"                          { value 8; }
                            enum "vsd"                          { value 9; }
                            enum "tli"                          { value 10; }
                            enum "dynamic-services"             { value 11; }
                        }
                        description "The protocol or mechanism that inserted this entry.";
                    }

                    leaf num-sub-entries {
                        type uint32;
                        description "Number of sub-entries.";
                    }

                    leaf num-cam-entries-fp2 {
                        type uint32;
                        description "Number of CAM entries required on FP2 or FP3 based line cards";
                    }

                    leaf num-cam-entries-fp4 {
                        type uint32;
                        description "Number of CAM entries required on FP4 (or higher) based line cards";
                    }

                    leaf log-instantiated {
                        type boolean;
                        description
                            "This object indicates if the filter log for this filter
                             entry has been instantiated or not.";
                    }

                    leaf downloaded-action {
                        type types-filter:filter-downloaded-action;
                        description
                            "The value of this object indicates the filter entry
                             action downloaded to IOM.";
                    }

                    leaf pbr-down-action {
                        type enumeration {
                            enum "drop"                         { value 1; }
                            enum "forward"                      { value 2; }
                        }
                        description
                            "Estimation of action performed if PBR target is down. This takes into
                             account configuration of PBR down action override, filter default action, and default
                             behavior of a filter action. But does not take into account where filter is applied
                             therefore performed action may differ at the end.";
                    }

                    leaf pbr-down-action-reason {
                        type enumeration {
                            enum "entry-default"                { value 1; }
                            enum "filter-default"               { value 2; }
                            enum "pbr-down-override"            { value 3; }
                        }
                        description "The source of the estimated value of PBR down action.";
                    }

                    leaf sticky-dest-hold-remain {
                        type int32 {
                            range "0..65535";
                        }
                        units "seconds";
                        description
                            "The value of this object indicates the remaining
                             time in seconds, until the best action will become
                             active and will be fixed.

                             Best action is:
                             - primary action if PBR target status of primary
                             action is up.
                             - secondary action if PBR target status of secondary
                             action is up and PBR target status of primary action
                             is down.
                             - none if both PBR targets are down.";
                    }

                    container embedding {
                        description "Enter the embedding context";

                        leaf origin {
                            type enumeration {
                                enum "fixed"                        { value 0; }
                                enum "flowspec"                     { value 3; }
                                enum "openflow"                     { value 7; }
                                enum "vsd"                          { value 9; }
                            }
                            description "Indicates the origin of the embedded filter which is the source of the entry embedded at this position.";
                        }

                        leaf filter-name {
                            type types-filter:filter-name;
                            description "Indicates the name of the embedded filter which is the source of the entry embedded at this position.";
                        }

                        leaf entry-id {
                            type types-filter:entry-id;
                            description "Indicates entry-id of embedded filter which was inserted at this position.";
                        }

                    } // container embedding

                    container statistics {
                        description "Enter the statistics context";

                        leaf ingress-hit-pkt {
                            type yang:zero-based-counter64;
                            description
                                "This object indicates the number of times an ingress packet
                                 matched this entry.";
                        }

                        leaf ingress-hit-byte {
                            type yang:zero-based-counter64;
                            description
                                "The value of this object indicates the number of bytes of
                                 all ingress packets that matched this entry.";
                        }

                        leaf egress-hit-pkt {
                            type yang:zero-based-counter64;
                            description
                                "This object indicates the number of times an egress packet
                                 matched this entry.";
                        }

                        leaf egress-hit-byte {
                            type yang:zero-based-counter64;
                            description
                                "This object indicates the number of bytes of all egress
                                 packets that matched this entry.";
                        }

                        container ingress-rate-limiter {
                            description "Enter the ingress-rate-limiter context";

                            leaf offered-pkt {
                                type yang:zero-based-counter64;
                                description
                                    "Indicates how many ingress packets were subjected to rate-limiting filter
                                     action.";
                            }

                            leaf offered-byte {
                                type yang:zero-based-counter64;
                                description
                                    "Indicates the number of bytes of all ingress packets that were subjected to
                                     rate-limiting filter action.";
                            }

                            leaf forwarded-pkt {
                                type yang:zero-based-counter64;
                                description
                                    "Indicates how many ingress packets which were subjected to rate-limiting
                                     filter action were forwarded.";
                            }

                            leaf forwarded-byte {
                                type yang:zero-based-counter64;
                                description
                                    "Indicates the number of bytes of all ingress packets which were subjected
                                     to rate-limiting filter action were forwarded.";
                            }

                            leaf dropped-pkt {
                                type yang:zero-based-counter64;
                                description
                                    "Indicates how many ingress packets which were subjected to rate-limiting
                                     filter action were dropped.";
                            }

                            leaf dropped-byte {
                                type yang:zero-based-counter64;
                                description
                                    "Indicates the number of bytes of all ingress packets which were subjected
                                     to rate-limiting filter action were dropped.";
                            }

                        } // container ingress-rate-limiter

                        container egress-rate-limiter {
                            description "Enter the egress-rate-limiter context";

                            leaf offered-pkt {
                                type yang:zero-based-counter64;
                                description
                                    "Indicates how many egress packets were subjected to rate-limiting filter
                                     action.";
                            }

                            leaf offered-byte {
                                type yang:zero-based-counter64;
                                description
                                    "Indicates the number of bytes of all egress packets that were subjected to
                                     rate-limiting filter action.";
                            }

                            leaf forwarded-pkt {
                                type yang:zero-based-counter64;
                                description
                                    "Indicates how many egress packets which were subjected to rate-limiting
                                     filter action were forwarded.";
                            }

                            leaf forwarded-byte {
                                type yang:zero-based-counter64;
                                description
                                    "Indicates the number of bytes of all egress packets which were subjected
                                     to rate-limiting filter action were forwarded.";
                            }

                            leaf dropped-pkt {
                                type yang:zero-based-counter64;
                                description
                                    "Indicates how many egress packets which were subjected to rate-limiting
                                     filter action were dropped.";
                            }

                            leaf dropped-byte {
                                type yang:zero-based-counter64;
                                description
                                    "Indicates the number of bytes of all egress packets which were subjected
                                     to rate-limiting filter action were dropped.";
                            }

                        } // container egress-rate-limiter

                        list card {
                            key "slot-number";
                            description "Enter the card list instance";

                            leaf slot-number {
                                type types-card:iom-card-slot;
                                description "The unique value which identifies the IOM slot within a chassis in the system.";
                            }

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                            container ingress-rate-limiter {
                                description "Enter the ingress-rate-limiter context";

                                leaf offered-pkt {
                                    type yang:zero-based-counter64;
                                    description
                                        "This object indicates the number of times an ingress packet
                                         matched this entry.";
                                }

                                leaf offered-byte {
                                    type yang:zero-based-counter64;
                                    description
                                        "The value of this object indicates the number of bytes of
                                         all ingress packets that matched this entry.";
                                }

                                leaf forwarded-pkt {
                                    type yang:zero-based-counter64;
                                    description
                                        "This object indicates the number of times an ingress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container ingress-rate-limiter

                            container egress-rate-limiter {
                                description "Enter the egress-rate-limiter context";

                                leaf offered-pkt {
                                    type yang:zero-based-counter64;
                                    description
                                        "This object indicates the number of times an egress packet
                                         matched this entry.";
                                }

                                leaf offered-byte {
                                    type yang:zero-based-counter64;
                                    description
                                        "This object indicates the number of bytes of all egress
                                         packets that matched this entry.";
                                }

                                leaf forwarded-pkt {
                                    type yang:zero-based-counter64;
                                    description
                                        "This object indicates the number of times an egress packet
                                         matched this entry.";
                                }

                                leaf forwarded-byte {
                                    type yang:zero-based-counter64;
                                    description
                                        "This object indicates the number of bytes of all egress
                                         packets that matched this entry.";
                                }

                                leaf dropped-pkt {
                                    type yang:zero-based-counter64;
                                    description
                                        "This object indicates the number of times an egress packet
                                         matched this entry.";
                                }

                                leaf dropped-byte {
                                    type yang:zero-based-counter64;
                                    description
                                        "This object indicates the number of bytes of all egress
                                         packets that matched this entry.";
                                }

                            } // container egress-rate-limiter

                        } // list card

                    } // container statistics

                    container action {
                        description "Enter the action context";

                        leaf pbr-target-status {
                            type types-filter:pbr-target-status;
                            description "Indicates the PBR target status.";
                        }

                        container secondary {
                            description "Enter the secondary context";

                            leaf pbr-target-status {
                                type types-filter:pbr-target-status;
                                description "Indicates the PBR target status.";
                            }

                        } // container secondary

                    } // container action

                } // list entry

                container embed {
                    description "Enter the embed context";

                } // container embed

                container association {
                    description "Enter the association context";

                    leaf-list card {
                        type types-card:iom-card-slot;
                        description "Cards associated with the filter.";
                    }

                    list service {
                        key "service-name";
                        description "Enter the service list instance";

                        leaf service-name {
                            type types-sros:named-item-64;
                            description "Service name.";
                        }

                        leaf service-type {
                            type types-services:service-type;
                            description "Service type.";
                        }

                        list sap {
                            key "sap-id";
                            description "Enter the sap list instance";

                            leaf sap-id {
                                type types-sros:sap;
                                description "Filter is associated with the SAP ID.";
                            }

                            leaf ingress {
                                type boolean;
                                description "Indicates if filter is configured on ingress.";
                            }

                            leaf egress {
                                type boolean;
                                description "Indicates if filter is configured on egress.";
                            }

                        } // list sap

                        list sdp-bind {
                            key "sdp-bind-id";
                            description "Enter the sdp-bind list instance";

                            leaf sdp-bind-id {
                                type types-services:sdp-bind-id;
                                description "Filter is associated with the SDP bind ID.";
                            }

                            leaf ingress {
                                type boolean;
                                description "Indicates if filter is configured on ingress.";
                            }

                            leaf egress {
                                type boolean;
                                description "Indicates if filter is configured on egress.";
                            }

                        } // list sdp-bind

                    } // list service

                    list epipe-sap-template {
                        key "name";
                        description "Enter the epipe-sap-template list instance";

                        leaf name {
                            type types-sros:named-item;
                            description "SAP template name";
                        }

                        leaf ingress {
                            type boolean;
                            description "Indicates if filter is configured on ingress.";
                        }

                        leaf egress {
                            type boolean;
                            description "Indicates if filter is configured on egress.";
                        }

                    } // list epipe-sap-template

                    list embedding {
                        key "filter";
                        description "Enter the embedding list instance";

                        leaf filter {
                            type types-filter:filter-name;
                            description "The name of the filter policy that embeds this filter";
                        }

                    } // list embedding

                } // container association

            } // list mac-filter

            container overload {
                description "Enter the overload context";

                list card {
                    key "slot-number";
                    description "Enter the card list instance";

                    leaf slot-number {
                        type types-card:iom-card-slot;
                        description "The unique value which identifies the IOM slot within a chassis in the system.";
                    }

                    list fp {
                        key "fp-number";
                        description "Enter the fp list instance";

                        leaf fp-number {
                            type types-card:fp-id;
                            description
                                "The unique value which uniquely identifies the forwarding plane within
                                 a specific IOM card in the system.";
                        }

                        leaf ingress-ip-mac {
                            type types-sros:cam-state;
                            description "Ingress IPv4-MAC filter CAM state";
                        }

                        leaf egress-ip-mac {
                            type types-sros:cam-state;
                            description "Egress IPv4-MAC filter CAM state";
                        }

                        leaf ingress-ipv6 {
                            type types-sros:cam-state;
                            description "Ingress IPv6 filter CAM state";
                        }

                        leaf egress-ipv6 {
                            type types-sros:cam-state;
                            description "Egress IPv6 filter CAM state";
                        }

                        container utilization {
                            description "Enter the utilization context";

                            leaf ingress-ip-mac {
                                type uint32 {
                                    range "0..100";
                                }
                                description "Ingress IPv4-MAC filter CAM utilization in percentage";
                            }

                            leaf egress-ip-mac {
                                type uint32 {
                                    range "0..100";
                                }
                                description "Egress IPv4-MAC filter CAM utilization in percentage";
                            }

                            leaf ingress-ipv6 {
                                type uint32 {
                                    range "0..100";
                                }
                                description "Ingress IPv6 filter CAM utilization in percentage";
                            }

                            leaf egress-ipv6 {
                                type uint32 {
                                    range "0..100";
                                }
                                description "Egress IPv6 filter CAM utilization in percentage";
                            }

                        } // container utilization

                        container overload-entries {
                            description "Enter the overload-entries context";

                            container ingress {
                                description "Enter the ingress context";

                                list ip-filter {
                                    key "filter-name";
                                    description "Enter the ip-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list ip-filter

                                list ipv6-filter {
                                    key "filter-name";
                                    description "Enter the ipv6-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list ipv6-filter

                                list mac-filter {
                                    key "filter-name";
                                    description "Enter the mac-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list mac-filter

                            } // container ingress

                            container egress {
                                description "Enter the egress context";

                                list ip-filter {
                                    key "filter-name";
                                    description "Enter the ip-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list ip-filter

                                list ipv6-filter {
                                    key "filter-name";
                                    description "Enter the ipv6-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list ipv6-filter

                                list mac-filter {
                                    key "filter-name";
                                    description "Enter the mac-filter list instance";

                                    leaf filter-name {
                                        type types-filter:filter-name;
                                        description "Filter name";
                                    }

                                    list entry {
                                        key "entry-id";
                                        description "Enter the entry list instance";

                                        leaf entry-id {
                                            type types-filter:entry-id;
                                            description "ID for a match criteria and the corresponding action";
                                        }

                                    } // list entry

                                } // list mac-filter

                            } // container egress

                        } // container overload-entries

                    } // list fp

                } // list card

            } // container overload

            uses state-filter-ip-exception;
            uses state-filter-ip-exception-ipv6-exception;
        } // container filter

    } // grouping state-filter

}
