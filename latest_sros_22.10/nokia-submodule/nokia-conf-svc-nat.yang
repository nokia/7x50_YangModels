submodule nokia-conf-svc-nat {

    yang-version "1.1";

    belongs-to nokia-conf { prefix "conf"; }

    import nokia-sros-yang-extensions     { prefix "sros-ext"; }
    import nokia-types-nat                { prefix "types-nat"; }
    import nokia-types-sros               { prefix "types-sros"; }

    include nokia-conf-groups;
    include nokia-conf-isa;
    include nokia-conf-service;
    include nokia-conf-svc-ipfix;


    sros-ext:sros-major-release "rel22";

    organization "Nokia";

    contact
        "Nokia SR OS Support
         Web: <http://www.nokia.com>";

    description
        "Nokia YANG Data model to configure NAT configuration common to all router instances on SR OS based routers.

         Copyright 2016 Nokia. All rights reserved. Reproduction of this document
         is authorized on the condition that the foregoing copyright notice is included.

         This nokia-conf-svc-nat YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-09-08";

    grouping conf-svc-nat {
        container nat {
            description "Enter the nat context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list firewall-policy {
                key "name";
                max-elements 2048;
                description "Enter the firewall-policy list instance";

                leaf name {
                    type types-sros:external-named-item;
                    description "Firewall policy name";
                }

                leaf description {
                    type types-sros:description;
                    description "Text description";
                }

                leaf filtering {
                    type types-nat:filtering;
                    description "Filtering method for inbound traffic for the policy";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice address-location {
                    case l2-outside {

                        leaf l2-outside {
                            type empty;
                            description "Use Layer 2 outside service address location";
                        }

                    }
                    case domain {

                        container domain {
                            description "Enter the domain context";

                            leaf router-instance {
                                type string;
                                description "Router or VPRN service name";
                            }

                            leaf name {
                                type types-sros:named-item;
                                description "Firewall domain name";
                            }

                        } // container domain

                    }
                }
                container alg {
                    description "Enter the alg context";

                    leaf ftp {
                        type boolean;
                        default "true";
                        description "Use FTP ALG for the policy";
                    }

                    leaf rtsp {
                        type boolean;
                        default "false";
                        description "Use RTSP ALG for the policy";
                    }

                    leaf sip {
                        type boolean;
                        default "false";
                        description "Use SIP ALG for the policy";
                    }

                } // container alg

                container port-limits {
                    description "Enter the port-limits context";

                    leaf forwarding {
                        type uint16 {
                            range "1..64";
                        }
                        description "Maximum number of port forwarding entries";
                    }

                } // container port-limits

                container priority-sessions {
                    description "Enter the priority-sessions context";

                    container fc {
                        description "Enter the fc context";

                        leaf be {
                            type boolean;
                            default "false";
                            description "Prioritize traffic from BE forwarding classes";
                        }

                        leaf l2 {
                            type boolean;
                            default "false";
                            description "Prioritize traffic from L2 forwarding classes";
                        }

                        leaf af {
                            type boolean;
                            default "false";
                            description "Prioritize traffic from AF forwarding classes";
                        }

                        leaf l1 {
                            type boolean;
                            default "false";
                            description "Prioritize traffic from L1 forwarding classes";
                        }

                        leaf h2 {
                            type boolean;
                            default "false";
                            description "Prioritize traffic from H2 forwarding classes";
                        }

                        leaf ef {
                            type boolean;
                            default "false";
                            description "Prioritize traffic from EF forwarding classes";
                        }

                        leaf h1 {
                            type boolean;
                            default "false";
                            description "Prioritize traffic from H1 forwarding classes";
                        }

                        leaf nc {
                            type boolean;
                            default "false";
                            description "Prioritize traffic from NC forwarding classes";
                        }

                    } // container fc

                } // container priority-sessions

                container session-limits {
                    description "Enter the session-limits context";

                    leaf max {
                        type uint16 {
                            range "1..65535";
                        }
                        default "65535";
                        description "Maximum number of sessions per subscriber";
                    }

                    leaf reserved {
                        type uint16 {
                            range "1..65534";
                        }
                        description "Number of sessions reserved for prioritized sessions";
                    }

                    container watermarks {
                        presence "Enable the watermarks context";
                        description "Enable the watermarks context";

                        leaf high {
                            type types-sros:percent;
                            mandatory true;
                            description "High watermark percentage";
                        }

                        leaf low {
                            type types-sros:percent;
                            mandatory true;
                            description "Low watermark percentage";
                        }

                    } // container watermarks

                } // container session-limits

                container tcp {
                    description "Enter the tcp context";

                    leaf mss-adjust {
                        type uint32 {
                            range "160..10240";
                        }
                        description "TCP MSS adjustment value";
                    }

                } // container tcp

                container timeouts {
                    description "Enter the timeouts context";

                    leaf icmp6-query {
                        type types-sros:time-duration {
                            range "60..240";
                        }
                        default "60";
                        description "Timeout applied to an ICMPv6 Query session";
                    }

                    leaf sip {
                        type types-sros:time-duration {
                            range "10..7200";
                        }
                        default "120";
                        description "SIP inactive media timeout";
                    }

                    leaf unknown-protocol {
                        type types-sros:time-duration {
                            range "60..86400";
                        }
                        sros-ext:isa-auto-clear-on-modify;
                        default "300";
                        description "Timeout for flows with an unknown protocol";
                    }

                    container tcp {
                        description "Enter the tcp context";

                        leaf established {
                            type types-sros:time-duration {
                                range "60..86400";
                            }
                            default "7440";
                            description "Idle timeout for TCP session in established state";
                        }

                        leaf rst {
                            type types-sros:time-duration {
                                range "0..240";
                            }
                            default "0";
                            description "Suspend time for TCP connection ports closed by RST";
                        }

                        leaf syn {
                            type types-sros:time-duration {
                                range "6..86400";
                            }
                            default "15";
                            description "TCP session timeout when synchronizing initial sequence";
                        }

                        leaf time-wait {
                            type types-sros:time-duration {
                                range "0..240";
                            }
                            default "0";
                            description "Timeout applied to a TCP session in the time-wait state";
                        }

                        leaf transitory {
                            type types-sros:time-duration {
                                range "60..86400";
                            }
                            default "240";
                            description "Idle timeout for TCP session in transitory state";
                        }

                    } // container tcp

                    container udp {
                        description "Enter the udp context";

                        leaf normal {
                            type types-sros:time-duration {
                                range "60..86400";
                            }
                            default "300";
                            description "UDP mapping timeout";
                        }

                        leaf dns {
                            type types-sros:time-duration {
                                range "15..86400";
                            }
                            default "15";
                            description "Timeout applied to UDP session with destination port 53";
                        }

                        leaf initial {
                            type types-sros:time-duration {
                                range "10..300";
                            }
                            default "15";
                            description "UDP mapping timeout applied to new sessions";
                        }

                    } // container udp

                } // container timeouts

                container udp {
                    description "Enter the udp context";

                    leaf inbound-refresh {
                        type boolean;
                        default "false";
                        description "Extend UDP session timeout on inbound traffic";
                    }

                } // container udp

                container unknown-protocols {
                    description "Enter the unknown-protocols context";

                    choice unknown-protocols {
                        case all {

                            leaf all {
                                type empty;
                                description "Allow all protocols to create unknown flows";
                            }

                        }
                        case protocol {

                            leaf-list protocol {
                                type uint8 {
                                    range "0..255";
                                }
                                max-elements 8;
                                description "IANA number of protocol allowed to create unknown flow";
                            }

                        }
                    }
                } // container unknown-protocols

            } // list firewall-policy

            list prefix-list {
                key "name";
                description "Enter the prefix-list list instance";

                leaf name {
                    type types-sros:named-item;
                    description "NAT prefix list name";
                }

                leaf application {
                    type types-nat:prefix-list-application;
                    sros-ext:immutable;
                    sros-ext:isa-auto-clear-on-modify;
                    description "Prefix list for the application";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list prefix {
                    key "ip-prefix";
                    max-elements 1024;
                    description "Enter the prefix list instance";

                    leaf ip-prefix {
                        type types-sros:ipv4-prefix;
                        description "NAT prefix";
                    }

                    leaf nat-policy {
                        type leafref {
                            path "../../../nat-policy/name";
                        }
                        sros-ext:immutable;
                        sros-ext:isa-auto-clear-on-modify;
                        description "NAT policy for LSN";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list prefix

            } // list prefix-list

            list pcp-server-policy {
                key "name";
                description "Enter the pcp-server-policy list instance";

                leaf name {
                    type types-sros:named-item;
                    description "PCP server policy name";
                }

                leaf description {
                    type types-sros:description;
                    description "Text description";
                }

                leaf max-description-size {
                    type uint32 {
                        range "1..64";
                    }
                    default "64";
                    description "Maximum length of mapping descriptions made by the PCP servers";
                }

                leaf reuse-external-ip-address {
                    type boolean;
                    default "false";
                    description "Reuse external IP address for NAT subscriber";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container lifetime {
                    description "Enter the lifetime context";

                    leaf minimum {
                        type uint32 {
                            range "60..86399";
                        }
                        default "120";
                        description "Minimum lifetime of explicit mappings made by the PCP servers";
                    }

                    leaf maximum {
                        type uint32 {
                            range "61..86400";
                        }
                        default "86400";
                        description "Maximum lifetime of explicit mappings made by the PCP servers";
                    }

                } // container lifetime

                container version {
                    description "Enter the version context";

                    leaf minimum {
                        type uint16 {
                            range "1..255";
                        }
                        default "1";
                        description "Minimum protocol version supported by the PCP servers";
                    }

                    leaf maximum {
                        type uint16 {
                            range "1..255";
                        }
                        default "1";
                        description "Maximum protocol version supported by the PCP servers";
                    }

                } // container version

                container opcode {
                    description "Enter the opcode context";

                    leaf announce {
                        type boolean;
                        default "false";
                        description "Process the announce PCP requests";
                    }

                    leaf get {
                        type boolean;
                        default "false";
                        description "Process the get PCP requests";
                    }

                    leaf map {
                        type boolean;
                        default "false";
                        description "Process the map PCP requests";
                    }

                } // container opcode

                container option {
                    description "Enter the option context";

                    leaf description {
                        type boolean;
                        default "false";
                        description "Text description";
                    }

                    leaf next {
                        type boolean;
                        default "false";
                        description "Process the PCP requests that contain the next option";
                    }

                    leaf port-reservation {
                        type boolean;
                        default "false";
                        description "Process the PCP requests that contain the prefer failure option";
                    }

                    leaf port-set {
                        type boolean;
                        default "false";
                        description "Support the PORT_SET option in PCP MAP requests";
                    }

                    leaf prefer-failure {
                        type boolean;
                        default "false";
                        description "Process the PCP requests that contain the port reservation option";
                    }

                    leaf third-party {
                        type boolean;
                        default "false";
                        description "Process the PCP requests that contain the third party option";
                    }

                } // container option

            } // list pcp-server-policy

            container syslog {
                description "Enter the syslog context";

                list export-policy {
                    key "name";
                    max-elements 8;
                    description "Enter the export-policy list instance";

                    leaf name {
                        type types-sros:named-item;
                        description "Syslog export policy name";
                    }

                    leaf description {
                        type types-sros:description;
                        description "Text description";
                    }

                    leaf facility {
                        type types-nat:syslog-facility;
                        default "local0";
                        description "Facility number in the PRI part of the NAT SYSLOG messages";
                    }

                    leaf log-prefix {
                        type types-sros:named-item;
                        default "TMNX";
                        description "Optional prefix text in the MSG part of the NAT syslog messages";
                    }

                    leaf max-tx-delay {
                        type uint32 {
                            range "0..100";
                        }
                        units "deciseconds";
                        default "3";
                        description "Maximum time a syslog message delays in the output buffer to aggregate multiple events";
                    }

                    leaf mtu {
                        type uint32 {
                            range "512..9000";
                        }
                        default "1500";
                        description "Maximum transmission unit";
                    }

                    leaf rate-limit {
                        type uint32 {
                            range "10..2147483647";
                        }
                        units "packets per second";
                        description "Frame limit";
                    }

                    leaf severity-level {
                        type types-nat:syslog-severity-level;
                        default "info";
                        description "Severity level in the PRI part of the syslog messages";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container include {
                        description "Enter the include context";

                        leaf destination-ip {
                            type boolean;
                            default "false";
                            description "Include the translated destination IP address";
                        }

                        leaf foreign-ip {
                            type boolean;
                            default "false";
                            description "Include the original destination IPv4 address";
                        }

                        leaf foreign-port {
                            type boolean;
                            default "false";
                            description "Include the original destination port";
                        }

                        leaf nat-policy-name {
                            type boolean;
                            default "false";
                            description "Include the NAT policy name in the flow log";
                        }

                        leaf sub-id {
                            type boolean;
                            default "false";
                            description "Subscriber ID in subscriber aware NAT";
                        }

                    } // container include

                    list collector {
                        key "router-instance ip-address";
                        max-elements 2;
                        description "Enter the collector list instance";

                        leaf router-instance {
                            type string;
                            description "Router instance";
                        }

                        leaf ip-address {
                            type types-sros:ipv4-unicast-address;
                            description "IPv4 address of the external collector node";
                        }

                        leaf admin-state {
                            type types-sros:admin-state;
                            default "disable";
                            description "Administrative state of the collector node";
                        }

                        leaf destination-port {
                            type types-sros:tcp-udp-port-non-zero;
                            sros-ext:auto-restart-to-modify;
                            default "514";
                            description "Destination port";
                        }

                        leaf ipv4-source-address {
                            type types-sros:ipv4-unicast-address;
                            sros-ext:auto-restart-to-modify;
                            description "IPv4 source address";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                    } // list collector

                } // list export-policy

            } // container syslog

            list classifier {
                key "name";
                max-elements 8;
                description "Enter the classifier list instance";

                leaf name {
                    type types-sros:named-item;
                    description "NAT classifier name";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container default {
                    description "Enter the default context";

                    leaf dnat-ip-address {
                        type types-sros:ipv4-unicast-address;
                        sros-ext:isa-auto-clear-on-modify;
                        description "Default destination IP address for matching entries with dNAT action";
                    }

                    container action {
                        description "Enter the action context";

                        choice action-choice {
                            default "forward-option";
                            case dnat-option {

                                leaf dnat {
                                    status obsolete;
                                    type empty;
                                    sros-ext:isa-auto-clear-on-modify;
                                    description "Default destination IP address for DNAT action";
                                }

                                leaf dnat-ip-address {
                                    status obsolete;
                                    type types-sros:ipv4-unicast-address;
                                    sros-ext:isa-auto-clear-on-modify;
                                    description "Substitute IP address for the destination IP address of the packets matching this classifier";
                                }

                                container destination-nat {
                                    presence "Enable the destination-nat context";
                                    description "Enable the destination-nat context";

                                    leaf ip-address {
                                        type types-sros:ipv4-unicast-address;
                                        description "Substitute destination IP address of matching packets";
                                    }

                                } // container destination-nat

                            }
                            case forward-option {

                                leaf forward {
                                    type empty;
                                    sros-ext:isa-auto-clear-on-modify;
                                    description "Forward mode of operation";
                                }

                            }
                        }
                    } // container action

                } // container default

                list entry {
                    key "id";
                    max-elements 32;
                    description "Enter the entry list instance";

                    leaf id {
                        type uint32 {
                            range "1..1000";
                        }
                        description "Classifier rule entry ID";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container action {
                        description "Enter the action context";

                        choice action-choice {
                            case dnat-option {

                                leaf dnat {
                                    status obsolete;
                                    type empty;
                                    sros-ext:isa-auto-clear-on-modify;
                                    description "Destination-NAT mode of operation";
                                }

                                leaf dnat-ip-address {
                                    status obsolete;
                                    type types-sros:ipv4-unicast-address;
                                    sros-ext:isa-auto-clear-on-modify;
                                    description "Substitute IP address for the destination IP address of the packets matching this classifier";
                                }

                                container destination-nat {
                                    presence "Enable the destination-nat context";
                                    description "Enable the destination-nat context";

                                    leaf ip-address {
                                        type types-sros:ipv4-unicast-address;
                                        description "Replacement destination IP address for packets";
                                    }

                                } // container destination-nat

                            }
                            case forward-option {

                                leaf forward {
                                    type empty;
                                    sros-ext:isa-auto-clear-on-modify;
                                    description "Forward mode of operation";
                                }

                            }
                        }
                    } // container action

                    container match {
                        description "Enter the match context";

                        leaf protocol {
                            type types-nat:ip-protocol-tcp-or-udp;
                            sros-ext:isa-auto-clear-on-modify;
                            description "IP protocol to match";
                        }

                        leaf foreign-ip-address {
                            type types-sros:ipv4-unicast-address;
                            sros-ext:isa-auto-clear-on-modify;
                            description "Foreign IP address as the match criterion";
                        }

                        container dst-port-range {
                            description "Enter the dst-port-range context";

                            leaf start {
                                type types-sros:tcp-udp-port;
                                sros-ext:isa-auto-clear-on-modify;
                                default "0";
                                description "Lower bound of the port range";
                            }

                            leaf end {
                                type types-sros:tcp-udp-port;
                                sros-ext:isa-auto-clear-on-modify;
                                default "65535";
                                description "Upper bound of the port range";
                            }

                        } // container dst-port-range

                    } // container match

                } // list entry

            } // list classifier

            list nat-policy {
                key "name";
                max-elements 4096;
                description "Enter the nat-policy list instance";

                leaf name {
                    type types-sros:external-named-item;
                    description "NAT policy name";
                }

                leaf description {
                    type types-sros:description;
                    description "Text description";
                }

                leaf block-limit {
                    type uint16 {
                        range "1..40";
                    }
                    default "1";
                    description "Maximum number of port blocks per subscriber";
                }

                leaf filtering {
                    type types-nat:filtering;
                    description "Filtering method for inbound traffic for the policy";
                }

                leaf port-forwarding-range-end {
                    type uint16 {
                        range "1023..65535";
                    }
                    default "1023";
                    description "End of the port forwarding range";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice address-location {
                    case pool {

                        container pool {
                            description "Enter the pool context";

                            leaf router-instance {
                                type string;
                                sros-ext:isa-auto-clear-on-modify;
                                description "Router or VPRN service name";
                            }

                            leaf name {
                                type types-sros:named-item;
                                sros-ext:isa-auto-clear-on-modify;
                                description "NAT pool name";
                            }

                        } // container pool

                    }
                    case dnat {

                        container dnat-only {
                            presence "Enable the dnat-only context";
                            description "Enable the dnat-only context";

                            leaf router-instance {
                                type string;
                                sros-ext:isa-auto-clear-on-modify;
                                mandatory true;
                                description "Router name or VPRN service name";
                            }

                            choice isa {
                                mandatory true;
                                case nat {

                                    leaf nat-group {
                                        type leafref {
                                            path "../../../../../isa/nat-group/id";
                                        }
                                        sros-ext:immutable;
                                        sros-ext:isa-auto-clear-on-modify;
                                        description "NAT group";
                                    }

                                }
                                case wlan-gw {

                                    leaf wlan-gw-group {
                                        type leafref {
                                            path "../../../../../isa/wlan-gw-group/id";
                                        }
                                        sros-ext:immutable;
                                        sros-ext:isa-auto-clear-on-modify;
                                        description "WLAN GW group used for NAT";
                                    }

                                }
                            }
                        } // container dnat-only

                    }
                    case l2-outside {

                        leaf l2-outside {
                            type empty;
                            description "Use Layer 2 outside service address location";
                        }

                    }
                }
                container alg {
                    description "Enter the alg context";

                    leaf ftp {
                        type boolean;
                        default "true";
                        description "Use FTP ALG for the policy";
                    }

                    leaf pptp {
                        type boolean;
                        default "false";
                        description "Use PPTP ALG for the policy";
                    }

                    leaf rtsp {
                        type boolean;
                        default "false";
                        description "Use RTSP ALG for the policy";
                    }

                    leaf sip {
                        type boolean;
                        default "false";
                        description "Use SIP ALG for the policy";
                    }

                } // container alg

                container dnat {
                    description "Enter the dnat context";

                    leaf classifier {
                        type leafref {
                            path "../../../classifier/name";
                        }
                        sros-ext:isa-auto-clear-on-modify;
                        description "NAT classifier";
                    }

                } // container dnat

                container flow-log-policy {
                    description "Enter the flow-log-policy context";

                    leaf ipfix {
                        type leafref {
                            path "../../../../ipfix/export-policy/name";
                        }
                        description "IPFIX export policy";
                    }

                    leaf syslog {
                        type leafref {
                            path "../../../syslog/export-policy/name";
                        }
                        description "Syslog export policy name";
                    }

                } // container flow-log-policy

                container port-limits {
                    description "Enter the port-limits context";

                    leaf forwarding {
                        type uint16 {
                            range "1..64";
                        }
                        description "Maximum number of port forwarding entries";
                    }

                    leaf reserved {
                        type uint16 {
                            range "1..65534";
                        }
                        description "Number of ports reserved for prioritized sessions";
                    }

                    container watermarks {
                        presence "Enable the watermarks context";
                        description "Enable the watermarks context";

                        leaf high {
                            type types-sros:percent;
                            mandatory true;
                            description "High watermark percentage";
                        }

                        leaf low {
                            type types-sros:percent;
                            mandatory true;
                            description "Low watermark percentage";
                        }

                    } // container watermarks

                } // container port-limits

                container priority-sessions {
                    description "Enter the priority-sessions context";

                    container fc {
                        description "Enter the fc context";

                        leaf be {
                            type boolean;
                            default "false";
                            description "Prioritize traffic from BE forwarding classes";
                        }

                        leaf l2 {
                            type boolean;
                            default "false";
                            description "Prioritize traffic from L2 forwarding classes";
                        }

                        leaf af {
                            type boolean;
                            default "false";
                            description "Prioritize traffic from AF forwarding classes";
                        }

                        leaf l1 {
                            type boolean;
                            default "false";
                            description "Prioritize traffic from L1 forwarding classes";
                        }

                        leaf h2 {
                            type boolean;
                            default "false";
                            description "Prioritize traffic from H2 forwarding classes";
                        }

                        leaf ef {
                            type boolean;
                            default "false";
                            description "Prioritize traffic from EF forwarding classes";
                        }

                        leaf h1 {
                            type boolean;
                            default "false";
                            description "Prioritize traffic from H1 forwarding classes";
                        }

                        leaf nc {
                            type boolean;
                            default "false";
                            description "Prioritize traffic from NC forwarding classes";
                        }

                    } // container fc

                } // container priority-sessions

                container session-limits {
                    description "Enter the session-limits context";

                    leaf max {
                        type uint16 {
                            range "1..65535";
                        }
                        default "65535";
                        description "Maximum number of sessions per subscriber";
                    }

                    leaf reserved {
                        type uint16 {
                            range "1..65534";
                        }
                        description "Number of sessions reserved for prioritized sessions";
                    }

                    container watermarks {
                        presence "Enable the watermarks context";
                        description "Enable the watermarks context";

                        leaf high {
                            type types-sros:percent;
                            mandatory true;
                            description "High watermark percentage";
                        }

                        leaf low {
                            type types-sros:percent;
                            mandatory true;
                            description "Low watermark percentage";
                        }

                    } // container watermarks

                } // container session-limits

                container tcp {
                    description "Enter the tcp context";

                    leaf reset-unknown {
                        type boolean;
                        default "false";
                        description "Generate TCP reset for packets from unknown flows";
                    }

                    leaf mss-adjust {
                        type uint32 {
                            range "160..10240";
                        }
                        description "TCP MSS adjustment value";
                    }

                } // container tcp

                container timeouts {
                    description "Enter the timeouts context";

                    leaf icmp-query {
                        type types-sros:time-duration {
                            range "60..240";
                        }
                        default "60";
                        description "Timeout applied to an ICMP Query session";
                    }

                    leaf sip {
                        type types-sros:time-duration {
                            range "10..7200";
                        }
                        default "120";
                        description "SIP inactive media timeout";
                    }

                    leaf subscriber-retention {
                        type types-sros:time-duration {
                            range "0..1440";
                        }
                        units "minutes";
                        default "0";
                        description "IP address hold time after host and port blocks expire";
                    }

                    container tcp {
                        description "Enter the tcp context";

                        leaf established {
                            type types-sros:time-duration {
                                range "60..86400";
                            }
                            default "7440";
                            description "Idle timeout for TCP session in established state";
                        }

                        leaf rst {
                            type types-sros:time-duration {
                                range "0..240";
                            }
                            default "0";
                            description "Suspend time for TCP connection ports closed by RST";
                        }

                        leaf syn {
                            type types-sros:time-duration {
                                range "6..86400";
                            }
                            default "15";
                            description "TCP session timeout when synchronizing initial sequence";
                        }

                        leaf time-wait {
                            type types-sros:time-duration {
                                range "0..240";
                            }
                            default "0";
                            description "Timeout applied to a TCP session in the time-wait state";
                        }

                        leaf transitory {
                            type types-sros:time-duration {
                                range "60..86400";
                            }
                            default "240";
                            description "Idle timeout for TCP session in transitory state";
                        }

                    } // container tcp

                    container udp {
                        description "Enter the udp context";

                        leaf normal {
                            type types-sros:time-duration {
                                range "60..86400";
                            }
                            default "300";
                            description "UDP mapping timeout";
                        }

                        leaf dns {
                            type types-sros:time-duration {
                                range "15..86400";
                            }
                            default "15";
                            description "Timeout applied to UDP session with destination port 53";
                        }

                        leaf initial {
                            type types-sros:time-duration {
                                range "10..300";
                            }
                            default "15";
                            description "UDP mapping timeout applied to new sessions";
                        }

                    } // container udp

                } // container timeouts

                container udp {
                    description "Enter the udp context";

                    leaf inbound-refresh {
                        type boolean;
                        default "false";
                        description "Extend UDP session timeout on inbound traffic";
                    }

                } // container udp

            } // list nat-policy

            list up-nat-policy {
                key "name";
                max-elements 32;
                description "Enter the up-nat-policy list instance";

                leaf name {
                    type types-sros:external-named-item;
                    description "UP NAT policy name";
                }

                leaf description {
                    type types-sros:description;
                    description "Text description";
                }

                leaf icmp-echo-reply {
                    type boolean;
                    default "false";
                    description "Enable replies to ICMP Echo Request messages";
                }

                leaf filtering {
                    type types-nat:filtering;
                    description "Filtering method for inbound traffic for the policy";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container alg {
                    description "Enter the alg context";

                    leaf ftp {
                        type boolean;
                        default "true";
                        description "Use FTP ALG for the policy";
                    }

                    leaf pptp {
                        type boolean;
                        default "false";
                        description "Use PPTP ALG for the policy";
                    }

                    leaf rtsp {
                        type boolean;
                        default "false";
                        description "Use RTSP ALG for the policy";
                    }

                    leaf sip {
                        type boolean;
                        default "false";
                        description "Use SIP ALG for the policy";
                    }

                } // container alg

                container default-host {
                    presence "Enable the default-host context";
                    description "Enable the default-host context";

                    leaf ip-address {
                        type types-sros:ipv4-unicast-address;
                        description "IP address of the default DMZ host";
                    }

                    leaf inside-router-instance {
                        type string;
                        description "Router instance of the DMZ";
                    }

                    leaf rate-limit {
                        type int32 {
                            range "1..10000";
                        }
                        default "10";
                        description "Rate limit for unknown traffic sent to default DMZ host";
                    }

                } // container default-host

                container flow-log-policy {
                    description "Enter the flow-log-policy context";

                    leaf ipfix {
                        type leafref {
                            path "../../../../ipfix/export-policy/name";
                        }
                        description "IPFIX export policy";
                    }

                } // container flow-log-policy

                container port-limits {
                    description "Enter the port-limits context";

                    leaf reserved {
                        type uint16 {
                            range "1..65534";
                        }
                        description "Number of ports reserved for prioritized sessions";
                    }

                    container watermarks {
                        presence "Enable the watermarks context";
                        description "Enable the watermarks context";

                        leaf high {
                            type types-sros:percent;
                            mandatory true;
                            description "High watermark percentage";
                        }

                        leaf low {
                            type types-sros:percent;
                            mandatory true;
                            description "Low watermark percentage";
                        }

                    } // container watermarks

                } // container port-limits

                container priority-sessions {
                    description "Enter the priority-sessions context";

                    container fc {
                        description "Enter the fc context";

                        leaf be {
                            type boolean;
                            default "false";
                            description "Prioritize traffic from BE forwarding classes";
                        }

                        leaf l2 {
                            type boolean;
                            default "false";
                            description "Prioritize traffic from L2 forwarding classes";
                        }

                        leaf af {
                            type boolean;
                            default "false";
                            description "Prioritize traffic from AF forwarding classes";
                        }

                        leaf l1 {
                            type boolean;
                            default "false";
                            description "Prioritize traffic from L1 forwarding classes";
                        }

                        leaf h2 {
                            type boolean;
                            default "false";
                            description "Prioritize traffic from H2 forwarding classes";
                        }

                        leaf ef {
                            type boolean;
                            default "false";
                            description "Prioritize traffic from EF forwarding classes";
                        }

                        leaf h1 {
                            type boolean;
                            default "false";
                            description "Prioritize traffic from H1 forwarding classes";
                        }

                        leaf nc {
                            type boolean;
                            default "false";
                            description "Prioritize traffic from NC forwarding classes";
                        }

                    } // container fc

                } // container priority-sessions

                container session-limits {
                    description "Enter the session-limits context";

                    leaf max {
                        type uint16 {
                            range "1..65535";
                        }
                        default "65535";
                        description "Maximum number of sessions per subscriber";
                    }

                    leaf reserved {
                        type uint16 {
                            range "1..65534";
                        }
                        description "Number of sessions reserved for prioritized sessions";
                    }

                    container watermarks {
                        presence "Enable the watermarks context";
                        description "Enable the watermarks context";

                        leaf high {
                            type types-sros:percent;
                            mandatory true;
                            description "High watermark percentage";
                        }

                        leaf low {
                            type types-sros:percent;
                            mandatory true;
                            description "Low watermark percentage";
                        }

                    } // container watermarks

                } // container session-limits

                container tcp {
                    description "Enter the tcp context";

                    leaf reset-unknown {
                        type boolean;
                        default "false";
                        description "Generate TCP reset for packets from unknown flows";
                    }

                    leaf mss-adjust {
                        type uint32 {
                            range "160..10240";
                        }
                        description "TCP MSS adjustment value";
                    }

                } // container tcp

                container timeouts {
                    description "Enter the timeouts context";

                    leaf icmp-query {
                        type types-sros:time-duration {
                            range "60..240";
                        }
                        default "60";
                        description "Timeout applied to an ICMP Query session";
                    }

                    leaf sip {
                        type types-sros:time-duration {
                            range "10..7200";
                        }
                        default "120";
                        description "SIP inactive media timeout";
                    }

                    leaf subscriber-retention {
                        type types-sros:time-duration {
                            range "0..1440";
                        }
                        units "minutes";
                        default "0";
                        description "IP address hold time after host and port blocks expire";
                    }

                    container tcp {
                        description "Enter the tcp context";

                        leaf established {
                            type types-sros:time-duration {
                                range "60..86400";
                            }
                            default "7440";
                            description "Idle timeout for TCP session in established state";
                        }

                        leaf rst {
                            type types-sros:time-duration {
                                range "0..240";
                            }
                            default "0";
                            description "Suspend time for TCP connection ports closed by RST";
                        }

                        leaf syn {
                            type types-sros:time-duration {
                                range "6..86400";
                            }
                            default "15";
                            description "TCP session timeout when synchronizing initial sequence";
                        }

                        leaf time-wait {
                            type types-sros:time-duration {
                                range "0..240";
                            }
                            default "0";
                            description "Timeout applied to a TCP session in the time-wait state";
                        }

                        leaf transitory {
                            type types-sros:time-duration {
                                range "60..86400";
                            }
                            default "240";
                            description "Idle timeout for TCP session in transitory state";
                        }

                    } // container tcp

                    container udp {
                        description "Enter the udp context";

                        leaf normal {
                            type types-sros:time-duration {
                                range "60..86400";
                            }
                            default "300";
                            description "UDP mapping timeout";
                        }

                        leaf dns {
                            type types-sros:time-duration {
                                range "15..86400";
                            }
                            default "15";
                            description "Timeout applied to UDP session with destination port 53";
                        }

                        leaf initial {
                            type types-sros:time-duration {
                                range "10..300";
                            }
                            default "15";
                            description "UDP mapping timeout applied to new sessions";
                        }

                    } // container udp

                } // container timeouts

                container udp {
                    description "Enter the udp context";

                    leaf inbound-refresh {
                        type boolean;
                        default "false";
                        description "Extend UDP session timeout on inbound traffic";
                    }

                } // container udp

            } // list up-nat-policy

            container deterministic-script {
                description "Enter the deterministic-script context";

                leaf location {
                    type types-sros:ftp-tftp-url {
                        length "1..180";
                    }
                    description "Remote location where Python script is exported";
                }

            } // container deterministic-script

            container map-t {
                description "Enter the map-t context";

                list domain {
                    key "name";
                    max-elements 63;
                    description "Enter the domain list instance";

                    leaf name {
                        type types-sros:named-item;
                        description "MAP domain name";
                    }

                    leaf description {
                        type types-sros:description;
                        description "Text description";
                    }

                    leaf dmr-prefix {
                        type types-sros:ipv6-prefix;
                        sros-ext:auto-restart-to-modify;
                        description "The Default Mapping Rule prefix";
                    }

                    leaf mtu {
                        type uint32 {
                            range "160..8686";
                        }
                        default "8686";
                        description "Configure the MTU";
                    }

                    leaf admin-state {
                        type types-sros:admin-state;
                        default "disable";
                        description "Administrative state of the MAP domain";
                    }

                    leaf tcp-mss-adjust {
                        type uint32 {
                            range "0 | 160..8626";
                        }
                        default "0";
                        description "The value to adjust the TCP Maximum Segment Size (MSS) option";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ip-fragmentation {
                        description "Enter the ip-fragmentation context";

                        leaf v6-frag-header {
                            type boolean;
                            default "false";
                            description "Enable insertion of fragmentation header in IPv6 packet";
                        }

                    } // container ip-fragmentation

                    list mapping-rule {
                        key "rule-name";
                        max-elements 16383;
                        description "Enter the mapping-rule list instance";

                        leaf rule-name {
                            type types-sros:named-item;
                            description "The name that identifies this mapping rule";
                        }

                        leaf description {
                            type types-sros:description;
                            description "Text description";
                        }

                        leaf ipv4-prefix {
                            type types-sros:ipv4-prefix;
                            sros-ext:auto-restart-to-modify;
                            description "The IPv4 prefix";
                        }

                        leaf ea-length {
                            type uint32 {
                                range "0..48";
                            }
                            sros-ext:auto-restart-to-modify;
                            default "0";
                            description "The length of the EA bits field in the End-user IPv6 prefix part of the IPv6 Map Address";
                        }

                        leaf psid-offset {
                            type uint32 {
                                range "0..16";
                            }
                            sros-ext:auto-restart-to-modify;
                            default "6";
                            description "The offset of the Port Set ID (PSID) within a 16 bits wide port space";
                        }

                        leaf rule-prefix {
                            type types-sros:ipv6-prefix;
                            sros-ext:auto-restart-to-modify;
                            description "The IPv6 prefix";
                        }

                        leaf admin-state {
                            type types-sros:admin-state;
                            default "disable";
                            description "Administrative state of the MAP rule";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                    } // list mapping-rule

                } // list domain

            } // container map-t

        } // container nat

    } // grouping conf-svc-nat

}
