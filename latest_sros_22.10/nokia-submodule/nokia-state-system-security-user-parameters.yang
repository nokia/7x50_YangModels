submodule nokia-state-system-security-user-parameters {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel22";

    organization "Nokia";

    contact
        "Nokia SR OS Support
         Web: <http://www.nokia.com>";

    description
        "Nokia YANG Data model with operational state for user and password parameters. on SR OS based routers.

         Copyright 2016 Nokia. All rights reserved. Reproduction of this document
         is authorized on the condition that the foregoing copyright notice is included.

         This nokia-state-system-security-user-parameters YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-08-05";

    grouping state-system-security-user-parameters-user-params {
        container user-params {
            description "Enter the user-params context";

            container local-user {
                description "Enter the local-user context";

                list user {
                    key "user-name";
                    description "Enter the user list instance";

                    leaf user-name {
                        type types-sros:named-item;
                        description "Local user name";
                    }

                    leaf attempted-logins {
                        type yang:counter32;
                        description
                            "Indicates the number of times the user has attempted to login
                             irrespective of whether the login succeeded or failed.";
                    }

                    leaf failed-logins {
                        type yang:counter32;
                        description "Indicates the number of times the user has failed to login.";
                    }

                    leaf locked-out {
                        type boolean;
                        description "Indicates that the user is locked out.";
                    }

                    leaf lockout-remaining-time {
                        type types-sros:time-duration;
                        units "seconds";
                        description "Indicates remaining time until the user is locked out in a format minutes:seconds.";
                    }

                    leaf password-changed-time {
                        type yang:date-and-time;
                        description "The calendar date and time when the password was changed.";
                    }

                    leaf password-expiration-time {
                        type yang:date-and-time;
                        description "The calendar date and time when the user password will expire.";
                    }

                } // list user

            } // container local-user

            list user-lockout {
                key "user-name";
                description "Enter the user-lockout list instance";

                leaf user-name {
                    type types-sros:named-item;
                    description "Specifies the name for a user";
                }

                leaf remaining-login-attempts {
                    type uint32;
                    description "Remaining login attempts for a user";
                }

                leaf remaining-lockout-time {
                    type types-sros:time-duration;
                    units "seconds";
                    description "Remaining lockout time";
                }

            } // list user-lockout

        } // container user-params

    } // grouping state-system-security-user-parameters-user-params

}
