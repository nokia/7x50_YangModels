submodule nokia-state-router-static-route {

    yang-version "1.1";

    belongs-to nokia-state { prefix "state"; }

    import ietf-yang-types                { prefix "yang"; }
    import nokia-sros-yang-extensions     { prefix "sros-ext"; }
    import nokia-types-router             { prefix "types-router"; }
    import nokia-types-sros               { prefix "types-sros"; }


    sros-ext:sros-major-release "rel22";

    organization "Nokia";

    contact
        "Nokia SR OS Support
         Web: <http://www.nokia.com>";

    description
        "Nokia YANG Data model with operational state for Static route attributes on SR OS based routers.

         Copyright 2016 Nokia. All rights reserved. Reproduction of this document
         is authorized on the condition that the foregoing copyright notice is included.

         This nokia-state-router-static-route YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-10-12";

    grouping state-router-static-route-static-routes {
        container static-routes {
            description "Enter the static-routes context";

            list route {
                key "ip-prefix route-type";
                description "Enter the route list instance";

                leaf ip-prefix {
                    type types-sros:ip-prefix;
                    description "IP prefix and prefix length for the static routes";
                }

                leaf route-type {
                    type types-router:unicast-multicast;
                    description "Static route type for unicast or multicast RPF";
                }

                leaf creation-origin {
                    type types-sros:creation-origin;
                    description "Indicates the mechanism used to create this entry.";
                }

                leaf next-hops-count {
                    type yang:counter32;
                    description "The number of next-hops configured under this prefix row entry.";
                }

                container blackhole {
                    description "Enter the blackhole context";

                    leaf last-enabled-time {
                        type types-sros:date-time;
                        description
                            "Indicates the time when 'status' was last set to active
                             to allow IP forwarding on this static route entry.";
                    }

                    leaf status {
                        type enumeration {
                            enum "active"                       { value 1; }
                            enum "inactive"                     { value 2; }
                        }
                        description "Indicates whether or not this route entry is active in the system.";
                    }

                    leaf egress-interface-index {
                        type int32 {
                            range "0..max";
                        }
                        description
                            "Indicates the outgoing interface index for this route as computed by the
                             static-route module.";
                    }

                    leaf creation-origin {
                        type types-sros:creation-origin;
                        description "Indicates the mechanism used to create this entry.";
                    }

                    leaf dynamic-bgp-next-hop {
                        type types-sros:ip-address;
                        description
                            "This is the next-hop of the BGP prefix that matches the static-route prefix in
                             a blackhole static-route. The static-route is programmed in the route-table
                             with this next-hop, if present.";
                    }

                    leaf hold-time-left {
                        type uint32;
                        description
                            "If a static-route hold timer is configured and this is non-zero, it indicates
                             the static-route is being held from becoming active and is the remaining time
                             in seconds for static route to become active.";
                    }

                    leaf backup-status {
                        type enumeration {
                            enum "inactive"                     { value 1; }
                            enum "active-as-backup"             { value 2; }
                            enum "active-as-primary"            { value 3; }
                        }
                        description "Indicates the backup route status of the static route entry.";
                    }

                } // container blackhole

                list indirect {
                    key "ip-address";
                    description "Enter the indirect list instance";

                    leaf ip-address {
                        type types-sros:ip-address;
                        description "Next-hop IP address used to reach the destination";
                    }

                    leaf last-enabled-time {
                        type types-sros:date-time;
                        description
                            "Indicates the time when 'status' was last set to active
                             to allow IP forwarding on this static route entry.";
                    }

                    leaf status {
                        type enumeration {
                            enum "active"                       { value 1; }
                            enum "inactive"                     { value 2; }
                        }
                        description "Indicates whether or not this route entry is active in the system.";
                    }

                    leaf egress-interface-index {
                        type int32 {
                            range "0..max";
                        }
                        description
                            "Indicates the outgoing interface index for this route as computed by the
                             static-route module.";
                    }

                    leaf creation-origin {
                        type types-sros:creation-origin;
                        description "Indicates the mechanism used to create this entry.";
                    }

                    leaf dynamic-bgp-next-hop {
                        type types-sros:ip-address;
                        description
                            "This is the next-hop of the BGP prefix that matches the static-route prefix in
                             a blackhole static-route. The static-route is programmed in the route-table
                             with this next-hop, if present.";
                    }

                    leaf hold-time-left {
                        type uint32;
                        description
                            "If a static-route hold timer is configured and this is non-zero, it indicates
                             the static-route is being held from becoming active and is the remaining time
                             in seconds for static route to become active.";
                    }

                    leaf backup-status {
                        type enumeration {
                            enum "inactive"                     { value 1; }
                            enum "active-as-backup"             { value 2; }
                            enum "active-as-primary"            { value 3; }
                        }
                        description "Indicates the backup route status of the static route entry.";
                    }

                    list cpe-check {
                        key "address";
                        description "Enter the cpe-check list instance";

                        leaf address {
                            type types-sros:ip-address;
                            description "IP address of the target CPE device";
                        }

                        leaf up-time {
                            type yang:timeticks;
                            description
                                "Indicates how long (in centiseconds) the CPE has been
                                 available.";
                        }

                        leaf in-packet-count {
                            type yang:counter32;
                            description "Indicates the number of echo-reply packets received.";
                        }

                        leaf out-packet-count {
                            type yang:counter32;
                            description "Indicates the number of echo-request packets sent.";
                        }

                        leaf down-transition {
                            type yang:gauge32;
                            description
                                "Indicates the number of times the CPE has transitioned
                                 to the unavailable state.";
                        }

                        leaf up-transition {
                            type yang:gauge32;
                            description
                                "Indicates the number of times the CPE has transitioned
                                 to the available state.";
                        }

                        leaf ttl {
                            type uint32;
                            units "seconds";
                            description "Indicates the time, in seconds, before the CPE will be declared down.";
                        }

                    } // list cpe-check

                } // list indirect

                list interface {
                    key "interface-name";
                    description "Enter the interface list instance";

                    leaf interface-name {
                        type types-sros:interface-name;
                        description "Router interface name";
                    }

                    leaf last-enabled-time {
                        type types-sros:date-time;
                        description
                            "Indicates the time when 'status' was last set to active
                             to allow IP forwarding on this static route entry.";
                    }

                    leaf status {
                        type enumeration {
                            enum "active"                       { value 1; }
                            enum "inactive"                     { value 2; }
                        }
                        description "Indicates whether or not this route entry is active in the system.";
                    }

                    leaf egress-interface-index {
                        type int32 {
                            range "0..max";
                        }
                        description
                            "Indicates the outgoing interface index for this route as computed by the
                             static-route module.";
                    }

                    leaf creation-origin {
                        type types-sros:creation-origin;
                        description "Indicates the mechanism used to create this entry.";
                    }

                    leaf dynamic-bgp-next-hop {
                        type types-sros:ip-address;
                        description
                            "This is the next-hop of the BGP prefix that matches the static-route prefix in
                             a blackhole static-route. The static-route is programmed in the route-table
                             with this next-hop, if present.";
                    }

                    leaf hold-time-left {
                        type uint32;
                        description
                            "If a static-route hold timer is configured and this is non-zero, it indicates
                             the static-route is being held from becoming active and is the remaining time
                             in seconds for static route to become active.";
                    }

                    leaf backup-status {
                        type enumeration {
                            enum "inactive"                     { value 1; }
                            enum "active-as-backup"             { value 2; }
                            enum "active-as-primary"            { value 3; }
                        }
                        description "Indicates the backup route status of the static route entry.";
                    }

                    list cpe-check {
                        key "address";
                        description "Enter the cpe-check list instance";

                        leaf address {
                            type types-sros:ip-address;
                            description "IP address of the target CPE device";
                        }

                        leaf up-time {
                            type yang:timeticks;
                            description
                                "Indicates how long (in centiseconds) the CPE has been
                                 available.";
                        }

                        leaf in-packet-count {
                            type yang:counter32;
                            description "Indicates the number of echo-reply packets received.";
                        }

                        leaf out-packet-count {
                            type yang:counter32;
                            description "Indicates the number of echo-request packets sent.";
                        }

                        leaf down-transition {
                            type yang:gauge32;
                            description
                                "Indicates the number of times the CPE has transitioned
                                 to the unavailable state.";
                        }

                        leaf up-transition {
                            type yang:gauge32;
                            description
                                "Indicates the number of times the CPE has transitioned
                                 to the available state.";
                        }

                        leaf ttl {
                            type uint32;
                            units "seconds";
                            description "Indicates the time, in seconds, before the CPE will be declared down.";
                        }

                    } // list cpe-check

                } // list interface

                list ipsec-tunnel {
                    key "ipsec-tunnel-name";
                    description "Enter the ipsec-tunnel list instance";

                    leaf ipsec-tunnel-name {
                        type types-sros:named-item;
                        description "IPsec tunnel name.";
                    }

                    leaf last-enabled-time {
                        type types-sros:date-time;
                        description
                            "Indicates the time when 'status' was last set to active
                             to allow IP forwarding on this static route entry.";
                    }

                    leaf status {
                        type enumeration {
                            enum "active"                       { value 1; }
                            enum "inactive"                     { value 2; }
                        }
                        description "Indicates whether or not this route entry is active in the system.";
                    }

                    leaf egress-interface-index {
                        type int32 {
                            range "0..max";
                        }
                        description
                            "Indicates the outgoing interface index for this route as computed by the
                             static-route module.";
                    }

                    leaf creation-origin {
                        type types-sros:creation-origin;
                        description "Indicates the mechanism used to create this entry.";
                    }

                    leaf dynamic-bgp-next-hop {
                        type types-sros:ip-address;
                        description
                            "This is the next-hop of the BGP prefix that matches the static-route prefix in
                             a blackhole static-route. The static-route is programmed in the route-table
                             with this next-hop, if present.";
                    }

                    leaf hold-time-left {
                        type uint32;
                        description
                            "If a static-route hold timer is configured and this is non-zero, it indicates
                             the static-route is being held from becoming active and is the remaining time
                             in seconds for static route to become active.";
                    }

                    leaf backup-status {
                        type enumeration {
                            enum "inactive"                     { value 1; }
                            enum "active-as-backup"             { value 2; }
                            enum "active-as-primary"            { value 3; }
                        }
                        description "Indicates the backup route status of the static route entry.";
                    }

                } // list ipsec-tunnel

                list next-hop {
                    key "ip-address";
                    description "Enter the next-hop list instance";

                    leaf ip-address {
                        type types-sros:ip-address-with-zone;
                        description "IP address of the directly-connected next hop";
                    }

                    leaf last-enabled-time {
                        type types-sros:date-time;
                        description
                            "Indicates the time when 'status' was last set to active
                             to allow IP forwarding on this static route entry.";
                    }

                    leaf status {
                        type enumeration {
                            enum "active"                       { value 1; }
                            enum "inactive"                     { value 2; }
                        }
                        description "Indicates whether or not this route entry is active in the system.";
                    }

                    leaf egress-interface-index {
                        type int32 {
                            range "0..max";
                        }
                        description
                            "Indicates the outgoing interface index for this route as computed by the
                             static-route module.";
                    }

                    leaf creation-origin {
                        type types-sros:creation-origin;
                        description "Indicates the mechanism used to create this entry.";
                    }

                    leaf dynamic-bgp-next-hop {
                        type types-sros:ip-address;
                        description
                            "This is the next-hop of the BGP prefix that matches the static-route prefix in
                             a blackhole static-route. The static-route is programmed in the route-table
                             with this next-hop, if present.";
                    }

                    leaf hold-time-left {
                        type uint32;
                        description
                            "If a static-route hold timer is configured and this is non-zero, it indicates
                             the static-route is being held from becoming active and is the remaining time
                             in seconds for static route to become active.";
                    }

                    leaf backup-status {
                        type enumeration {
                            enum "inactive"                     { value 1; }
                            enum "active-as-backup"             { value 2; }
                            enum "active-as-primary"            { value 3; }
                        }
                        description "Indicates the backup route status of the static route entry.";
                    }

                    list cpe-check {
                        key "address";
                        description "Enter the cpe-check list instance";

                        leaf address {
                            type types-sros:ip-address;
                            description "IP address of the target CPE device";
                        }

                        leaf up-time {
                            type yang:timeticks;
                            description
                                "Indicates how long (in centiseconds) the CPE has been
                                 available.";
                        }

                        leaf in-packet-count {
                            type yang:counter32;
                            description "Indicates the number of echo-reply packets received.";
                        }

                        leaf out-packet-count {
                            type yang:counter32;
                            description "Indicates the number of echo-request packets sent.";
                        }

                        leaf down-transition {
                            type yang:gauge32;
                            description
                                "Indicates the number of times the CPE has transitioned
                                 to the unavailable state.";
                        }

                        leaf up-transition {
                            type yang:gauge32;
                            description
                                "Indicates the number of times the CPE has transitioned
                                 to the available state.";
                        }

                        leaf ttl {
                            type uint32;
                            units "seconds";
                            description "Indicates the time, in seconds, before the CPE will be declared down.";
                        }

                    } // list cpe-check

                } // list next-hop

            } // list route

        } // container static-routes

    } // grouping state-router-static-route-static-routes

}
