submodule nokia-conf-router-bier {

    yang-version "1.1";

    belongs-to nokia-conf { prefix "conf"; }

    import ietf-inet-types                { prefix "inet"; }
    import nokia-sros-yang-extensions     { prefix "sros-ext"; }
    import nokia-types-sros               { prefix "types-sros"; }

    include nokia-conf-groups;


    sros-ext:sros-major-release "rel22";

    organization "Nokia";

    contact
        "Nokia SR OS Support
         Web: <http://www.nokia.com>";

    description
        "Nokia YANG Data model to configure Base router BIER protocol on SR OS based routers.

         Copyright 2016 Nokia. All rights reserved. Reproduction of this document
         is authorized on the condition that the foregoing copyright notice is included.

         This nokia-conf-router-bier YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-06-27";

    grouping conf-router-bier {
        container bier {
            presence "Enable the bier context";
            description "Enable the bier context";

            leaf admin-state {
                type types-sros:admin-state;
                default "disable";
                description "Administrative state of BIER";
            }

            leaf fast-reroute {
                type boolean;
                default "false";
                description "Enable BIER Fast Reroute";
            }

            leaf-list bfd-liveness {
                type enumeration {
                    enum "ipv4"                         { value 1; }
                }
                max-elements 1;
                description "BIER next-hops with BFD enabled";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list template {
                key "template-name";
                description "Enter the template list instance";

                leaf admin-state {
                    type types-sros:admin-state;
                    default "disable";
                    description "Administrative state of the BIER template";
                }

                leaf template-name {
                    type types-sros:named-item;
                    description "BIER template name";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list sub-domain {
                    key "start end";
                    description "Enter the sub-domain list instance";

                    leaf start {
                        type inet:as-number {
                            range "0..255";
                        }
                        description "Lower bound of sub-domain range";
                    }

                    leaf end {
                        type inet:as-number {
                            range "0..255";
                        }
                        description "Upper bound of sub-domain range";
                    }

                    leaf bfr-id {
                        type inet:as-number {
                            range "1..4096";
                        }
                        description "BIER ID for the sub-domain";
                    }

                    leaf multi-topology {
                        type enumeration {
                            enum "ipv4-unicast"                 { value 0; }
                            enum "ipv6-unicast"                 { value 2; }
                            enum "ipv4-multicast"               { value 3; }
                            enum "ipv6-multicast"               { value 4; }
                        }
                        default "ipv4-unicast";
                        description "Multi-topology for the sub-domain";
                    }

                    leaf prefix {
                        type types-sros:ipv4-unicast-address;
                        default "0.0.0.0";
                        description "IP address used as BFR prefix";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list sub-domain

            } // list template

        } // container bier

    } // grouping conf-router-bier

}
