module nokia-notifications {

    yang-version "1.1";

    namespace "urn:nokia.com:sros:ns:yang:sr:notifications";

    prefix "notif";

    import nokia-sros-yang-extensions   { prefix "sros-ext"; }
    import nokia-types-log              { prefix "types-log"; }
    import nokia-types-sros             { prefix "types-sros"; }
    import ietf-netconf-notifications   { prefix "ietf-ncn"; }

    description "Description of the notifications which are available in the 
                 system and can be sent out by the logger.";

    sros-ext:sros-major-release "rel20";

    organization "Nokia";

    contact
        "Nokia SR OS Support
         Web: <http://www.nokia.com>";


    revision "2019-06-16";

//  -------------------- AUGMENT STANDARD NOTIFICATIONS --------------------

    augment "/ietf-ncn:netconf-config-change/ietf-ncn:edit" {
        leaf value {
            description
                "The new value of the target.";
            type string;
        }
    }

//  -------------------------- SROS NOTIFICATIONS --------------------------

    notification sros-config-change-event {
        description
            "Generated when the configuration of the system gets created, 
             modified or deleted.";

        uses basic-event-params;
        uses nokia-event-data;
    }

    notification sros-state-change-event {
        description
            "Generated on state changes in the system.";

        uses basic-event-params;
        uses nokia-event-data;
    }

    notification sros-command-accounting-event {
        description
            "Generated when a user executes a command on a management interface.";

        uses basic-event-params;
        uses nokia-event-data;
    }

    notification sros-md-rpc-accounting-event {
        description
            "Generated when a user executes a RPC on a management interface.";

        uses basic-event-params;
        uses nokia-event-data;
    }

    notification sros-operation-status-change-event {
        description
            "Generated on operation status change.";

        uses basic-event-params;
        uses nokia-event-data;
    }

    notification sros-log-generic-event {
        description
            "Generated on any event that is generated in the system
             that is not modeled by a more specific event.";

        uses basic-event-params;
        uses nokia-event-data;
    }

//  -------------------------- GROUPINGS --------------------------

    grouping basic-event-params {
        leaf sequence-number {
            description
                "A sequence number to indicate the ordering of log events in the log-id.
                 If the event is replayed, the sequence number is replayed as well.";
            type uint64;
        }

        leaf severity {
            description
                "The severity level of the log event.";
            type types-log:severity-level;
        }

        leaf application {
            description
                "The name of the application that reports the log event.";
            type types-log:application;
        }

        leaf event-id {
            description
                "The id the event that was generated.
                 Each log event type has a unique identifying number.  This number is
                 unique within a particular software application, such as IP, MPLS,
                 OSPF, etc.; but it is not necessarily unique across different software
                 applications.  That is MPLS event #1001 may be different from OSPF
                 event #1001.";
            type uint32 {
                range 1..max;
            }
        }

        leaf event-name {
            description
                "The name of the log event that was generated.";
            type types-sros:named-item;
        }

        leaf router-name {
            description
                "The router context name that generated the log event.";
            type types-sros:named-item-or-empty;
        }

        leaf subject {
            description
                "The router context name that generated the log event.
                 The subject is the entity that originated the event, such as the Port ID.";
            type types-sros:named-item;
        }

        leaf message {
            description
                "The log event message.";
            type string {
                length 1..4100;
            }
        }
    }

    grouping nokia-event-data {
        anyxml event-params {
            description
                "The event specific data splitted in parameters.";
        }
    }
}
