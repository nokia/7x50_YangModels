module nokia-types-sfm {

    yang-version "1.1";

    namespace "urn:nokia.com:sros:ns:yang:sr:types-sfm";

    prefix "types-sfm";

    import nokia-sros-yang-extensions     { prefix "sros-ext"; }

    sros-ext:sros-major-release "rel22";

    organization "Nokia";

    contact
        "Nokia SR OS Support
         Web: <http://www.nokia.com>";

    description
        "Common sfm types data types used in the SR OS management system.

         Copyright 2016 Nokia. All rights reserved. Reproduction of this document
         is authorized on the condition that the foregoing copyright notice is included.

         This nokia-types-sfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-11-11";

    typedef sros-sfm-type {
        type enumeration {
            enum "sfm-x20"                      { value 3; }
            enum "sfm-x20-b"                    { value 6; }
            enum "m-sfm5-7"                     { value 8; }
            enum "m-sfm5-12"                    { value 9; }
            enum "m-sfm5-12e"                   { value 10; }
            enum "sfm-x20s-b"                   { value 11; }
            enum "sfm-ixr-6"                    { value 13; }
            enum "sfm-ixr-10"                   { value 14; }
            enum "sfm-s"                        { value 15; }
            enum "m-sfm6-12e"                   { value 16; }
            enum "sfm2-x20s"                    { value 17; }
            enum "sfm-2s"                       { value 21; }
            enum "m-sfm6-7/12"                  { value 22; }
            enum "sfm-2se"                      { value 26; }
            enum "sfm2-s"                       { value 27; }
        }
        description "Specifies an SR OS series Switch Fabric Module type.";
    }

    typedef sros-sfm-type-state {
        type enumeration {
            enum "unknown"                      { value 0; }
            enum "unassigned"                   { value 1; }
            enum "sfm-x20"                      { value 3; }
            enum "sfm-x20-b"                    { value 6; }
            enum "m-sfm5-7"                     { value 8; }
            enum "m-sfm5-12"                    { value 9; }
            enum "m-sfm5-12e"                   { value 10; }
            enum "sfm-x20s-b"                   { value 11; }
            enum "sfm-ixr-6"                    { value 13; }
            enum "sfm-ixr-10"                   { value 14; }
            enum "sfm-s"                        { value 15; }
            enum "m-sfm6-12e"                   { value 16; }
            enum "sfm2-x20s"                    { value 17; }
            enum "sfm-2s"                       { value 21; }
            enum "m-sfm6-7/12"                  { value 22; }
            enum "sfm-2se"                      { value 26; }
            enum "sfm2-s"                       { value 27; }
        }
        description "Specifies an SR OS series Switch Fabric Module type.";
    }

}
