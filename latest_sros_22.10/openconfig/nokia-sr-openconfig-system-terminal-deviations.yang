module nokia-sr-openconfig-system-terminal-deviations {

    namespace "urn:nokia.com:sros:ns:yang:sr:openconfig-system-terminal-deviations";

    prefix "nokia-oc-sys-term-devs";

    import nokia-sros-yang-extensions     { prefix "sros-ext"; }
    import openconfig-extensions          { prefix "oc-ext"; }
    import openconfig-system              { prefix "oc-sys"; }
    import openconfig-system-terminal     { prefix "oc-sys-term"; }

    sros-ext:sros-major-release "rel22";

    organization "Nokia";

    contact
        "Nokia SR OS Support
         Web: <http://www.nokia.com>";

    description
        "This module contains the list of deviations against the openconfig-system-terminal
          module for the Nokia SR OS based routers.

         Copyright 2016 Nokia. All rights reserved. Reproduction of this document
         is authorized on the condition that the foregoing copyright notice is included.

         This nokia-sr-openconfig-system-terminal-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-09-18";

    deviation /oc-sys:system/oc-sys:ssh-server/oc-sys:config/oc-sys:timeout {
        deviate replace {
            type uint32 {
                range 0..86400;
            }
        }
        deviate add {
            default 1800;
        }
        deviate add {
            must "(. mod 60) = 0";
        }
    }

    deviation /oc-sys:system/oc-sys:ssh-server/oc-sys:config/oc-sys:rate-limit {
        deviate not-supported;
    }

    deviation /oc-sys:system/oc-sys:ssh-server/oc-sys:config/oc-sys:session-limit {
        deviate replace {
            type uint16 {
                range 0..50;
            }
        }
        deviate add {
            default 5;
        }
    }

    deviation /oc-sys:system/oc-sys:ssh-server/oc-sys:config/oc-sys:protocol-version {
        deviate add {
            must ". = 'V2'";
        }
    }

    deviation /oc-sys:system/oc-sys:ssh-server/oc-sys:state/oc-sys:timeout {
        deviate replace {
            type uint32 {
                range 0..86400;
            }
        }
        deviate add {
            default 1800;
        }
        deviate add {
            must "(. mod 60) = 0";
        }
    }

    deviation /oc-sys:system/oc-sys:ssh-server/oc-sys:state/oc-sys:rate-limit {
        deviate not-supported;
    }

    deviation /oc-sys:system/oc-sys:ssh-server/oc-sys:state/oc-sys:session-limit {
        deviate replace {
            type uint16 {
                range 0..50;
            }
        }
        deviate add {
            default 5;
        }
    }

    deviation /oc-sys:system/oc-sys:ssh-server/oc-sys:state/oc-sys:protocol-version {
        deviate add {
            must ". = 'V2'";
        }
    }

    deviation /oc-sys:system/oc-sys:telnet-server/oc-sys:config/oc-sys:timeout {
        deviate replace {
            type uint32 {
                range 0..86400;
            }
        }
        deviate add {
            default 1800;
        }
        deviate add {
            must "(. mod 60) = 0";
        }
    }

    deviation /oc-sys:system/oc-sys:telnet-server/oc-sys:config/oc-sys:rate-limit {
        deviate not-supported;
    }

    deviation /oc-sys:system/oc-sys:telnet-server/oc-sys:config/oc-sys:session-limit {
        deviate replace {
            type uint16 {
                range 0..50;
            }
        }
        deviate add {
            default 5;
        }
    }

    deviation /oc-sys:system/oc-sys:telnet-server/oc-sys:state/oc-sys:timeout {
        deviate replace {
            type uint32 {
                range 0..86400;
            }
        }
        deviate add {
            default 1800;
        }
        deviate add {
            must "(. mod 60) = 0";
        }
    }

    deviation /oc-sys:system/oc-sys:telnet-server/oc-sys:state/oc-sys:rate-limit {
        deviate not-supported;
    }

    deviation /oc-sys:system/oc-sys:telnet-server/oc-sys:state/oc-sys:session-limit {
        deviate replace {
            type uint16 {
                range 0..50;
            }
        }
        deviate add {
            default 5;
        }
    }

}
