module nokia-sr-openconfig-mpls-ldp-deviations {

    namespace "urn:nokia.com:sros:ns:yang:sr:openconfig-mpls-ldp-deviations";

    prefix "nokia-oc-ldp-devs";

    import nokia-sros-yang-extensions     { prefix "sros-ext"; }
    import openconfig-extensions          { prefix "oc-ext"; }
    import openconfig-inet-types          { prefix "oc-inet"; }
    import openconfig-interfaces          { prefix "oc-if"; }
    import openconfig-mpls                { prefix "oc-mpls"; }
    import openconfig-mpls-ldp            { prefix "oc-ldp"; }
    import openconfig-network-instance    { prefix "oc-netinst"; }
    import openconfig-types               { prefix "oc-types"; }
    import openconfig-yang-types          { prefix "oc-yang"; }

    sros-ext:sros-major-release "rel22";

    organization "Nokia";

    contact
        "Nokia SR OS Support
         Web: <http://www.nokia.com>";

    description
        "This module contains the list of deviations against the openconfig-mpls-ldp
          module for the Nokia SR OS based routers.

         Copyright 2016 Nokia. All rights reserved. Reproduction of this document
         is authorized on the condition that the foregoing copyright notice is included.

         This nokia-sr-openconfig-mpls-ldp-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-07-09";

    deviation /oc-netinst:network-instances/oc-netinst:network-instance/oc-netinst:mpls/oc-netinst:signaling-protocols/oc-netinst:ldp/oc-netinst:global/oc-netinst:config {
        deviate not-supported;
    }

    deviation /oc-netinst:network-instances/oc-netinst:network-instance/oc-netinst:mpls/oc-netinst:signaling-protocols/oc-netinst:ldp/oc-netinst:global/oc-netinst:state {
        deviate not-supported;
    }

    deviation /oc-netinst:network-instances/oc-netinst:network-instance/oc-netinst:mpls/oc-netinst:signaling-protocols/oc-netinst:ldp/oc-netinst:global/oc-netinst:graceful-restart/oc-netinst:config/oc-netinst:reconnect-time {
        deviate not-supported;
    }

    deviation /oc-netinst:network-instances/oc-netinst:network-instance/oc-netinst:mpls/oc-netinst:signaling-protocols/oc-netinst:ldp/oc-netinst:global/oc-netinst:graceful-restart/oc-netinst:config/oc-netinst:recovery-time {
        deviate not-supported;
    }

    deviation /oc-netinst:network-instances/oc-netinst:network-instance/oc-netinst:mpls/oc-netinst:signaling-protocols/oc-netinst:ldp/oc-netinst:global/oc-netinst:graceful-restart/oc-netinst:config/oc-netinst:forwarding-holdtime {
        deviate not-supported;
    }

    deviation /oc-netinst:network-instances/oc-netinst:network-instance/oc-netinst:mpls/oc-netinst:signaling-protocols/oc-netinst:ldp/oc-netinst:global/oc-netinst:graceful-restart/oc-netinst:config/oc-netinst:enabled {
        deviate not-supported;
    }

    deviation /oc-netinst:network-instances/oc-netinst:network-instance/oc-netinst:mpls/oc-netinst:signaling-protocols/oc-netinst:ldp/oc-netinst:global/oc-netinst:graceful-restart/oc-netinst:config/oc-netinst:helper-enable {
        deviate add {
            default false;
        }
    }

    deviation /oc-netinst:network-instances/oc-netinst:network-instance/oc-netinst:mpls/oc-netinst:signaling-protocols/oc-netinst:ldp/oc-netinst:global/oc-netinst:graceful-restart/oc-netinst:state/oc-netinst:reconnect-time {
        deviate not-supported;
    }

    deviation /oc-netinst:network-instances/oc-netinst:network-instance/oc-netinst:mpls/oc-netinst:signaling-protocols/oc-netinst:ldp/oc-netinst:global/oc-netinst:graceful-restart/oc-netinst:state/oc-netinst:recovery-time {
        deviate not-supported;
    }

    deviation /oc-netinst:network-instances/oc-netinst:network-instance/oc-netinst:mpls/oc-netinst:signaling-protocols/oc-netinst:ldp/oc-netinst:global/oc-netinst:graceful-restart/oc-netinst:state/oc-netinst:forwarding-holdtime {
        deviate not-supported;
    }

    deviation /oc-netinst:network-instances/oc-netinst:network-instance/oc-netinst:mpls/oc-netinst:signaling-protocols/oc-netinst:ldp/oc-netinst:global/oc-netinst:graceful-restart/oc-netinst:state/oc-netinst:enabled {
        deviate not-supported;
    }

    deviation /oc-netinst:network-instances/oc-netinst:network-instance/oc-netinst:mpls/oc-netinst:signaling-protocols/oc-netinst:ldp/oc-netinst:global/oc-netinst:graceful-restart/oc-netinst:state/oc-netinst:helper-enable {
        deviate add {
            default false;
        }
    }

    deviation /oc-netinst:network-instances/oc-netinst:network-instance/oc-netinst:mpls/oc-netinst:signaling-protocols/oc-netinst:ldp/oc-netinst:global/oc-netinst:authentication/oc-netinst:config/oc-netinst:enable {
        deviate not-supported;
    }

    deviation /oc-netinst:network-instances/oc-netinst:network-instance/oc-netinst:mpls/oc-netinst:signaling-protocols/oc-netinst:ldp/oc-netinst:global/oc-netinst:authentication/oc-netinst:config/oc-netinst:authentication-key {
        deviate replace {
            type oc-types:routing-password {
                length 1..370;
                pattern "(.{1,255})|(.{1,364} hash)|(.{1,364} hash2)|(.{1,344} custom)";
            }
        }
    }

    deviation /oc-netinst:network-instances/oc-netinst:network-instance/oc-netinst:mpls/oc-netinst:signaling-protocols/oc-netinst:ldp/oc-netinst:global/oc-netinst:authentication/oc-netinst:state/oc-netinst:enable {
        deviate not-supported;
    }

    deviation /oc-netinst:network-instances/oc-netinst:network-instance/oc-netinst:mpls/oc-netinst:signaling-protocols/oc-netinst:ldp/oc-netinst:global/oc-netinst:authentication/oc-netinst:state/oc-netinst:authentication-key {
        deviate replace {
            type oc-types:routing-password {
                length 1..370;
                pattern "(.{1,255})|(.{1,364} hash)|(.{1,364} hash2)|(.{1,344} custom)";
            }
        }
    }

    deviation /oc-netinst:network-instances/oc-netinst:network-instance/oc-netinst:mpls/oc-netinst:signaling-protocols/oc-netinst:ldp/oc-netinst:interface-attributes/oc-netinst:config/oc-netinst:hello-holdtime {
        deviate add {
            default 15;
        }
        deviate replace {
            type uint16 {
                range 3..65535;
            }
        }
        deviate add {
            units seconds;
        }
    }

    deviation /oc-netinst:network-instances/oc-netinst:network-instance/oc-netinst:mpls/oc-netinst:signaling-protocols/oc-netinst:ldp/oc-netinst:interface-attributes/oc-netinst:config/oc-netinst:hello-interval {
        deviate add {
            default 5;
        }
        deviate replace {
            type uint16 {
                range 1..65535;
            }
        }
        deviate add {
            units seconds;
        }
    }

    deviation /oc-netinst:network-instances/oc-netinst:network-instance/oc-netinst:mpls/oc-netinst:signaling-protocols/oc-netinst:ldp/oc-netinst:interface-attributes/oc-netinst:interfaces/oc-netinst:interface/oc-netinst:config/oc-netinst:hello-holdtime {
        deviate add {
            default 15;
        }
        deviate replace {
            type uint16 {
                range 3..65535;
            }
        }
        deviate add {
            units seconds;
        }
    }

    deviation /oc-netinst:network-instances/oc-netinst:network-instance/oc-netinst:mpls/oc-netinst:signaling-protocols/oc-netinst:ldp/oc-netinst:interface-attributes/oc-netinst:interfaces/oc-netinst:interface/oc-netinst:config/oc-netinst:hello-interval {
        deviate add {
            default 5;
        }
        deviate replace {
            type uint16 {
                range 1..65535;
            }
        }
        deviate add {
            units seconds;
        }
    }

    deviation /oc-netinst:network-instances/oc-netinst:network-instance/oc-netinst:mpls/oc-netinst:signaling-protocols/oc-netinst:ldp/oc-netinst:interface-attributes/oc-netinst:interfaces/oc-netinst:interface/oc-netinst:state/oc-netinst:counters {
        deviate not-supported;
    }

    deviation /oc-netinst:network-instances/oc-netinst:network-instance/oc-netinst:mpls/oc-netinst:signaling-protocols/oc-netinst:ldp/oc-netinst:interface-attributes/oc-netinst:interfaces/oc-netinst:interface {
        deviate add {
            unique "oc-netinst:interface-ref/oc-netinst:config/oc-netinst:interface oc-netinst:interface-ref/oc-netinst:config/oc-netinst:subinterface";
        }
    }

    deviation /oc-netinst:network-instances/oc-netinst:network-instance/oc-netinst:mpls/oc-netinst:signaling-protocols/oc-netinst:ldp/oc-netinst:targeted/oc-netinst:config/oc-netinst:hello-holdtime {
        deviate add {
            default 15;
        }
        deviate replace {
            type uint16 {
                range 3..65535;
            }
        }
        deviate add {
            units seconds;
        }
    }

    deviation /oc-netinst:network-instances/oc-netinst:network-instance/oc-netinst:mpls/oc-netinst:signaling-protocols/oc-netinst:ldp/oc-netinst:targeted/oc-netinst:config/oc-netinst:hello-interval {
        deviate add {
            default 5;
        }
        deviate replace {
            type uint16 {
                range 1..65535;
            }
        }
        deviate add {
            units seconds;
        }
    }

    deviation /oc-netinst:network-instances/oc-netinst:network-instance/oc-netinst:mpls/oc-netinst:signaling-protocols/oc-netinst:ldp/oc-netinst:targeted/oc-netinst:address-families/oc-netinst:address-family/oc-netinst:targets/oc-netinst:target/oc-netinst:config/oc-netinst:hello-holdtime {
        deviate add {
            default 15;
        }
        deviate replace {
            type uint16 {
                range 3..65535;
            }
        }
        deviate add {
            units seconds;
        }
    }

    deviation /oc-netinst:network-instances/oc-netinst:network-instance/oc-netinst:mpls/oc-netinst:signaling-protocols/oc-netinst:ldp/oc-netinst:targeted/oc-netinst:address-families/oc-netinst:address-family/oc-netinst:targets/oc-netinst:target/oc-netinst:config/oc-netinst:hello-interval {
        deviate add {
            default 5;
        }
        deviate replace {
            type uint16 {
                range 1..65535;
            }
        }
        deviate add {
            units seconds;
        }
    }

    deviation /oc-netinst:network-instances/oc-netinst:network-instance/oc-netinst:mpls/oc-netinst:signaling-protocols/oc-netinst:ldp/oc-netinst:targeted/oc-netinst:address-families/oc-netinst:address-family/oc-netinst:targets/oc-netinst:target/oc-netinst:config/oc-netinst:local-address {
        deviate not-supported;
    }

    deviation /oc-netinst:network-instances/oc-netinst:network-instance/oc-netinst:mpls/oc-netinst:signaling-protocols/oc-netinst:ldp/oc-netinst:targeted/oc-netinst:address-families/oc-netinst:address-family/oc-netinst:targets/oc-netinst:target/oc-netinst:state/oc-netinst:local-address {
        deviate not-supported;
    }

    deviation /oc-netinst:network-instances/oc-netinst:network-instance/oc-netinst:mpls/oc-netinst:signaling-protocols/oc-netinst:ldp/oc-netinst:neighbors/oc-netinst:neighbor/oc-netinst:config/oc-netinst:label-space-id {
        deviate add {
            must ". = 0";
        }
    }

    deviation /oc-netinst:network-instances/oc-netinst:network-instance/oc-netinst:mpls/oc-netinst:signaling-protocols/oc-netinst:ldp/oc-netinst:neighbors/oc-netinst:neighbor/oc-netinst:state/oc-netinst:label-space-id {
        deviate add {
            must ". = 0";
        }
    }

    deviation /oc-netinst:network-instances/oc-netinst:network-instance/oc-netinst:mpls/oc-netinst:signaling-protocols/oc-netinst:ldp/oc-netinst:neighbors/oc-netinst:neighbor/oc-netinst:hello-adjacencies/oc-netinst:hello-adjacency/oc-netinst:state/oc-netinst:adjacency-type {
        deviate replace {
            type enumeration {
                enum LINK;
                enum TARGETED;
                enum BOTH;
            }
        }
    }

    deviation /oc-netinst:network-instances/oc-netinst:network-instance/oc-netinst:mpls/oc-netinst:signaling-protocols/oc-netinst:ldp/oc-netinst:neighbors/oc-netinst:neighbor/oc-netinst:hello-adjacencies/oc-netinst:hello-adjacency/oc-netinst:state/oc-netinst:last-clear {
        deviate not-supported;
    }

    deviation /oc-netinst:network-instances/oc-netinst:network-instance/oc-netinst:mpls/oc-netinst:signaling-protocols/oc-netinst:ldp/oc-netinst:neighbors/oc-netinst:neighbor/oc-netinst:hello-adjacencies/oc-netinst:hello-adjacency/oc-netinst:state/oc-netinst:hello-dropped {
        deviate not-supported;
    }

    deviation /oc-netinst:network-instances/oc-netinst:network-instance/oc-netinst:mpls/oc-netinst:signaling-protocols/oc-netinst:ldp/oc-netinst:neighbors/oc-netinst:neighbor/oc-netinst:hello-adjacencies/oc-netinst:hello-adjacency/oc-netinst:hello-holdtime/oc-netinst:state/oc-netinst:negotiated {
        deviate not-supported;
    }

    deviation /oc-netinst:network-instances/oc-netinst:network-instance/oc-netinst:mpls/oc-netinst:signaling-protocols/oc-netinst:ldp/oc-netinst:neighbors/oc-netinst:neighbor/oc-netinst:hello-adjacencies/oc-netinst:hello-adjacency/oc-netinst:hello-holdtime/oc-netinst:state/oc-netinst:next-hello {
        deviate not-supported;
    }

    deviation /oc-netinst:network-instances/oc-netinst:network-instance/oc-netinst:mpls/oc-netinst:signaling-protocols/oc-netinst:ldp/oc-netinst:neighbors/oc-netinst:neighbor/oc-netinst:authentication/oc-netinst:config/oc-netinst:enable {
        deviate not-supported;
    }

    deviation /oc-netinst:network-instances/oc-netinst:network-instance/oc-netinst:mpls/oc-netinst:signaling-protocols/oc-netinst:ldp/oc-netinst:neighbors/oc-netinst:neighbor/oc-netinst:authentication/oc-netinst:config/oc-netinst:authentication-key {
        deviate replace {
            type oc-types:routing-password {
                length 1..370;
                pattern "(.{1,255})|(.{1,364} hash)|(.{1,364} hash2)|(.{1,344} custom)";
            }
        }
    }

    deviation /oc-netinst:network-instances/oc-netinst:network-instance/oc-netinst:mpls/oc-netinst:signaling-protocols/oc-netinst:ldp/oc-netinst:neighbors/oc-netinst:neighbor/oc-netinst:authentication/oc-netinst:state/oc-netinst:enable {
        deviate not-supported;
    }

    deviation /oc-netinst:network-instances/oc-netinst:network-instance/oc-netinst:mpls/oc-netinst:signaling-protocols/oc-netinst:ldp/oc-netinst:neighbors/oc-netinst:neighbor/oc-netinst:authentication/oc-netinst:state/oc-netinst:authentication-key {
        deviate replace {
            type oc-types:routing-password {
                length 1..370;
                pattern "(.{1,255})|(.{1,364} hash)|(.{1,364} hash2)|(.{1,344} custom)";
            }
        }
    }

}
