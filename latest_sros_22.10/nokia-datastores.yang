module nokia-datastores {

    yang-version "1.1";

    namespace "urn:nokia.com:sros:ns:yang:sr:datastores";

    prefix "nokia-ds";

    import ietf-datastores                { prefix "ds"; }
    import nokia-sros-yang-extensions     { prefix "sros-ext"; }

    sros-ext:sros-major-release "rel22";

    organization "Nokia";

    contact
        "Nokia SR OS Support
         Web: <http://www.nokia.com>";

    description
        "Common proprietary Nokia datastores data types used in the SR OS management system.

         Copyright 2016 Nokia. All rights reserved. Reproduction of this document
         is authorized on the condition that the foregoing copyright notice is included.

         This nokia-datastores YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-12-04" {
        description "Initial nokia revision.";
        reference "Proprietary Nokia SR OS datastores";
    }

    identity configure-region {
        base ds:datastore;
    }

    identity configure-running {
        base configure-region;
        description "The configure-running configuration datastore.";
    }

    identity configure-candidate {
        base configure-region;
        description "The configure-candidate configuration datastore.";
    }

    identity configure-startup {
        base configure-region;
        description "The configure-startup configuration datastore.";
    }

    identity configure-intended {
        base configure-region;
        description "The configure-intended configuration datastore.";
    }

    identity configure-operational {
        base configure-region;
        description "The configure-intended configuration datastore.";
    }

    identity li-region {
        base ds:datastore;
    }

    identity li-running {
        base li-region;
        description "The li-running configuration datastore.";
    }

    identity li-candidate {
        base li-region;
        description "The li-candidate configuration datastore.";
    }

    identity li-startup {
        base li-region;
        description "The li-startup configuration datastore.";
    }

    identity li-intended {
        base li-region;
        description "The li-intended configuration datastore.";
    }

    identity bof-region {
        base ds:datastore;
    }

    identity bof-running {
        base bof-region;
        description "The bof-running configuration datastore.";
    }

    identity bof-candidate {
        base bof-region;
        description "The bof-candidate configuration datastore.";
    }

    identity bof-startup {
        base bof-region;
        description "The bof-startup configuration datastore.";
    }

    identity bof-intended {
        base bof-region;
        description "The bof-intended configuration datastore.";
    }






}
