submodule nokia-state-port-tdm {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }


    sros-ext:sros-major-release "rel21";

    organization "Nokia";

    contact
        "Nokia SR OS Support
         Web: <http://www.nokia.com>";

    description
        "Nokia YANG Data model with operational state for TDM ports on SR OS based routers.

         Copyright 2016 Nokia. All rights reserved. Reproduction of this document
         is authorized on the condition that the foregoing copyright notice is included.

         This nokia-state-port-tdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-26";

    grouping state-port-tdm {
        container tdm {
            description "Enter the tdm context";

            leaf gain {
                type int32;
                units "decibels";
                description "Indicates the number of decibels the received signal is increased to compensate for loss.";
            }

            list ds1 {
                key "ds1-index";
                description "Enter the ds1 list instance";

                leaf ds1-index {
                    type types-port:tdm-ds1-index;
                    description "DS-1 channel ID";
                }

                leaf clock-sync-state {
                    type types-port:tdm-dsx-clock-sync-state;
                    description "Indicates the current clock synchronization state";
                }

                leaf current-alarms {
                    type types-port:tdm-report-alarm;
                    description "Indicates the current alarms on the TDM DS1 port.";
                }

                leaf in-remote-loop {
                    type boolean;
                    description "Indicates whether the remote end has put this channel in remote loopback.";
                }

                leaf master-port-id {
                    type types-sros:port;
                    description "Indicates the current clock synchronization master port identifier.";
                }

                list channel-group {
                    key "ds0-index";
                    description "Enter the channel-group list instance";

                    leaf ds0-index {
                        type uint32 {
                            range "1..24";
                        }
                        description "Channel group ID";
                    }

                    leaf oper-mtu {
                        type uint32;
                        units "bytes";
                        description "Indicates the negotiated size of the largest packet which can be sent on the channel.";
                    }

                    container ppp {
                        description "Enter the ppp context";

                        leaf header-compression {
                            type bits {
                                bit acfc                           { position 0; }
                                bit pfc                            { position 1; }
                            }
                            description "Indicates whether or not the ACFC or PFC protocols are requested in config requests sent and accepted in config requests received.";
                        }

                        leaf line-monitor-method {
                            type enumeration {
                                enum "none"                         { value 1; }
                                enum "keepalive"                    { value 2; }
                                enum "lqm"                          { value 3; }
                            }
                            description "Indicates the type of line monitoring packets being sent and received on this PPP link";
                        }

                        leaf time-to-link-drop {
                            type types-sros:time-interval;
                            description "Indicates the time remaining before the link will be declared dropped if a keepalive echo reply packet is not received.";
                        }

                        container local {
                            description "Enter the local context";

                            leaf ipv4-address {
                                type types-sros:ipv4-address;
                                description "Indicates the IPv4 address of the local end of the PPP link.";
                            }

                            leaf ipv6-address {
                                type types-sros:ipv6-address;
                                description "Indicates the IPv6 address of the local end of the PPP link.";
                            }

                            leaf magic-number {
                                type uint32;
                                description "Indicates the magic number to be sent to the peer. The magic number provides a method to detect loopbacks. If the value of local-magic-number is the same as the value of remote-magic-number, then it is possible that the link might be looped back. If the two magic numbers do not match, then the link is not looped back.";
                            }

                        } // container local

                        container remote {
                            description "Enter the remote context";

                            leaf ipv4-address {
                                type types-sros:ipv4-address;
                                description "Indicates the IPv4 address of the remote end of the PPP link.";
                            }

                            leaf ipv6-address {
                                type types-sros:ipv6-address;
                                description "Indicates the IPv6 address of the remote end of the PPP link.";
                            }

                            leaf mac-address {
                                type yang:mac-address;
                                description "Indicates the Ethernet MAC address sent by the remote end of the PPP link.";
                            }

                            leaf magic-number {
                                type uint32;
                                description "Indicates the magic number sent by the peer. If the value of local-magic-number is the same as the value of remote-magic-number, then it is possible that the link might be looped back. If the two magic numbers do not match, then the link is not looped back.";
                            }

                        } // container remote

                        container statistics {
                            description "Enter the statistics context";

                            leaf last-cleared-time {
                                type yang:date-and-time;
                                description "Indicates the last time that keepalive stats were cleared. Note that the keepalive stats are cleared when changing from LQM to keepalives or vice versa.";
                            }

                            leaf in-packets {
                                type yang:counter32;
                                description "Indicates the number of echo-reply packets received.";
                            }

                            leaf out-packets {
                                type yang:counter32;
                                description "Indicates the number of echo-request packets sent.";
                            }

                            leaf threshold-exceeded {
                                type yang:counter32;
                                description "Indicates the number of times that drop-count was reached.";
                            }

                        } // container statistics

                        list control-protocol {
                            key "protocol";
                            description "Enter the control-protocol list instance";

                            leaf protocol {
                                type enumeration {
                                    enum "lcp"                          { value 1; }
                                    enum "ipcp"                         { value 2; }
                                    enum "mplscp"                       { value 3; }
                                    enum "bcp"                          { value 4; }
                                    enum "osicp"                        { value 5; }
                                    enum "lqr"                          { value 6; }
                                    enum "ipv6cp"                       { value 7; }
                                }
                                description "Indicates the control protocol type.";
                            }

                            leaf state {
                                type enumeration {
                                    enum "initial"                      { value 1; }
                                    enum "starting"                     { value 2; }
                                    enum "closed"                       { value 3; }
                                    enum "stopped"                      { value 4; }
                                    enum "closing"                      { value 5; }
                                    enum "stopping"                     { value 6; }
                                    enum "request-sent"                 { value 7; }
                                    enum "ack-received"                 { value 8; }
                                    enum "ack-sent"                     { value 9; }
                                    enum "opened"                       { value 10; }
                                }
                                description "Indicates the current state of the PPP Control Protocol on this interface.";
                            }

                            leaf state-last-changed {
                                type yang:date-and-time;
                                description "Indicates the last time the value of state changed.";
                            }

                            leaf restart-count {
                                type yang:counter32;
                                description "Indicates the number of times the control protocol has reached the 'opened' state.";
                            }

                            leaf restart-count-last-cleared {
                                type yang:date-and-time;
                                description "Indicates the last time restart-count has been reset to zero.";
                            }

                        } // list control-protocol

                    } // container ppp

                } // list channel-group

                container statistics {
                    description "Enter the statistics context";

                    leaf bursty-errored-seconds {
                        type yang:counter32;
                        description "Indicates the number of Bursty Errored Seconds (BES).";
                    }

                    leaf controlled-slip-seconds {
                        type yang:counter32;
                        description "Indicates the number of Controlled Slip Seconds (CSS).";
                    }

                    leaf degraded-minutes {
                        type yang:counter32;
                        description "Indicates the number of Degraded Minutes (DM).";
                    }

                    leaf errored-seconds {
                        type yang:counter32;
                        description "Indicates the number of Errored Seconds (ES).";
                    }

                    leaf line-errored-seconds {
                        type yang:counter32;
                        description "Indicates the number of Line Errored Seconds (LES).";
                    }

                    leaf path-coding-violations {
                        type yang:counter32;
                        description "Indicates the number of Path Coding Violations (PCV)";
                    }

                    leaf severely-errored-seconds {
                        type yang:counter32;
                        description "Indicates the number of Severely Errored Seconds (SES).";
                    }

                    leaf severely-errored-frame-seconds {
                        type yang:counter32;
                        description "Indicates the number of Severely Errored Frame Seconds (SEFS).";
                    }

                    leaf unavailable-seconds {
                        type yang:counter32;
                        description "Indicates the number of Unavailable Seconds (UAS).";
                    }

                    leaf line-coding-violations {
                        type yang:counter32;
                        description "Indicates the number of Line Coding Violations (LCV)";
                    }

                    leaf looped {
                        type yang:counter32;
                        description "Indicates the number of looped occurrences.";
                    }

                    container far-end {
                        description "Enter the far-end context";

                        leaf bursty-errored-seconds {
                            type yang:counter32;
                            description "Indicates the number of Bursty Errored Seconds (BES).";
                        }

                        leaf controlled-slip-seconds {
                            type yang:counter32;
                            description "Indicates the number of Controlled Slip Seconds (CSS).";
                        }

                        leaf degraded-minutes {
                            type yang:counter32;
                            description "Indicates the number of Degraded Minutes (DM).";
                        }

                        leaf errored-seconds {
                            type yang:counter32;
                            description "Indicates the number of Errored Seconds (ES).";
                        }

                        leaf line-errored-seconds {
                            type yang:counter32;
                            description "Indicates the number of Line Errored Seconds (LES).";
                        }

                        leaf path-coding-violations {
                            type yang:counter32;
                            description "Indicates the number of Path Coding Violations (PCV)";
                        }

                        leaf severely-errored-seconds {
                            type yang:counter32;
                            description "Indicates the number of Severely Errored Seconds (SES).";
                        }

                        leaf severely-errored-frame-seconds {
                            type yang:counter32;
                            description "Indicates the number of Severely Errored Frame Seconds (SEFS).";
                        }

                        leaf unavailable-seconds {
                            type yang:counter32;
                            description "Indicates the number of Unavailable Seconds (UAS).";
                        }

                    } // container far-end

                    container receive {
                        description "Enter the receive context";

                        leaf alarm-indication-signal {
                            type yang:counter32;
                            description "Indicates the number of Alarm Indication Signal (AIS) occurrences.";
                        }

                        leaf loss-of-signal {
                            type yang:counter32;
                            description "Indicates the number of loss of signal (LOS) occurrences.";
                        }

                        leaf loss-of-frame {
                            type yang:counter32;
                            description "Indicates the number of loss of frame (LOF) occurrences.";
                        }

                        leaf far-end-loss-of-frame {
                            type yang:counter32;
                            description "Indicates the number of Far End Loss of Frame (FE-LOF) occurrences.";
                        }

                    } // container receive

                    container transmit {
                        description "Enter the transmit context";

                        leaf alarm-indication-signal {
                            type yang:counter32;
                            description "Indicates the number of Alarm Indication Signal (AIS) occurrences.";
                        }

                        leaf far-end-loss-of-frame {
                            type yang:counter32;
                            description "Indicates the number of Far End Loss of Frame (FE-LOF) occurrences.";
                        }

                    } // container transmit

                } // container statistics

            } // list ds1

            list ds3 {
                key "ds3-index";
                description "Enter the ds3 list instance";

                leaf ds3-index {
                    type types-port:tdm-ds3-index;
                    description "TDM DS3 index";
                }

                leaf current-alarms {
                    type types-port:tdm-report-alarm;
                    description "Indicates the current alarms on the TDM DS3 port.";
                }

                leaf in-feac-loop {
                    type boolean;
                    description "Indicates whether the remote end has put this channel in FEAC (Far End Alarm Control) loopback.";
                }

                leaf oper-mtu {
                    type uint32;
                    units "bytes";
                    description "Indicates the negotiated size of the largest packet which can be sent on the channel.";
                }

                container maintenance-data-link {
                    description "Enter the maintenance-data-link context";

                    container far-end {
                        description "Enter the far-end context";

                        leaf idle-signal-port {
                            type string {
                                length "0..38";
                            }
                            description "Indicates the port number string received in the MDL idle signal message.";
                        }

                        leaf test-signal-generator {
                            type string {
                                length "0..38";
                            }
                            description "Indicates the generator number string received in the MDL test signal message.";
                        }

                        leaf equipment-id-code {
                            type string {
                                length "0..10";
                            }
                            description "Configure the Equipment ID Code (EIC) of the MDL.";
                        }

                        leaf facility-id-code {
                            type string {
                                length "0..38";
                            }
                            description "Configure the Facility ID Code sent in the MDL Path message.";
                        }

                        leaf frame-id-code {
                            type string {
                                length "0..10";
                            }
                            description "Configure the Frame ID Code (FIC) of the MDL.";
                        }

                        leaf location-id-code {
                            type string {
                                length "0..11";
                            }
                            description "Configure the Location ID Code (LIC) of the MDL.";
                        }

                        leaf unit-id-code {
                            type string {
                                length "0..6";
                            }
                            description "Configure the Unit ID Code (UIC) of the MDL.";
                        }

                    } // container far-end

                } // container maintenance-data-link

                container ppp {
                    description "Enter the ppp context";

                    leaf header-compression {
                        type bits {
                            bit acfc                           { position 0; }
                            bit pfc                            { position 1; }
                        }
                        description "Indicates whether or not the ACFC or PFC protocols are requested in config requests sent and accepted in config requests received.";
                    }

                    leaf line-monitor-method {
                        type enumeration {
                            enum "none"                         { value 1; }
                            enum "keepalive"                    { value 2; }
                            enum "lqm"                          { value 3; }
                        }
                        description "Indicates the type of line monitoring packets being sent and received on this PPP link";
                    }

                    leaf time-to-link-drop {
                        type types-sros:time-interval;
                        description "Indicates the time remaining before the link will be declared dropped if a keepalive echo reply packet is not received.";
                    }

                    container local {
                        description "Enter the local context";

                        leaf ipv4-address {
                            type types-sros:ipv4-address;
                            description "Indicates the IPv4 address of the local end of the PPP link.";
                        }

                        leaf ipv6-address {
                            type types-sros:ipv6-address;
                            description "Indicates the IPv6 address of the local end of the PPP link.";
                        }

                        leaf magic-number {
                            type uint32;
                            description "Indicates the magic number to be sent to the peer. The magic number provides a method to detect loopbacks. If the value of local-magic-number is the same as the value of remote-magic-number, then it is possible that the link might be looped back. If the two magic numbers do not match, then the link is not looped back.";
                        }

                    } // container local

                    container remote {
                        description "Enter the remote context";

                        leaf ipv4-address {
                            type types-sros:ipv4-address;
                            description "Indicates the IPv4 address of the remote end of the PPP link.";
                        }

                        leaf ipv6-address {
                            type types-sros:ipv6-address;
                            description "Indicates the IPv6 address of the remote end of the PPP link.";
                        }

                        leaf mac-address {
                            type yang:mac-address;
                            description "Indicates the Ethernet MAC address sent by the remote end of the PPP link.";
                        }

                        leaf magic-number {
                            type uint32;
                            description "Indicates the magic number sent by the peer. If the value of local-magic-number is the same as the value of remote-magic-number, then it is possible that the link might be looped back. If the two magic numbers do not match, then the link is not looped back.";
                        }

                    } // container remote

                    container statistics {
                        description "Enter the statistics context";

                        leaf last-cleared-time {
                            type yang:date-and-time;
                            description "Indicates the last time that keepalive stats were cleared. Note that the keepalive stats are cleared when changing from LQM to keepalives or vice versa.";
                        }

                        leaf in-packets {
                            type yang:counter32;
                            description "Indicates the number of echo-reply packets received.";
                        }

                        leaf out-packets {
                            type yang:counter32;
                            description "Indicates the number of echo-request packets sent.";
                        }

                        leaf threshold-exceeded {
                            type yang:counter32;
                            description "Indicates the number of times that drop-count was reached.";
                        }

                    } // container statistics

                    list control-protocol {
                        key "protocol";
                        description "Enter the control-protocol list instance";

                        leaf protocol {
                            type enumeration {
                                enum "lcp"                          { value 1; }
                                enum "ipcp"                         { value 2; }
                                enum "mplscp"                       { value 3; }
                                enum "bcp"                          { value 4; }
                                enum "osicp"                        { value 5; }
                                enum "lqr"                          { value 6; }
                                enum "ipv6cp"                       { value 7; }
                            }
                            description "Indicates the control protocol type.";
                        }

                        leaf state {
                            type enumeration {
                                enum "initial"                      { value 1; }
                                enum "starting"                     { value 2; }
                                enum "closed"                       { value 3; }
                                enum "stopped"                      { value 4; }
                                enum "closing"                      { value 5; }
                                enum "stopping"                     { value 6; }
                                enum "request-sent"                 { value 7; }
                                enum "ack-received"                 { value 8; }
                                enum "ack-sent"                     { value 9; }
                                enum "opened"                       { value 10; }
                            }
                            description "Indicates the current state of the PPP Control Protocol on this interface.";
                        }

                        leaf state-last-changed {
                            type yang:date-and-time;
                            description "Indicates the last time the value of state changed.";
                        }

                        leaf restart-count {
                            type yang:counter32;
                            description "Indicates the number of times the control protocol has reached the 'opened' state.";
                        }

                        leaf restart-count-last-cleared {
                            type yang:date-and-time;
                            description "Indicates the last time restart-count has been reset to zero.";
                        }

                    } // list control-protocol

                } // container ppp

                container statistics {
                    description "Enter the statistics context";

                    leaf unavailable-seconds {
                        type yang:counter32;
                        description "Indicates the number of Unavailable Seconds (UAS).";
                    }

                    leaf severely-errored-frame-seconds {
                        type yang:counter32;
                        description "Indicates the number of Severely Errored Frame Seconds (SEFS).";
                    }

                    leaf looped {
                        type yang:counter32;
                        description "Indicates the number of looped occurrences.";
                    }

                    container c-bit {
                        description "Enter the c-bit context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                    } // container c-bit

                    container p-bit {
                        description "Enter the p-bit context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                    } // container p-bit

                    container line {
                        description "Enter the line context";

                        leaf coding-violations {
                            type yang:counter32;
                            description "Indicates the number of Coding Violations (CV)";
                        }

                        leaf errored-seconds {
                            type yang:counter32;
                            description "Indicates the number of Errored Seconds (ES).";
                        }

                    } // container line

                    container far-end {
                        description "Enter the far-end context";

                        leaf unavailable-seconds {
                            type yang:counter32;
                            description "Indicates the number of Unavailable Seconds (UAS).";
                        }

                        container c-bit {
                            description "Enter the c-bit context";

                            leaf coding-violations {
                                type yang:counter32;
                                description "Indicates the number of Coding Violations (CV)";
                            }

                            leaf errored-seconds {
                                type yang:counter32;
                                description "Indicates the number of Errored Seconds (ES).";
                            }

                            leaf severely-errored-seconds {
                                type yang:counter32;
                                description "Indicates the number of Severely Errored Seconds (SES).";
                            }

                        } // container c-bit

                    } // container far-end

                    container receive {
                        description "Enter the receive context";

                        leaf alarm-indication-signal {
                            type yang:counter32;
                            description "Indicates the number of Alarm Indication Signal (AIS) occurrences.";
                        }

                        leaf loss-of-signal {
                            type yang:counter32;
                            description "Indicates the number of loss of signal (LOS) occurrences.";
                        }

                        leaf loss-of-frame {
                            type yang:counter32;
                            description "Indicates the number of loss of frame (LOF) occurrences.";
                        }

                        leaf remote-alarm-indication {
                            type yang:counter32;
                            description "Indicates the number of Remote Alarm Indication (RAI) occurrences.";
                        }

                    } // container receive

                    container transmit {
                        description "Enter the transmit context";

                        leaf alarm-indication-signal {
                            type yang:counter32;
                            description "Indicates the number of Alarm Indication Signal (AIS) occurrences.";
                        }

                        leaf remote-alarm-indication {
                            type yang:counter32;
                            description "Indicates the number of Remote Alarm Indication (RAI) occurrences.";
                        }

                    } // container transmit

                } // container statistics

            } // list ds3

            list e3 {
                key "e3-index";
                description "Enter the e3 list instance";

                leaf e3-index {
                    type types-port:tdm-e3-index;
                    description "Components making up the SONET/SDH Path";
                }

                leaf clock-sync-state {
                    type types-port:tdm-dsx-clock-sync-state;
                    description "Indicates the clock sync state of the TDM E3 port.";
                }

                leaf clock-master-port-id {
                    type types-sros:port;
                    description "Indicates the clock master port-id of the TDM E3 port.";
                }

                leaf current-alarms {
                    type types-port:tdm-report-alarm;
                    description "Indicates the current alarms on the TDM E3 port.";
                }

                leaf oper-mtu {
                    type uint32;
                    units "bytes";
                    description "Indicates the negotiated size of the largest packet which can be sent on the channel.";
                }

                container ppp {
                    description "Enter the ppp context";

                    leaf header-compression {
                        type bits {
                            bit acfc                           { position 0; }
                            bit pfc                            { position 1; }
                        }
                        description "Indicates whether or not the ACFC or PFC protocols are requested in config requests sent and accepted in config requests received.";
                    }

                    leaf line-monitor-method {
                        type enumeration {
                            enum "none"                         { value 1; }
                            enum "keepalive"                    { value 2; }
                            enum "lqm"                          { value 3; }
                        }
                        description "Indicates the type of line monitoring packets being sent and received on this PPP link";
                    }

                    leaf time-to-link-drop {
                        type types-sros:time-interval;
                        description "Indicates the time remaining before the link will be declared dropped if a keepalive echo reply packet is not received.";
                    }

                    container local {
                        description "Enter the local context";

                        leaf ipv4-address {
                            type types-sros:ipv4-address;
                            description "Indicates the IPv4 address of the local end of the PPP link.";
                        }

                        leaf ipv6-address {
                            type types-sros:ipv6-address;
                            description "Indicates the IPv6 address of the local end of the PPP link.";
                        }

                        leaf magic-number {
                            type uint32;
                            description "Indicates the magic number to be sent to the peer. The magic number provides a method to detect loopbacks. If the value of local-magic-number is the same as the value of remote-magic-number, then it is possible that the link might be looped back. If the two magic numbers do not match, then the link is not looped back.";
                        }

                    } // container local

                    container remote {
                        description "Enter the remote context";

                        leaf ipv4-address {
                            type types-sros:ipv4-address;
                            description "Indicates the IPv4 address of the remote end of the PPP link.";
                        }

                        leaf ipv6-address {
                            type types-sros:ipv6-address;
                            description "Indicates the IPv6 address of the remote end of the PPP link.";
                        }

                        leaf mac-address {
                            type yang:mac-address;
                            description "Indicates the Ethernet MAC address sent by the remote end of the PPP link.";
                        }

                        leaf magic-number {
                            type uint32;
                            description "Indicates the magic number sent by the peer. If the value of local-magic-number is the same as the value of remote-magic-number, then it is possible that the link might be looped back. If the two magic numbers do not match, then the link is not looped back.";
                        }

                    } // container remote

                    container statistics {
                        description "Enter the statistics context";

                        leaf last-cleared-time {
                            type yang:date-and-time;
                            description "Indicates the last time that keepalive stats were cleared. Note that the keepalive stats are cleared when changing from LQM to keepalives or vice versa.";
                        }

                        leaf in-packets {
                            type yang:counter32;
                            description "Indicates the number of echo-reply packets received.";
                        }

                        leaf out-packets {
                            type yang:counter32;
                            description "Indicates the number of echo-request packets sent.";
                        }

                        leaf threshold-exceeded {
                            type yang:counter32;
                            description "Indicates the number of times that drop-count was reached.";
                        }

                    } // container statistics

                    list control-protocol {
                        key "protocol";
                        description "Enter the control-protocol list instance";

                        leaf protocol {
                            type enumeration {
                                enum "lcp"                          { value 1; }
                                enum "ipcp"                         { value 2; }
                                enum "mplscp"                       { value 3; }
                                enum "bcp"                          { value 4; }
                                enum "osicp"                        { value 5; }
                                enum "lqr"                          { value 6; }
                                enum "ipv6cp"                       { value 7; }
                            }
                            description "Indicates the control protocol type.";
                        }

                        leaf state {
                            type enumeration {
                                enum "initial"                      { value 1; }
                                enum "starting"                     { value 2; }
                                enum "closed"                       { value 3; }
                                enum "stopped"                      { value 4; }
                                enum "closing"                      { value 5; }
                                enum "stopping"                     { value 6; }
                                enum "request-sent"                 { value 7; }
                                enum "ack-received"                 { value 8; }
                                enum "ack-sent"                     { value 9; }
                                enum "opened"                       { value 10; }
                            }
                            description "Indicates the current state of the PPP Control Protocol on this interface.";
                        }

                        leaf state-last-changed {
                            type yang:date-and-time;
                            description "Indicates the last time the value of state changed.";
                        }

                        leaf restart-count {
                            type yang:counter32;
                            description "Indicates the number of times the control protocol has reached the 'opened' state.";
                        }

                        leaf restart-count-last-cleared {
                            type yang:date-and-time;
                            description "Indicates the last time restart-count has been reset to zero.";
                        }

                    } // list control-protocol

                } // container ppp

                container statistics {
                    description "Enter the statistics context";

                    leaf unavailable-seconds {
                        type yang:counter32;
                        description "Indicates the number of Unavailable Seconds (UAS).";
                    }

                    leaf severely-errored-frame-seconds {
                        type yang:counter32;
                        description "Indicates the number of Severely Errored Frame Seconds (SEFS).";
                    }

                    leaf looped {
                        type yang:counter32;
                        description "Indicates the number of looped occurrences.";
                    }

                    container c-bit {
                        description "Enter the c-bit context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                    } // container c-bit

                    container p-bit {
                        description "Enter the p-bit context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                    } // container p-bit

                    container line {
                        description "Enter the line context";

                        leaf coding-violations {
                            type yang:counter32;
                            description "Indicates the number of Coding Violations (CV)";
                        }

                        leaf errored-seconds {
                            type yang:counter32;
                            description "Indicates the number of Errored Seconds (ES).";
                        }

                    } // container line

                    container far-end {
                        description "Enter the far-end context";

                        leaf unavailable-seconds {
                            type yang:counter32;
                            description "Indicates the number of Unavailable Seconds (UAS).";
                        }

                        container c-bit {
                            description "Enter the c-bit context";

                            leaf coding-violations {
                                type yang:counter32;
                                description "Indicates the number of Coding Violations (CV)";
                            }

                            leaf errored-seconds {
                                type yang:counter32;
                                description "Indicates the number of Errored Seconds (ES).";
                            }

                            leaf severely-errored-seconds {
                                type yang:counter32;
                                description "Indicates the number of Severely Errored Seconds (SES).";
                            }

                        } // container c-bit

                    } // container far-end

                    container receive {
                        description "Enter the receive context";

                        leaf alarm-indication-signal {
                            type yang:counter32;
                            description "Indicates the number of Alarm Indication Signal (AIS) occurrences.";
                        }

                        leaf loss-of-signal {
                            type yang:counter32;
                            description "Indicates the number of loss of signal (LOS) occurrences.";
                        }

                        leaf loss-of-frame {
                            type yang:counter32;
                            description "Indicates the number of loss of frame (LOF) occurrences.";
                        }

                        leaf remote-alarm-indication {
                            type yang:counter32;
                            description "Indicates the number of Remote Alarm Indication (RAI) occurrences.";
                        }

                    } // container receive

                    container transmit {
                        description "Enter the transmit context";

                        leaf alarm-indication-signal {
                            type yang:counter32;
                            description "Indicates the number of Alarm Indication Signal (AIS) occurrences.";
                        }

                        leaf remote-alarm-indication {
                            type yang:counter32;
                            description "Indicates the number of Remote Alarm Indication (RAI) occurrences.";
                        }

                    } // container transmit

                } // container statistics

            } // list e3

            list e1 {
                key "e1-index";
                description "Enter the e1 list instance";

                leaf e1-index {
                    type types-port:tdm-e1-index;
                    description "E-1 channel";
                }

                leaf clock-sync-state {
                    type types-port:tdm-dsx-clock-sync-state;
                    description "Indicates the current clock synchronization state";
                }

                leaf current-alarms {
                    type types-port:tdm-report-alarm;
                    description "Indicates the current alarms on the TDM DS1 port.";
                }

                leaf in-remote-loop {
                    type boolean;
                    description "Indicates whether the remote end has put this channel in remote loopback.";
                }

                leaf master-port-id {
                    type types-sros:port;
                    description "Indicates the current clock synchronization master port identifier.";
                }

                list channel-group {
                    key "ds0-index";
                    description "Enter the channel-group list instance";

                    leaf ds0-index {
                        type uint32 {
                            range "1..32";
                        }
                        description "DS0 channel group in a channelized DS1 or E1 circuit";
                    }

                    leaf oper-mtu {
                        type uint32;
                        units "bytes";
                        description "Indicates the negotiated size of the largest packet which can be sent on the channel.";
                    }

                    container ppp {
                        description "Enter the ppp context";

                        leaf header-compression {
                            type bits {
                                bit acfc                           { position 0; }
                                bit pfc                            { position 1; }
                            }
                            description "Indicates whether or not the ACFC or PFC protocols are requested in config requests sent and accepted in config requests received.";
                        }

                        leaf line-monitor-method {
                            type enumeration {
                                enum "none"                         { value 1; }
                                enum "keepalive"                    { value 2; }
                                enum "lqm"                          { value 3; }
                            }
                            description "Indicates the type of line monitoring packets being sent and received on this PPP link";
                        }

                        leaf time-to-link-drop {
                            type types-sros:time-interval;
                            description "Indicates the time remaining before the link will be declared dropped if a keepalive echo reply packet is not received.";
                        }

                        container local {
                            description "Enter the local context";

                            leaf ipv4-address {
                                type types-sros:ipv4-address;
                                description "Indicates the IPv4 address of the local end of the PPP link.";
                            }

                            leaf ipv6-address {
                                type types-sros:ipv6-address;
                                description "Indicates the IPv6 address of the local end of the PPP link.";
                            }

                            leaf magic-number {
                                type uint32;
                                description "Indicates the magic number to be sent to the peer. The magic number provides a method to detect loopbacks. If the value of local-magic-number is the same as the value of remote-magic-number, then it is possible that the link might be looped back. If the two magic numbers do not match, then the link is not looped back.";
                            }

                        } // container local

                        container remote {
                            description "Enter the remote context";

                            leaf ipv4-address {
                                type types-sros:ipv4-address;
                                description "Indicates the IPv4 address of the remote end of the PPP link.";
                            }

                            leaf ipv6-address {
                                type types-sros:ipv6-address;
                                description "Indicates the IPv6 address of the remote end of the PPP link.";
                            }

                            leaf mac-address {
                                type yang:mac-address;
                                description "Indicates the Ethernet MAC address sent by the remote end of the PPP link.";
                            }

                            leaf magic-number {
                                type uint32;
                                description "Indicates the magic number sent by the peer. If the value of local-magic-number is the same as the value of remote-magic-number, then it is possible that the link might be looped back. If the two magic numbers do not match, then the link is not looped back.";
                            }

                        } // container remote

                        container statistics {
                            description "Enter the statistics context";

                            leaf last-cleared-time {
                                type yang:date-and-time;
                                description "Indicates the last time that keepalive stats were cleared. Note that the keepalive stats are cleared when changing from LQM to keepalives or vice versa.";
                            }

                            leaf in-packets {
                                type yang:counter32;
                                description "Indicates the number of echo-reply packets received.";
                            }

                            leaf out-packets {
                                type yang:counter32;
                                description "Indicates the number of echo-request packets sent.";
                            }

                            leaf threshold-exceeded {
                                type yang:counter32;
                                description "Indicates the number of times that drop-count was reached.";
                            }

                        } // container statistics

                        list control-protocol {
                            key "protocol";
                            description "Enter the control-protocol list instance";

                            leaf protocol {
                                type enumeration {
                                    enum "lcp"                          { value 1; }
                                    enum "ipcp"                         { value 2; }
                                    enum "mplscp"                       { value 3; }
                                    enum "bcp"                          { value 4; }
                                    enum "osicp"                        { value 5; }
                                    enum "lqr"                          { value 6; }
                                    enum "ipv6cp"                       { value 7; }
                                }
                                description "Indicates the control protocol type.";
                            }

                            leaf state {
                                type enumeration {
                                    enum "initial"                      { value 1; }
                                    enum "starting"                     { value 2; }
                                    enum "closed"                       { value 3; }
                                    enum "stopped"                      { value 4; }
                                    enum "closing"                      { value 5; }
                                    enum "stopping"                     { value 6; }
                                    enum "request-sent"                 { value 7; }
                                    enum "ack-received"                 { value 8; }
                                    enum "ack-sent"                     { value 9; }
                                    enum "opened"                       { value 10; }
                                }
                                description "Indicates the current state of the PPP Control Protocol on this interface.";
                            }

                            leaf state-last-changed {
                                type yang:date-and-time;
                                description "Indicates the last time the value of state changed.";
                            }

                            leaf restart-count {
                                type yang:counter32;
                                description "Indicates the number of times the control protocol has reached the 'opened' state.";
                            }

                            leaf restart-count-last-cleared {
                                type yang:date-and-time;
                                description "Indicates the last time restart-count has been reset to zero.";
                            }

                        } // list control-protocol

                    } // container ppp

                } // list channel-group

                container statistics {
                    description "Enter the statistics context";

                    leaf bursty-errored-seconds {
                        type yang:counter32;
                        description "Indicates the number of Bursty Errored Seconds (BES).";
                    }

                    leaf controlled-slip-seconds {
                        type yang:counter32;
                        description "Indicates the number of Controlled Slip Seconds (CSS).";
                    }

                    leaf degraded-minutes {
                        type yang:counter32;
                        description "Indicates the number of Degraded Minutes (DM).";
                    }

                    leaf errored-seconds {
                        type yang:counter32;
                        description "Indicates the number of Errored Seconds (ES).";
                    }

                    leaf line-errored-seconds {
                        type yang:counter32;
                        description "Indicates the number of Line Errored Seconds (LES).";
                    }

                    leaf path-coding-violations {
                        type yang:counter32;
                        description "Indicates the number of Path Coding Violations (PCV)";
                    }

                    leaf severely-errored-seconds {
                        type yang:counter32;
                        description "Indicates the number of Severely Errored Seconds (SES).";
                    }

                    leaf severely-errored-frame-seconds {
                        type yang:counter32;
                        description "Indicates the number of Severely Errored Frame Seconds (SEFS).";
                    }

                    leaf unavailable-seconds {
                        type yang:counter32;
                        description "Indicates the number of Unavailable Seconds (UAS).";
                    }

                    leaf line-coding-violations {
                        type yang:counter32;
                        description "Indicates the number of Line Coding Violations (LCV)";
                    }

                    leaf looped {
                        type yang:counter32;
                        description "Indicates the number of looped occurrences.";
                    }

                    container far-end {
                        description "Enter the far-end context";

                        leaf bursty-errored-seconds {
                            type yang:counter32;
                            description "Indicates the number of Bursty Errored Seconds (BES).";
                        }

                        leaf controlled-slip-seconds {
                            type yang:counter32;
                            description "Indicates the number of Controlled Slip Seconds (CSS).";
                        }

                        leaf degraded-minutes {
                            type yang:counter32;
                            description "Indicates the number of Degraded Minutes (DM).";
                        }

                        leaf errored-seconds {
                            type yang:counter32;
                            description "Indicates the number of Errored Seconds (ES).";
                        }

                        leaf line-errored-seconds {
                            type yang:counter32;
                            description "Indicates the number of Line Errored Seconds (LES).";
                        }

                        leaf path-coding-violations {
                            type yang:counter32;
                            description "Indicates the number of Path Coding Violations (PCV)";
                        }

                        leaf severely-errored-seconds {
                            type yang:counter32;
                            description "Indicates the number of Severely Errored Seconds (SES).";
                        }

                        leaf severely-errored-frame-seconds {
                            type yang:counter32;
                            description "Indicates the number of Severely Errored Frame Seconds (SEFS).";
                        }

                        leaf unavailable-seconds {
                            type yang:counter32;
                            description "Indicates the number of Unavailable Seconds (UAS).";
                        }

                    } // container far-end

                    container receive {
                        description "Enter the receive context";

                        leaf alarm-indication-signal {
                            type yang:counter32;
                            description "Indicates the number of Alarm Indication Signal (AIS) occurrences.";
                        }

                        leaf loss-of-signal {
                            type yang:counter32;
                            description "Indicates the number of loss of signal (LOS) occurrences.";
                        }

                        leaf loss-of-frame {
                            type yang:counter32;
                            description "Indicates the number of loss of frame (LOF) occurrences.";
                        }

                        leaf far-end-loss-of-frame {
                            type yang:counter32;
                            description "Indicates the number of Far End Loss of Frame (FE-LOF) occurrences.";
                        }

                    } // container receive

                    container transmit {
                        description "Enter the transmit context";

                        leaf alarm-indication-signal {
                            type yang:counter32;
                            description "Indicates the number of Alarm Indication Signal (AIS) occurrences.";
                        }

                        leaf far-end-loss-of-frame {
                            type yang:counter32;
                            description "Indicates the number of Far End Loss of Frame (FE-LOF) occurrences.";
                        }

                    } // container transmit

                } // container statistics

            } // list e1

        } // container tdm

    } // grouping state-port-tdm

}
