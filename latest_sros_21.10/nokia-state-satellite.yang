submodule nokia-state-satellite {

    yang-version "1.1";

    belongs-to nokia-state { prefix "state"; }

    import nokia-sros-yang-extensions     { prefix "sros-ext"; }
    import nokia-types-chassis            { prefix "types-chassis"; }
    import nokia-types-sros               { prefix "types-sros"; }

    include nokia-state-system;


    sros-ext:sros-major-release "rel21";

    organization "Nokia";

    contact
        "Nokia SR OS Support
         Web: <http://www.nokia.com>";

    description
        "Nokia YANG Data model with operational state for satellite parameters on SR OS based routers.

         Copyright 2016 Nokia. All rights reserved. Reproduction of this document
         is authorized on the condition that the foregoing copyright notice is included.

         This nokia-state-satellite YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-09-09";

    grouping state-satellite {
        container satellite {
            description "Enter the satellite context";

            list ethernet-satellite {
                key "satellite-id";
                description "Enter the ethernet-satellite list instance";

                leaf satellite-id {
                    type uint32 {
                        range "1..20";
                    }
                    description "The unique index identifying this satellite";
                }

                leaf console-access-status {
                    type enumeration {
                        enum "disabled"                     { value 1; }
                        enum "requested"                    { value 2; }
                        enum "enabled"                      { value 3; }
                        enum "not-applicable"               { value 4; }
                    }
                    description "The status of console access for this satellite.";
                }

            } // list ethernet-satellite

        } // container satellite

    } // grouping state-satellite

}
