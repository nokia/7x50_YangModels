submodule nokia-state-eth-cfm {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-lldp               { prefix "types-lldp"; }
    import nokia-types-services           { prefix "types-services"; }
    import nokia-types-sros               { prefix "types-sros"; }


    sros-ext:sros-major-release "rel21";

    organization "Nokia";

    contact
        "Nokia SR OS Support
         Web: <http://www.nokia.com>";

    description
        "Nokia YANG Data model with operational state for eth-cfm on SR OS based routers.

         Copyright 2016 Nokia. All rights reserved. Reproduction of this document
         is authorized on the condition that the foregoing copyright notice is included.

         This nokia-state-eth-cfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-01-24";

    grouping state-eth-cfm {
        container eth-cfm {
            description "Enter the eth-cfm context";

            container system-state {
                description "Enter the system-state context";

                leaf ccm-grace-period {
                    type enumeration {
                        enum "active"                       { value 1; }
                        enum "inactive"                     { value 2; }
                    }
                    description "Indicates whether or not the node is actively executing a grace period.";
                }

            } // container system-state

            container default-domain {
                description "Enter the default-domain context";

                container system-settings {
                    description "Enter the system-settings context";

                    leaf level {
                        type types-eth-cfm:mp-level;
                        description "The level for the bridge and VLAN of the default domain";
                    }

                    leaf mhf-creation {
                        type types-eth-cfm:mhf-creation-type;
                        description "A value indicating if the Management entity can create MHFs (MIP Half Function) for the default domain.";
                    }

                    leaf id-permission {
                        type types-eth-cfm:permission-type;
                        description "Sender ID TLV permissions for the default domain.";
                    }

                    leaf mip-ltr-priority {
                        type types-eth-cfm:frame-priority;
                        description "Default priority value to be used for link-trace responses by MIPs in the default domain.";
                    }

                } // container system-settings

            } // container default-domain

            list domain {
                key "md-admin-name";
                description "Enter the domain list instance";

                leaf md-admin-name {
                    type types-eth-cfm:admin-name;
                    description "Unique domain name";
                }

                leaf domain-index {
                    type uint32 {
                        range "1..4294967295";
                    }
                    description "The index of this domain entry.";
                }

                leaf creation-origin {
                    type types-sros:creation-origin;
                    description "The mechanism which created this eth-cfm domain entry.";
                }

                leaf next-ma-index {
                    type uint32 {
                        range "0..max";
                    }
                    description "The next available association index, or a zero to indicate that none exist.";
                }

                list association {
                    key "ma-admin-name";
                    description "Enter the association list instance";

                    leaf ma-admin-name {
                        type types-eth-cfm:admin-name;
                        description "Domain association name";
                    }

                    leaf association-index {
                        type uint32 {
                            range "1..4294967295";
                        }
                        description "The index of this assosiation entry.";
                    }

                    container statistics {
                        description "Enter the statistics context";

                        leaf total-mep-count {
                            type yang:counter32;
                            description "The number of unique MEPs configured (both local and remote) that are associated with this MA.";
                        }

                    } // container statistics

                    list mep {
                        key "mep-id";
                        description "Enter the mep list instance";

                        leaf mep-id {
                            type types-eth-cfm:mep-id-type;
                            description "A local maintenance association end point identifier unique over a given maintanance association.";
                        }

                        container loopback-results {
                            description "Enter the loopback-results context";

                            container unicast-latest-run {
                                description "Enter the unicast-latest-run context";

                                leaf test-status {
                                    type enumeration {
                                        enum "completed"                    { value 1; }
                                        enum "terminated-incomplete"        { value 2; }
                                        enum "in-progress"                  { value 3; }
                                    }
                                    description "The status of the last test that was requested. If the test-status is failed-to-start the statistics from a prior latest-run are deleted";
                                }

                                leaf start-time {
                                    type yang:date-and-time;
                                    description "UTC date and time when the test started.";
                                }

                                leaf end-time {
                                    type yang:date-and-time;
                                    description "UTC date and time when a test ended.";
                                }

                                leaf remote-mep-id {
                                    type uint32;
                                    description "Indicates the remote mepid used for the last test.";
                                }

                                leaf destination-mac-address {
                                    type yang:mac-address;
                                    description "Indicates the destination mac address used for the last test.";
                                }

                                container statistics {
                                    description "Enter the statistics context";

                                    leaf sent-packets {
                                        type uint32;
                                        description "Indicates the number of packets sent during the last test.";
                                    }

                                    leaf received-in-order {
                                        type yang:counter32;
                                        description "Total number of valid, in-order Loopback Replies received.";
                                    }

                                    leaf received-out-of-order {
                                        type yang:counter32;
                                        description "The total number of valid, out-of-order Loopback Replies received.";
                                    }

                                    leaf received-bad-msdu {
                                        type yang:counter32;
                                        description "The total number of LBRs received whose mac_service_data_unit did not match (except for the OpCode) that of the corresponding LBM (20.2.3).";
                                    }

                                    leaf packet-loss {
                                        type decimal64 {
                                            range "0.00..100.00";
                                            fraction-digits 2;
                                        }
                                        units "percent";
                                        description "Percentage of packet loss during testing.";
                                    }

                                } // container statistics

                            } // container unicast-latest-run

                            container multicast-latest-run {
                                description "Enter the multicast-latest-run context";

                                leaf test-status {
                                    type enumeration {
                                        enum "completed"                    { value 1; }
                                        enum "terminated-incomplete"        { value 2; }
                                        enum "in-progress"                  { value 3; }
                                    }
                                    description "The status of the last test that was requested. If the test-status is failed-to-start the statistics from a prior latest-run are deleted";
                                }

                                leaf start-time {
                                    type yang:date-and-time;
                                    description "UTC date and time when the test started.";
                                }

                                leaf end-time {
                                    type yang:date-and-time;
                                    description "UTC date and time when a test ended.";
                                }

                                container statistics {
                                    description "Enter the statistics context";

                                    leaf sent-packets {
                                        type uint32;
                                        description "Indicates the number of packets sent during the last multicast test.";
                                    }

                                    leaf received-packets {
                                        type yang:counter32;
                                        description "Total number of valid multicast Loopback Replies received.";
                                    }

                                } // container statistics

                                list remote-mep-mac {
                                    key "remote-mac-address";
                                    description "Enter the remote-mep-mac list instance";

                                    leaf remote-mac-address {
                                        type yang:mac-address;
                                        description "Specifies the MAC address of the remote MEP responding to the multicast loopback message.";
                                    }

                                    list sequence-number {
                                        key "id received-index";
                                        description "Enter the sequence-number list instance";

                                        leaf id {
                                            type uint32;
                                            description "Specifies the sequence number contained within the reply message.";
                                        }

                                        leaf received-index {
                                            type uint32;
                                            description "Indicates the order in which the reply was received for the corresponding remote MAC address. It is locally assigned and can be used to detect out of order responses.";
                                        }

                                    } // list sequence-number

                                } // list remote-mep-mac

                            } // container multicast-latest-run

                        } // container loopback-results

                        container linktrace-results {
                            description "Enter the linktrace-results context";

                            container latest-run {
                                description "Enter the latest-run context";

                                leaf test-status {
                                    type enumeration {
                                        enum "completed"                    { value 1; }
                                        enum "terminated-incomplete"        { value 2; }
                                        enum "in-progress"                  { value 3; }
                                    }
                                    description "The status of the last test that was requested. If the test-status is failed-to-start the statistics from a prior latest-run are deleted";
                                }

                                leaf start-time {
                                    type yang:date-and-time;
                                    description "UTC date and time when the test started.";
                                }

                                leaf end-time {
                                    type yang:date-and-time;
                                    description "UTC date and time when a test ended.";
                                }

                                leaf remote-mep-id {
                                    type uint32;
                                    description "Indicates the remote mepid used for the last test.";
                                }

                                leaf destination-mac-address {
                                    type yang:mac-address;
                                    description "Indicates the destination mac address used for the last test.";
                                }

                                list sequence-number {
                                    key "id receive-order";
                                    description "Enter the sequence-number list instance";

                                    leaf id {
                                        type uint32 {
                                            range "0..4294967295";
                                        }
                                        description "Transaction identifier/Sequence number returned by a previous transmit linktrace message command, indicating which LTM's response is going to be returned.";
                                    }

                                    leaf receive-order {
                                        type uint32 {
                                            range "1..4294967295";
                                        }
                                        description "An index to distinguish among multiple LTRs with the same LTR Transaction Identifier field value. dot1agCfmLtrReceiveOrder are assigned sequentially from 1, in the order that the Linktrace Initiator received the LTRs.";
                                    }

                                    leaf ingress-mac {
                                        type yang:mac-address;
                                        description "MAC address returned in the ingress MAC address field. If the ingress-action leaf contains the value ing-no-tlv(0), then the contents of this leaf are meaningless.";
                                    }

                                    leaf egress-mac {
                                        type yang:mac-address;
                                        description "MAC address returned in the egress MAC address field. If the egress-action leaf contains the value egr-no-tlv(0), then the contents of this leaf are meaningless.";
                                    }

                                    leaf relay {
                                        type enumeration {
                                            enum "rly-hit"                      { value 1; }
                                            enum "rly-fdb"                      { value 2; }
                                            enum "rly-mpdb"                     { value 3; }
                                        }
                                        description "Value returned in the Relay Action field.";
                                    }

                                    leaf action {
                                        type enumeration {
                                            enum "terminate"                    { value 1; }
                                            enum "forward"                      { value 2; }
                                            enum "none"                         { value 3; }
                                        }
                                        description "Value indicating how the forwarded LTM was processed by the responding MP.";
                                    }

                                    leaf chassis-id-subtype {
                                        type union {
                                            type uint32 {
                                                range "8..255";
                                            }
                                            type types-lldp:chassis-id-subtype;
                                        }
                                        description "This object specifies the format of the Chassis ID returned in the Sender ID TLV of the LTR, if any. This value is meaningless if the chassis-id has a length of 0.";
                                    }

                                    leaf chassis-id {
                                        type string;
                                        description "The Chassis ID returned in the Sender ID TLV of the LTR, if any. The format of this object is determined by the value of the chassis-id-subtype object.";
                                    }

                                    leaf management-address-domain {
                                        type string;
                                        description "The domain that identifies the type and format of the related management-address leaf, used to access the system transmitting the LTR. The value is received in the LTR Sender ID TLV from that system. Typical values will be one of (not all inclusive) list: snmpUDPDomain (from SNMPv2-TM, RFC3417) snmpIeee802Domain (from SNMP-IEEE802-TM-MIB, RFC4789) The value 'zeroDotZero' (from RFC2578) indicates 'no management address was present in the LTR', in which case the related management-address leaf must not contain a value.";
                                    }

                                    leaf management-address {
                                        type string;
                                        description "The TAddress that can be used to access the SNMP agent of the system transmitting the CCM, received in the CCM Sender ID TLV from that system. If the related management-address-domain leaf contains the value 'zeroDotZero', this object must have a zero-length OCTET STRING as a value.";
                                    }

                                } // list sequence-number

                            } // container latest-run

                        } // container linktrace-results

                    } // list mep

                } // list association

            } // list domain

            container resource-limits {
                description "Enter the resource-limits context";

                container domain {
                    description "Enter the domain context";

                    leaf current-usage {
                        type yang:counter32;
                        description "Indicates the current resource usage of the ETH-CFM component.";
                    }

                    leaf system-limit {
                        type yang:counter32;
                        description "Indicates the maximum resource usage limit of the ETH-CFM component.";
                    }

                } // container domain

                container association {
                    description "Enter the association context";

                    leaf current-usage {
                        type yang:counter32;
                        description "Indicates the current resource usage of the ETH-CFM component.";
                    }

                    leaf system-limit {
                        type yang:counter32;
                        description "Indicates the maximum resource usage limit of the ETH-CFM component.";
                    }

                    container extended-association {
                        description "Enter the extended-association context";

                        leaf current-usage {
                            type yang:counter32;
                            description "Indicates the current resource usage of the ETH-CFM component.";
                        }

                        leaf system-limit {
                            type yang:counter32;
                            description "Indicates the maximum resource usage limit of the ETH-CFM component.";
                        }

                    } // container extended-association

                } // container association

                container mep {
                    description "Enter the mep context";

                    leaf current-usage {
                        type yang:counter32;
                        description "Indicates the current resource usage of the ETH-CFM component.";
                    }

                    leaf system-limit {
                        type yang:counter32;
                        description "Indicates the maximum resource usage limit of the ETH-CFM component.";
                    }

                    container one-second {
                        description "Enter the one-second context";

                        leaf current-usage {
                            type yang:counter32;
                            description "Indicates the current resource usage of the ETH-CFM component.";
                        }

                        leaf system-limit {
                            type yang:counter32;
                            description "Indicates the maximum resource usage limit of the ETH-CFM component.";
                        }

                    } // container one-second

                    container sub-second {
                        description "Enter the sub-second context";

                        leaf current-usage {
                            type yang:counter32;
                            description "Indicates the current resource usage of the ETH-CFM component.";
                        }

                        leaf system-limit {
                            type yang:counter32;
                            description "Indicates the maximum resource usage limit of the ETH-CFM component.";
                        }

                    } // container sub-second

                    container remote-mep {
                        description "Enter the remote-mep context";

                        leaf current-usage {
                            type yang:counter32;
                            description "Indicates the current resource usage of the ETH-CFM component.";
                        }

                        leaf system-limit {
                            type yang:counter32;
                            description "Indicates the maximum resource usage limit of the ETH-CFM component.";
                        }

                    } // container remote-mep

                } // container mep

                container primary-vlan-management-point {
                    description "Enter the primary-vlan-management-point context";

                    container ingress {
                        description "Enter the ingress context";

                        leaf current-usage {
                            type yang:counter32;
                            description "Indicates the current resource usage of the ETH-CFM component.";
                        }

                        leaf system-limit {
                            type yang:counter32;
                            description "Indicates the maximum resource usage limit of the ETH-CFM component.";
                        }

                    } // container ingress

                    container egress {
                        description "Enter the egress context";

                        leaf current-usage {
                            type yang:counter32;
                            description "Indicates the current resource usage of the ETH-CFM component.";
                        }

                        leaf system-limit {
                            type yang:counter32;
                            description "Indicates the maximum resource usage limit of the ETH-CFM component.";
                        }

                    } // container egress

                } // container primary-vlan-management-point

                container ais {
                    description "Enter the ais context";

                    leaf current-usage {
                        type yang:counter32;
                        description "Indicates the current resource usage of the ETH-CFM component.";
                    }

                    leaf system-limit {
                        type yang:counter32;
                        description "Indicates the maximum resource usage limit of the ETH-CFM component.";
                    }

                } // container ais

                container csf {
                    description "Enter the csf context";

                    leaf current-usage {
                        type yang:counter32;
                        description "Indicates the current resource usage of the ETH-CFM component.";
                    }

                    leaf system-limit {
                        type yang:counter32;
                        description "Indicates the maximum resource usage limit of the ETH-CFM component.";
                    }

                } // container csf

                container lmm-statistics-collectors {
                    description "Enter the lmm-statistics-collectors context";

                    leaf current-usage {
                        type yang:counter32;
                        description "Indicates the current resource usage of the ETH-CFM component.";
                    }

                    leaf system-limit {
                        type yang:counter32;
                        description "Indicates the maximum resource usage limit of the ETH-CFM component.";
                    }

                } // container lmm-statistics-collectors

                container lbm-concurrent-test {
                    description "Enter the lbm-concurrent-test context";

                    leaf current-usage {
                        type yang:counter32;
                        description "Indicates the current resource usage of the ETH-CFM component.";
                    }

                    leaf system-limit {
                        type yang:counter32;
                        description "Indicates the maximum resource usage limit of the ETH-CFM component.";
                    }

                    container multicast-concurrent-test {
                        description "Enter the multicast-concurrent-test context";

                        leaf current-usage {
                            type yang:counter32;
                            description "Indicates the current resource usage of the ETH-CFM component.";
                        }

                        leaf system-limit {
                            type yang:counter32;
                            description "Indicates the maximum resource usage limit of the ETH-CFM component.";
                        }

                    } // container multicast-concurrent-test

                } // container lbm-concurrent-test

                container ltm-concurrent-test {
                    description "Enter the ltm-concurrent-test context";

                    leaf current-usage {
                        type yang:counter32;
                        description "Indicates the current resource usage of the ETH-CFM component.";
                    }

                    leaf system-limit {
                        type yang:counter32;
                        description "Indicates the maximum resource usage limit of the ETH-CFM component.";
                    }

                } // container ltm-concurrent-test

            } // container resource-limits

            list learned-remote-mac {
                key "md-admin-name ma-admin-name local-mep-id remote-mep-id";
                description "Enter the learned-remote-mac list instance";

                leaf md-admin-name {
                    type leafref {
                        path "../../domain/md-admin-name";
                    }
                    description "A unique administratively assigned name used to identify a domain.";
                }

                leaf ma-admin-name {
                    type leafref {
                        path "../../domain/association/ma-admin-name";
                    }
                    description "A unique administratively assigned name used to identify an association.";
                }

                leaf local-mep-id {
                    type types-eth-cfm:mep-id-type;
                    description "Specifies a local Maintenance Association (MA) End Point identifier unique over a given maintanance association.";
                }

                leaf remote-mep-id {
                    type types-eth-cfm:mep-id-type;
                    description "Specifies a remote Maintenance Association (MA) End Point identifier unique over a given maintanance association.";
                }

                leaf remote-mac-address {
                    type yang:mac-address;
                    description "The the source MAC address used by the remote MEP in the most recently received CCM PDU.";
                }

                leaf stale-flag {
                    type boolean;
                    description "Flag that indicates if the learned MAC entry for this remote MEP matches the entry found in the list on the local MEP. The value 'false' indicates that the MAC address matches the entry found in both the lists for the same local and remote MEP values and therefore is not considered stale. The value 'true' indicates either the entries do not match, or there is no equivalent entry for the remote MEP in the list on the local MEP, so the learned remote MAC address in this table is considered stale.";
                }

                leaf changed-flag {
                    type boolean;
                    description "Indicates if the learned MAC entry for this remote MEP has been modified in the last CCM interval of the local MEP. The value 'true' indicates that the local MEP received a CCM from the remote MEP with a MAC address that does not match the address in learned-remote-mac from the last CCM interval of the local MEP. The new address will be stored in learned-remote-mac. The value 'false' indicates a new entry or an entry where learned-remote-mac has not changed in over one CCM interval. This object can be used to detect if a remote MEP MAC address has recently changed. This may help detect configuration changes of remote MEP MAC addresses, or possibly duplicate remote MEPs configured in the network.";
                }

            } // list learned-remote-mac

            container statistics {
                description "Enter the statistics context";

                leaf receive-count {
                    type yang:counter32;
                    description "Indicates the number of received ETH-CFM packets on the node.";
                }

                leaf transmit-count {
                    type yang:counter32;
                    description "Indicates the number of transmitted ETH-CFM packets on the node.";
                }

                leaf congestion-drops {
                    type yang:counter32;
                    description "Indicates the number of dropped ETH-CFM packets on the node. A packet is dropped because of resource contention.";
                }

                leaf error-discards {
                    type yang:counter32;
                    description "Indicates the number of discarded ETH-CFM packets on the node. A packet may be discarded for several reasons including, but not limited to, malformed PDU, invalid TLVs, MEP admin down, etc.";
                }

                leaf ais-transmit-active {
                    type yang:counter32;
                    description "Indicates the number of sessions where fault (AIS or other) is actively being transmitted.";
                }

                leaf ais-transmit-fail {
                    type yang:counter32;
                    description "Indicates the number of sessions where fault (AIS or other) can't be transmitted due to lack of resources.";
                }

                list opcode {
                    key "opcode-name";
                    description "Enter the opcode list instance";

                    leaf opcode-name {
                        type types-eth-cfm:statistics-opcode-name;
                        description "Integer that defines which CFM PDU Opcode the statictics refer to.";
                    }

                    leaf transmitted {
                        type yang:counter32;
                        description "The total number of PDUs transmitted from the node with the specified Opcode.";
                    }

                    leaf received {
                        type yang:counter32;
                        description "The total number of PDUs received on the node with the specified Opcode.";
                    }

                } // list opcode

            } // container statistics

            container cfm-stack-table {
                description "Enter the cfm-stack-table context";

                container sap {
                    description "Enter the sap context";

                    list sap {
                        key "sap-id level direction";
                        description "Enter the sap list instance";

                        leaf sap-id {
                            type types-sros:sap;
                            description "SAP identifier.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list sap

                } // container sap

                container eth-ring {
                    description "Enter the eth-ring context";

                    list port-and-raps-tag {
                        key "port-and-raps-tag-id level direction";
                        description "Enter the port-and-raps-tag list instance";

                        leaf port-and-raps-tag-id {
                            type types-sros:port-and-encap;
                            description "Port-id and raps-tag associated with the eth-ring path.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list port-and-raps-tag

                } // container eth-ring

                container facility {
                    description "Enter the facility context";

                    list port {
                        key "port-id vlan level direction";
                        description "Enter the port list instance";

                        leaf port-id {
                            type types-sros:port;
                            description "Port identifier.";
                        }

                        leaf vlan {
                            type types-eth-cfm:vlan-id-or-none;
                            description "The VLAN ID that uniquely identifies a specific VLAN.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list port

                    list interface {
                        key "interface-name level direction";
                        description "Enter the interface list instance";

                        leaf interface-name {
                            type types-sros:interface-name;
                            description "Router interface name.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list interface

                } // container facility

                container sdp {
                    description "Enter the sdp context";

                    list sdp-bind {
                        key "sdp-bind-id level direction";
                        description "Enter the sdp-bind list instance";

                        leaf sdp-bind-id {
                            type types-services:sdp-bind-id;
                            description "SDP Binding identifier as <sdp-id>:<vc-id>. sdp-id - [1..32767] vc-id - [1..4294967295].";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list sdp-bind

                } // container sdp

                container virtual {
                    description "Enter the virtual context";

                    list service {
                        key "service-name level direction";
                        description "Enter the service list instance";

                        leaf service-name {
                            type types-services:service-name;
                            description "Name of service.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list service

                } // container virtual

                container sap-primary-vlan {
                    description "Enter the sap-primary-vlan context";

                    list sap {
                        key "sap-id primary-vlan level direction";
                        description "Enter the sap list instance";

                        leaf sap-id {
                            type types-sros:sap;
                            description "SAP identifier.";
                        }

                        leaf primary-vlan {
                            type uint32;
                            description "Primary Vlan ID.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                    } // list sap

                } // container sap-primary-vlan

                container sdp-primary-vlan {
                    description "Enter the sdp-primary-vlan context";

                    list sdp-bind {
                        key "sdp-bind-id primary-vlan level direction";
                        description "Enter the sdp-bind list instance";

                        leaf sdp-bind-id {
                            type types-services:sdp-bind-id;
                            description "SDP Binding identifier as <sdp-id>:<vc-id>. sdp-id - [1..32767] vc-id - [1..4294967295].";
                        }

                        leaf primary-vlan {
                            type uint32;
                            description "Primary Vlan ID.";
                        }

                        leaf level {
                            type types-eth-cfm:mp-level;
                            description "The level for the bridge and VLAN of the default domain.";
                        }

                        leaf direction {
                            type types-eth-cfm:mp-direction;
                            description "The direction the MEP/MIP faces on the Bridge port. If 'down' the Management Point (MP) sends CFM PDUs away from the MAC Relay Entity. If 'up' the MP sends CFM PDUs towards the MAC Relay Entity.";
                        }

                        leaf md-admin-name {
                            type types-eth-cfm:admin-name;
                            description "A unique administratively assigned name used to identify a domain.";
                        }

                        leaf ma-admin-name {
                            type types-eth-cfm:admin-name;
                            description "A unique administratively assigned name used to identify an association.";
                        }

                        leaf mep-id {
                            type types-eth-cfm:mep-id-type;
                            description "Indicates a local Maintenance association End Point identifier unique over a given maintanance association.";
                        }

                        leaf is-mip {
                            type boolean;
                            description "Indicates if the Maintenance Point is a MIP.";
                        }

                        leaf mac-address {
                            type yang:mac-address;
                            description "MAC address of the Maintenance Endpoint.";
                        }

                    } // list sdp-bind

                } // container sdp-primary-vlan

            } // container cfm-stack-table

        } // container eth-cfm

    } // grouping state-eth-cfm

}
