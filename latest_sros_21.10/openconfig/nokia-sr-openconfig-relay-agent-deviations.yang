module nokia-sr-openconfig-relay-agent-deviations {

    namespace "urn:nokia.com:sros:ns:yang:sr:openconfig-relay-agent-deviations";

    prefix "nokia-oc-relay-devs";

    import nokia-sros-yang-extensions     { prefix "sros-ext"; }
    import openconfig-extensions          { prefix "oc-ext"; }
    import openconfig-inet-types          { prefix "oc-inet"; }
    import openconfig-interfaces          { prefix "oc-if"; }
    import openconfig-relay-agent         { prefix "oc-relay"; }

    sros-ext:sros-major-release "rel21";

    organization "Nokia";

    contact
        "Nokia SR OS Support
         Web: <http://www.nokia.com>";

    description
        "This module contains the list of deviations against the openconfig-relay-agent
          module for the Nokia SR OS based routers.

         Copyright 2016 Nokia. All rights reserved. Reproduction of this document
         is authorized on the condition that the foregoing copyright notice is included.

         This nokia-sr-openconfig-relay-agent-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2016-05-16";

    deviation /oc-relay:relay-agent/oc-relay:dhcp/oc-relay:config {
        deviate not-supported;
    }

    deviation /oc-relay:relay-agent/oc-relay:dhcp/oc-relay:state {
        deviate not-supported;
    }

    deviation /oc-relay:relay-agent/oc-relay:dhcp/oc-relay:agent-information-option {
        deviate not-supported;
    }

    deviation /oc-relay:relay-agent/oc-relay:dhcp/oc-relay:interfaces/oc-relay:interface/oc-relay:config/oc-relay:helper-address {
        deviate add {
            max-elements 8;
        }
        deviate replace {
            type oc-inet:ipv4-address;
        }
    }

    deviation /oc-relay:relay-agent/oc-relay:dhcp/oc-relay:interfaces/oc-relay:interface/oc-relay:state/oc-relay:helper-address {
        deviate add {
            max-elements 8;
        }
        deviate replace {
            type oc-inet:ipv4-address;
        }
    }

    deviation /oc-relay:relay-agent/oc-relay:dhcp/oc-relay:interfaces/oc-relay:interface/oc-relay:agent-information-option/oc-relay:config/oc-relay:circuit-id {
        deviate replace {
            type string {
                pattern "ascii-tuple|ifindex|if-name|port-id|vlan-ascii-tuple|none";
            }
        }
    }

    deviation /oc-relay:relay-agent/oc-relay:dhcp/oc-relay:interfaces/oc-relay:interface/oc-relay:agent-information-option/oc-relay:config/oc-relay:remote-id {
        deviate replace {
            type string {
                pattern "mac|string (.*\\S.*)|none";
            }
        }
    }

    deviation /oc-relay:relay-agent/oc-relay:dhcp/oc-relay:interfaces/oc-relay:interface/oc-relay:agent-information-option/oc-relay:state/oc-relay:circuit-id {
        deviate replace {
            type string {
                pattern "ascii-tuple|ifindex|if-name|port-id|vlan-ascii-tuple|none";
            }
        }
    }

    deviation /oc-relay:relay-agent/oc-relay:dhcp/oc-relay:interfaces/oc-relay:interface/oc-relay:agent-information-option/oc-relay:state/oc-relay:remote-id {
        deviate replace {
            type string {
                pattern "mac|string (.*\\S.*)|none";
            }
        }
    }

    deviation /oc-relay:relay-agent/oc-relay:dhcpv6 {
        deviate not-supported;
    }

}
