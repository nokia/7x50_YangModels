submodule nokia-conf-system-telemetry {

    yang-version "1.1";

    belongs-to nokia-conf { prefix "conf"; }

    import nokia-sros-yang-extensions     { prefix "sros-ext"; }
    import nokia-types-qos                { prefix "types-qos"; }
    import nokia-types-sros               { prefix "types-sros"; }
    import nokia-types-system             { prefix "types-system"; }

    include nokia-conf-groups;
    include nokia-conf-system;
    include nokia-conf-system-security;
    include nokia-conf-system-security-tls;


    sros-ext:sros-major-release "rel21";

    organization "Nokia";

    contact
        "Nokia SR OS Support
         Web: <http://www.nokia.com>";

    description
        "Nokia YANG Data model to configure system telemetry parameters. on SR OS based routers.

         Copyright 2016 Nokia. All rights reserved. Reproduction of this document
         is authorized on the condition that the foregoing copyright notice is included.

         This nokia-conf-system-telemetry YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-04";

    grouping conf-system-telemetry {
        container telemetry {
            description "Enter the telemetry context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container notification-bundling {
                description "Enter the notification-bundling context";

                leaf admin-state {
                    type types-sros:admin-state;
                    default "disable";
                    description "Administrative state of notification bundling";
                }

                leaf max-time-granularity {
                    type types-sros:time-duration {
                        range "1..1000";
                    }
                    units "milliseconds";
                    default "100";
                    description "Maximum interval when bundling of notifications occurs";
                }

                leaf max-msg-count {
                    type uint32 {
                        range "2..1000";
                    }
                    default "100";
                    description "Maximum notifications count in telemetry message bundle";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container notification-bundling

            list destination-group {
                key "name";
                max-elements 225;
                description "Enter the destination-group list instance";

                leaf name {
                    type types-sros:named-item;
                    description "Destination group name";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice transport {
                    case tls-client-profile {

                        leaf tls-client-profile {
                            type leafref {
                                path "../../../security/tls/client-tls-profile/client-profile-name";
                            }
                            description "TLS client profile assigned to the destination group";
                        }

                    }
                    case allow-unsecure-connection {

                        leaf allow-unsecure-connection {
                            type empty;
                            description "Allow connection without secured transport protocol";
                        }

                    }
                }
                container tcp-keepalive {
                    description "Enter the tcp-keepalive context";

                    leaf admin-state {
                        type types-sros:admin-state;
                        default "disable";
                        description "Administrative state of the TCP keep-alive algorithm";
                    }

                    leaf idle-time {
                        type types-sros:time-duration {
                            range "1..100000";
                        }
                        units "seconds";
                        default "600";
                        description "Time until the first TCP keepalive probe is sent";
                    }

                    leaf interval {
                        type types-sros:time-duration {
                            range "1..100000";
                        }
                        units "seconds";
                        default "15";
                        description "Time between TCP keepalive probes";
                    }

                    leaf retries {
                        type uint32 {
                            range "3..100";
                        }
                        default "4";
                        description "Number of probe retries before closing the connection";
                    }

                } // container tcp-keepalive

                list destination {
                    key "address port";
                    max-elements 4;
                    ordered-by user;
                    description "Enter the destination list instance";

                    leaf address {
                        type union {
                            type types-sros:ip-address;
                            type types-sros:fully-qualified-domain-name;
                        }
                        description "Address of the destination within the destination group";
                    }

                    leaf port {
                        type types-sros:tcp-udp-port;
                        description "TCP port number for the destination";
                    }

                    leaf router-instance {
                        type string;
                        description "Router name or VPRN service name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list destination

            } // list destination-group

            container persistent-subscriptions {
                description "Enter the persistent-subscriptions context";

                list subscription {
                    key "name";
                    max-elements 225;
                    description "Enter the subscription list instance";

                    leaf name {
                        type types-sros:named-item;
                        description "Persistent subscription name";
                    }

                    leaf admin-state {
                        type types-sros:admin-state;
                        default "disable";
                        description "Administrative state of the persistent subscription";
                    }

                    leaf description {
                        type types-sros:description;
                        description "Text description";
                    }

                    leaf sensor-group {
                        type leafref {
                            path "../../../sensor-groups/sensor-group/name";
                        }
                        description "Sensor group used in the persistent subscription";
                    }

                    leaf mode {
                        type types-system:telemetry-path-mode;
                        description "Mode for telemetry notifications";
                    }

                    leaf sample-interval {
                        when "not(../mode = 'on-change')";
                        type uint64 {
                            range "1000..max";
                        }
                        units "milliseconds";
                        default "10000";
                        description "Sampling interval for the persistent subscription";
                    }

                    leaf destination-group {
                        type leafref {
                            path "../../../destination-group/name";
                        }
                        description "Name of the destination group used in the subscription";
                    }

                    leaf local-source-address {
                        type types-sros:ip-address;
                        description "Local IP address of packets sent from the source";
                    }

                    leaf originated-qos-marking {
                        type types-qos:dscp-name;
                        description "QoS marking used for telemetry notification packets";
                    }

                    leaf encoding {
                        type types-system:telemetry-value-encoding;
                        default "json";
                        description "Encoding used for telemetry notifications";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list subscription

            } // container persistent-subscriptions

            container sensor-groups {
                description "Enter the sensor-groups context";

                list sensor-group {
                    key "name";
                    max-elements 225;
                    description "Enter the sensor-group list instance";

                    leaf name {
                        type types-sros:named-item;
                        description "Sensor group name";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list path {
                        key "xpath";
                        max-elements 4500;
                        description "Add a list entry for path";

                        leaf xpath {
                            type string {
                                length "1..512";
                            }
                            description "gNMI path to be streamed";
                        }

                    } // list path

                } // list sensor-group

            } // container sensor-groups

        } // container telemetry

    } // grouping conf-system-telemetry

}
