submodule nokia-state-openflow {

    yang-version "1.1";

    belongs-to nokia-state { prefix "state"; }

    import nokia-sros-yang-extensions     { prefix "sros-ext"; }
    import nokia-types-sros               { prefix "types-sros"; }


    sros-ext:sros-major-release "rel21";

    organization "Nokia";

    contact
        "Nokia SR OS Support
         Web: <http://www.nokia.com>";

    description
        "Nokia YANG Data model with operational state for openflow parameters on SR OS based routers.

         Copyright 2016 Nokia. All rights reserved. Reproduction of this document
         is authorized on the condition that the foregoing copyright notice is included.

         This nokia-state-openflow YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-07";

    grouping state-openflow {
        container openflow {
            description "Enter the openflow context";

            list of-switch {
                key "name";
                description "Enter the of-switch list instance";

                leaf name {
                    type types-sros:named-item;
                    description "OpenFlow switch name";
                }

                leaf data-path-id {
                    type string {
                        length "1..64";
                    }
                    description "64-bit identifier for this OpenFlow switch instance in hex string. The lower 48-bits are its MAC address and the upper 16-bits are implementation dependent.";
                }

                leaf oper-ofs-id {
                    type uint32 {
                        range "1..8";
                    }
                    description "Operational value of unique identifier of an OpenFlow switch instance.";
                }

                leaf buffer-size {
                    type uint32;
                    description "Maximum number of packets this OpenFlow switch instance can buffer while sending the packets to the controller when the message type is 'packet-in'.";
                }

                leaf num-tables {
                    type uint32;
                    description "Number of OpenFlow tables associated with this switch instance.";
                }

                leaf-list capability {
                    type enumeration {
                        enum "flow-stats"                   { value 1; }
                        enum "table-stats"                  { value 2; }
                        enum "port-stats"                   { value 3; }
                        enum "group-stats"                  { value 4; }
                    }
                    description "Capabilities supported by the datapath associated with this OpenFlow switch instance.";
                }

                list flowtable {
                    key "table-id";
                    description "Enter the flowtable list instance";

                    leaf table-id {
                        type uint32;
                        description "OpenFlow table ID";
                    }

                    leaf oper-state {
                        type types-sros:oper-state;
                        description "Operational status of the flowtable for a given OpenFlow switch instance.";
                    }

                } // list flowtable

                list controller {
                    key "address port";
                    description "Enter the controller list instance";

                    leaf address {
                        type types-sros:ip-unicast-address;
                        description "IP address of the OpenFlow channel to the controller";
                    }

                    leaf port {
                        type uint32 {
                            range "1..65535";
                        }
                        description "Controller port ID";
                    }

                    leaf role {
                        type enumeration {
                            enum "no-change"                    { value 0; }
                            enum "equal"                        { value 1; }
                            enum "master"                       { value 2; }
                            enum "slave"                        { value 3; }
                        }
                        description "The role that the controller will request to OpenFlow switches when multiple controllers are connected to a switch. equal sets the role to equal master sets the requested role to master slave sets the requested role to slave. The default role is equal.";
                    }

                    leaf gen-id {
                        type uint64;
                        description "64-bit generation identifier used for checking of stale messages when the value of controller role is 'master' or 'slave'.";
                    }

                } // list controller

            } // list of-switch

        } // container openflow

    } // grouping state-openflow

}
