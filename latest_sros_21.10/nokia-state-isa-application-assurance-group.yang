submodule nokia-state-isa-application-assurance-group {

    yang-version "1.1";

    belongs-to nokia-state { prefix "state"; }

    import ietf-yang-types                { prefix "yang"; }
    import nokia-sros-yang-extensions     { prefix "sros-ext"; }
    import nokia-types-application-assurance { prefix "types-aa"; }
    import nokia-types-esa                { prefix "types-esa"; }
    import nokia-types-isa                { prefix "types-isa"; }
    import nokia-types-services           { prefix "types-services"; }
    import nokia-types-sros               { prefix "types-sros"; }


    sros-ext:sros-major-release "rel21";

    organization "Nokia";

    contact
        "Nokia SR OS Support
         Web: <http://www.nokia.com>";

    description
        "Nokia YANG Data model with operational state for ISA Application Assurance group configuration on SR OS based routers.

         Copyright 2016 Nokia. All rights reserved. Reproduction of this document
         is authorized on the condition that the foregoing copyright notice is included.

         This nokia-state-isa-application-assurance-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-09-17";

    grouping state-isa-application-assurance-group {
        list application-assurance-group {
            key "aa-group-id";
            description "Enter the application-assurance-group list instance";

            leaf aa-group-id {
                type types-aa:isa-aa-grp-id;
                description "AA group ID";
            }

            leaf oper-state {
                type types-sros:oper-state;
                description
                    "The operational state for the ISA-AA group.
                     When 'outOfService', traffic destined to this ISA-AA group
                     will apply its configured failure behaviour.";
            }

            leaf wlan-gw-group-id {
                type types-isa:wlan-gw-group-id;
                description "The identifier of the WLAN Gateway Integrated Service Adaptor group associated with this ISA-AA group.";
            }

            leaf last-active-change {
                type yang:date-and-time;
                description "The most recent time that an ISA within the group changed to or from the active state.";
            }

            leaf load-balance-state {
                type types-aa:balance-state;
                description "The status of the load-balance operation for the ISA-AA group.";
            }

            list esa {
                key "esa-id vm";
                description "Enter the esa list instance";

                leaf esa-id {
                    type types-esa:esa-id;
                    description "ESA ID";
                }

                leaf vm {
                    type types-esa:vm-id;
                    description "VM ID within the ESA";
                }

                leaf activity-state {
                    type types-aa:isa-activity-state;
                    description "The current activity status of the ISA (MDA or ESA-VM) in the group.";
                }

                container statistics {
                    description "Enter the statistics context";

                    leaf capacity-cost {
                        type yang:gauge32;
                        description "The current capacity cost assigned to the ISA-AA MDA in the group.";
                    }

                    leaf aa-subs {
                        type yang:gauge32;
                        description "The current number of Application Assurance subscriber resources in use on the ISA-AA MDA in the group.";
                    }

                    leaf aa-sub-stats {
                        type yang:gauge32;
                        description "The current number of Application Assurance subscriber statistics resources in use on the ISA-AA MDA in the group.";
                    }

                    leaf transit-ip-addresses {
                        type yang:gauge32;
                        description "The current number of Transit IP subscriber addresses associated with the ISA-AA MDA in the group.";
                    }

                    container transit-prefix-entries {
                        description "Enter the transit-prefix-entries context";

                        leaf ipv4 {
                            type yang:gauge32;
                            description "The current number of transit prefix IPv4 entries active on the ISA-AA MDA in the group.";
                        }

                        leaf ipv4-remote {
                            type yang:gauge32;
                            description "The current number of transit prefix IPv4 remote entries active on the ISA-AA MDA in the group.";
                        }

                        leaf ipv6 {
                            type yang:gauge32;
                            description "The current number of transit prefix IPv6 entries active on the ISA-AA MDA in the group.";
                        }

                        leaf ipv6-remote {
                            type yang:gauge32;
                            description "The current number of transit prefix IPv6 remote entries active on the ISA-AA MDA in the group.";
                        }

                    } // container transit-prefix-entries

                    container assigned-subscribers {
                        description "Enter the assigned-subscribers context";

                        leaf esm {
                            type yang:gauge32;
                            description "The current number of Enhanced Subscriber Management (ESM) subscribers assigned on the ISA-AA MDA in the group.";
                        }

                        leaf sap {
                            type yang:gauge32;
                            description "The current number of Service Access Point (SAP) subscribers assigned on the ISA-AA MDA in the group.";
                        }

                        leaf spoke-sdp {
                            type yang:gauge32;
                            description "The current number of Spoke SDP subscribers assigned on the ISA-AA MDA in the group.";
                        }

                        leaf transit {
                            type yang:gauge32;
                            description "The current number of transit subscribers assigned on the ISA-AA MDA in the group.";
                        }

                        leaf esm-mac {
                            type yang:gauge32;
                            description "The current number of Enhanced Subscriber Management (ESM) MAC host subscribers assigned on the ISA-AA MDA in the group.";
                        }

                    } // container assigned-subscribers

                } // container statistics

                container shared-resources {
                    description "Enter the shared-resources context";

                    leaf gtp-tunnel-database-size {
                        type uint64;
                        description "The number of entries in the shared resources GTP Tunnel Database.";
                    }

                    leaf gtp-tunnel-database-utilization {
                        type yang:gauge32 {
                            range "0..100";
                        }
                        units "percent";
                        description "The utilization level of the shared resources GTP Tunnel Database.";
                    }

                } // container shared-resources

            } // list esa

            list isa {
                key "mda-id";
                description "Enter the isa list instance";

                leaf mda-id {
                    type types-isa:slot-mda;
                    description "MDA/ISA ID";
                }

                leaf activity-state {
                    type types-aa:isa-activity-state;
                    description "The current activity status of the ISA (MDA or ESA-VM) in the group.";
                }

                container statistics {
                    description "Enter the statistics context";

                    leaf capacity-cost {
                        type yang:gauge32;
                        description "The current capacity cost assigned to the ISA-AA MDA in the group.";
                    }

                    leaf aa-subs {
                        type yang:gauge32;
                        description "The current number of Application Assurance subscriber resources in use on the ISA-AA MDA in the group.";
                    }

                    leaf aa-sub-stats {
                        type yang:gauge32;
                        description "The current number of Application Assurance subscriber statistics resources in use on the ISA-AA MDA in the group.";
                    }

                    leaf transit-ip-addresses {
                        type yang:gauge32;
                        description "The current number of Transit IP subscriber addresses associated with the ISA-AA MDA in the group.";
                    }

                    container transit-prefix-entries {
                        description "Enter the transit-prefix-entries context";

                        leaf ipv4 {
                            type yang:gauge32;
                            description "The current number of transit prefix IPv4 entries active on the ISA-AA MDA in the group.";
                        }

                        leaf ipv4-remote {
                            type yang:gauge32;
                            description "The current number of transit prefix IPv4 remote entries active on the ISA-AA MDA in the group.";
                        }

                        leaf ipv6 {
                            type yang:gauge32;
                            description "The current number of transit prefix IPv6 entries active on the ISA-AA MDA in the group.";
                        }

                        leaf ipv6-remote {
                            type yang:gauge32;
                            description "The current number of transit prefix IPv6 remote entries active on the ISA-AA MDA in the group.";
                        }

                    } // container transit-prefix-entries

                    container assigned-subscribers {
                        description "Enter the assigned-subscribers context";

                        leaf esm {
                            type yang:gauge32;
                            description "The current number of Enhanced Subscriber Management (ESM) subscribers assigned on the ISA-AA MDA in the group.";
                        }

                        leaf sap {
                            type yang:gauge32;
                            description "The current number of Service Access Point (SAP) subscribers assigned on the ISA-AA MDA in the group.";
                        }

                        leaf spoke-sdp {
                            type yang:gauge32;
                            description "The current number of Spoke SDP subscribers assigned on the ISA-AA MDA in the group.";
                        }

                        leaf transit {
                            type yang:gauge32;
                            description "The current number of transit subscribers assigned on the ISA-AA MDA in the group.";
                        }

                        leaf esm-mac {
                            type yang:gauge32;
                            description "The current number of Enhanced Subscriber Management (ESM) MAC host subscribers assigned on the ISA-AA MDA in the group.";
                        }

                    } // container assigned-subscribers

                } // container statistics

                container shared-resources {
                    description "Enter the shared-resources context";

                    leaf gtp-tunnel-database-size {
                        type uint64;
                        description "The number of entries in the shared resources GTP Tunnel Database.";
                    }

                    leaf gtp-tunnel-database-utilization {
                        type yang:gauge32 {
                            range "0..100";
                        }
                        units "percent";
                        description "The utilization level of the shared resources GTP Tunnel Database.";
                    }

                } // container shared-resources

            } // list isa

            container unassigned-subscribers {
                description "Enter the unassigned-subscribers context";

                container statistics {
                    description "Enter the statistics context";

                    leaf esm {
                        type yang:gauge32;
                        description
                            "The number of Enhanced Subscriber Management (ESM) subscribers
                             that have not been assigned to an ISA-AA MDA within a group.";
                    }

                    leaf sap {
                        type yang:gauge32;
                        description
                            "The number of Service Access Point (SAP) subscribers that
                             have not been assigned to an ISA-AA MDA within a group.";
                    }

                    leaf spoke-sdp {
                        type yang:gauge32;
                        description
                            "The number of Spoke SDP subscribers that have not been assigned
                             to an ISA-AA MDA within a group.";
                    }

                    leaf esm-mac {
                        type yang:gauge32;
                        description
                            "The number of Enhanced Subscriber Management (ESM) MAC host subscribers
                             that have not been assigned to an ISA-AA MDA within a group.";
                    }

                    leaf transit {
                        type yang:gauge32;
                        description
                            "The number of AA transit subscribers that have not been assigned to
                             an ISA-AA MDA within a group.";
                    }

                } // container statistics

                container transit {
                    description "Enter the transit context";

                    list sap {
                        key "sap-id";
                        description "Enter the sap list instance";

                        leaf sap-id {
                            type types-sros:sap;
                            description "Specifies an AA subscriber on a sap Id.";
                        }

                        container statistics {
                            description "Enter the statistics context";

                            leaf transits {
                                type yang:gauge32;
                                description
                                    "The number of transit subscribers under the parent subscriber tmnxBsxIsaLoadBalUnSub
                                     which have not been assigned to an ISA-AA MDA.";
                            }

                        } // container statistics

                    } // list sap

                    list spoke-sdp {
                        key "sdp-bind-id";
                        description "Enter the spoke-sdp list instance";

                        leaf sdp-bind-id {
                            type types-services:sdp-bind-id;
                            description "Specifies an AA subscriber on a spoke sdp Id.";
                        }

                        container statistics {
                            description "Enter the statistics context";

                            leaf transits {
                                type yang:gauge32;
                                description
                                    "The number of transit subscribers under the parent subscriber tmnxBsxIsaLoadBalUnSub
                                     which have not been assigned to an ISA-AA MDA.";
                            }

                        } // container statistics

                    } // list spoke-sdp

                } // container transit

            } // container unassigned-subscribers

        } // list application-assurance-group

    } // grouping state-isa-application-assurance-group

}
