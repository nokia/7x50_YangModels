module nokia-types-port {

    yang-version "1.1";

    namespace "urn:nokia.com:sros:ns:yang:sr:types-port";

    prefix "types-port";

    import nokia-sros-yang-extensions     { prefix "sros-ext"; }

    sros-ext:sros-major-release "rel21";

    organization "Nokia";

    contact
        "Nokia SR OS Support
         Web: <http://www.nokia.com>";

    description
        "Common port data types used in the SR OS management system.

         Copyright 2016 Nokia. All rights reserved. Reproduction of this document
         is authorized on the condition that the foregoing copyright notice is included.

         This nokia-types-port YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-02-16";

    typedef aps-switch-command {
        type enumeration {
            enum "no-command"                   { value 1; }
            enum "clear"                        { value 2; }
            enum "lockout-of-protection"        { value 3; }
            enum "forced-switch-work-to-protect" { value 4; }
            enum "forced-switch-protect-to-work" { value 5; }
            enum "manual-switch-work-to-protect" { value 6; }
            enum "manual-switch-protect-to-work" { value 7; }
            enum "exercise"                     { value 8; }
        }
        description "Specifies the switch command parameters.";
    }

    typedef channel-type {
        type enumeration {
            enum "sts768"                       { value 1; }
            enum "sts192"                       { value 2; }
            enum "sts48"                        { value 3; }
            enum "sts12"                        { value 4; }
            enum "sts3"                         { value 5; }
            enum "sts1"                         { value 6; }
            enum "tug3"                         { value 7; }
            enum "vtg"                          { value 8; }
            enum "vt15"                         { value 9; }
            enum "vt2"                          { value 10; }
            enum "vt3"                          { value 11; }
            enum "vt6"                          { value 12; }
            enum "tu3"                          { value 13; }
            enum "ds3"                          { value 14; }
            enum "e3"                           { value 15; }
            enum "ds1"                          { value 16; }
            enum "e1"                           { value 17; }
            enum "ds0-group"                    { value 18; }
        }
        description "Specifies the channel type.";
    }

    typedef sonet-group-payload-type {
        type enumeration {
            enum "vt15"                         { value 9; }
            enum "vt2"                          { value 10; }
            enum "tu3"                          { value 13; }
        }
        description "Specifies the SONET/SDH payload type for a group.";
    }

    typedef sonet-path-payload-type {
        type enumeration {
            enum "sts3"                         { value 5; }
            enum "tug3"                         { value 7; }
            enum "vt15"                         { value 9; }
            enum "vt2"                          { value 10; }
            enum "ds3"                          { value 14; }
            enum "e3"                           { value 15; }
            enum "ds1"                          { value 16; }
            enum "e1"                           { value 17; }
        }
        description "Specifies the SONET/SDH payload type for a path.";
    }

    typedef dwdm-wavetracker-report-alarms {
        type bits {
            bit encoder-failure                { position 0; }
            bit encoder-degrade                { position 1; }
            bit power-control-failure          { position 2; }
            bit power-control-degrade          { position 3; }
            bit power-control-high-limit       { position 4; }
            bit power-control-low-limit        { position 5; }
            bit missing-pluggable-voa          { position 6; }
        }
        description
            "Specifies a bitmask that describes the alarms that can be
             raised/cleared on an DWDM wavetracker port.";
    }

    typedef efm-oam-local-port-action {
        type enumeration {
            enum "log-only"                     { value 1; }
            enum "port-out-of-service"          { value 2; }
        }
        description
            "Specifies the action which the local port will take
             when receiving an event that has occurred at the Ethernet OAM level.
             These events include both locally and remotely detected events.";
    }

    typedef etype {
        type string;
        description "Specifies the encapsulation type on the port.";
    }

    typedef mode {
        type enumeration {
            enum "access"                       { value 1; }
            enum "network"                      { value 2; }
            enum "hybrid"                       { value 3; }
        }
        description
            "An enumerated integer that describes the values used to
             identify the mode in which a specific port is configured ";
    }

    typedef port-class {
        type enumeration {
            enum "unknown"                      { value 1; }
            enum "fast-e"                       { value 2; }
            enum "gig-e"                        { value 3; }
            enum "xgig-e"                       { value 4; }
            enum "sonet"                        { value 5; }
            enum "vport"                        { value 6; }
            enum "xcm-e"                        { value 8; }
            enum "tdm"                          { value 9; }
            enum "xlgig-e"                      { value 10; }
            enum "cgig-e"                       { value 11; }
            enum "vsm-e"                        { value 12; }
            enum "gnss"                         { value 13; }
            enum "vspeed-e"                     { value 14; }
            enum "serial"                       { value 17; }
            enum "wireless"                     { value 18; }
            enum "connector"                    { value 19; }
            enum "xxvgig-e"                     { value 20; }
            enum "cdgig-e"                      { value 21; }
            enum "lgig-e"                       { value 24; }
            enum "anchor"                       { value 26; }
        }
        description
            "The port-class data type is an enumerated integer that
             describes the values used to identify the class of interface
             provided by this port.";
    }

    typedef port-oper-state {
        type enumeration {
            enum "unknown"                      { value 1; }
            enum "up"                           { value 2; }
            enum "down"                         { value 3; }
            enum "diagnosing"                   { value 4; }
            enum "failed"                       { value 5; }
        }
        description "Indicates the operational state of the port.";
    }

    typedef family {
        type enumeration {
            enum "unknown"                      { value 1; }
            enum "vport"                        { value 2; }
            enum "ethernet"                     { value 3; }
            enum "sonet"                        { value 4; }
            enum "tdm"                          { value 5; }
            enum "serial"                       { value 6; }
            enum "gnss"                         { value 7; }
            enum "wireless"                     { value 8; }
            enum "connector"                    { value 9; }
            enum "anchor"                       { value 11; }
        }
        description
            "The family data type is an enumerated integer that
             describes the port family.";
    }

    typedef load-balancing-algorithm {
        type enumeration {
            enum "default"                      { value 1; }
            enum "include-l4"                   { value 2; }
            enum "exclude-l4"                   { value 3; }
        }
        description "Specifies the load balancing algorithm options.";
    }

    typedef type {
        type enumeration {
            enum "unknown"                      { value 1; }
            enum "10/100-ethernet-tx"           { value 2; }
            enum "100-mb-ethernet-fx"           { value 3; }
            enum "1-gig-ethernet-dual-fiber"    { value 6; }
            enum "oc-3-sonet/sdh"               { value 7; }
            enum "oc-12-sonet/sdh"              { value 8; }
            enum "oc-48-sonet/sdh"              { value 9; }
            enum "oc-192-sonet/sdh"             { value 10; }
            enum "10-gig-ethernet"              { value 11; }
            enum "oc-3/oc-12-sonet/sdh"         { value 12; }
            enum "virtual-port"                 { value 13; }
            enum "ds3/e3"                       { value 14; }
            enum "10/100/gig-ethernet-tx"       { value 15; }
            enum "1-gig-ethernet-sfp"           { value 16; }
            enum "10/100/gig-ethernet-sfp"      { value 17; }
            enum "ds1/e1"                       { value 19; }
            enum "ipsec"                        { value 20; }
            enum "application-assurance"        { value 21; }
            enum "video-mda"                    { value 22; }
            enum "mobile-gateway"               { value 23; }
            enum "broadband"                    { value 24; }
            enum "40-gig-ethernet"              { value 25; }
            enum "oc-768-sonet/sdh"             { value 26; }
            enum "100-gig-ethernet"             { value 27; }
            enum "cross-connect-ethernet"       { value 28; }
            enum "ip-reas-mda"                  { value 29; }
            enum "tms"                          { value 30; }
            enum "10/100/gig-ethernet-combo"    { value 34; }
            enum "40/100-gig-ethernet"          { value 35; }
            enum "rs-232-serial"                { value 36; }
            enum "cellular"                     { value 46; }
            enum "gnss"                         { value 47; }
            enum "1-gig/10-gig-ethernet"        { value 48; }
            enum "qsfp28-connector"             { value 49; }
            enum "25-gig-ethernet"              { value 50; }
            enum "wlan-vport"                   { value 51; }
            enum "vsr"                          { value 52; }
            enum "cdgig"                        { value 53; }
            enum "cfp8-connector"               { value 56; }
            enum "qsfp-dd-connector"            { value 57; }
            enum "cfp2-connector"               { value 58; }
            enum "10/25-gig-ethernet-sfp"       { value 59; }
            enum "sfp28-connector"              { value 60; }
            enum "sfp-dd-connector"             { value 63; }
            enum "sfp56-connector"              { value 64; }
            enum "50-gig-ethernet"              { value 65; }
            enum "100mb-1/10-gig-ethernet"      { value 66; }
            enum "anchor"                       { value 68; }
        }
        description
            "The type data type is an enumerated integer that describes
             the values used to identify the specific type of hardware port.";
    }

    typedef port-state {
        type enumeration {
            enum "none"                         { value 1; }
            enum "ghost"                        { value 2; }
            enum "link-down"                    { value 3; }
            enum "link-up"                      { value 4; }
            enum "up"                           { value 5; }
            enum "diagnose"                     { value 6; }
        }
        description
            "The state level of this port.  A value of 'none' indicates the
             port is either in its initial creation state or is just about to
             be deleted.  A value of 'ghost' represents a port that is not
             physically present.  This state may represent a pre-provisioned
             port.  A value of 'link-down' represents a port that is physically
             present but does not have a link.  The 'link-up' state represents a
             port that is physically present and has physical link present.
             A port in 'up' state is ready to pass some kinds of traffic. The 
             'diagnose' state represents the port undergoing diagnostic test.";
    }

    typedef duplex-mode {
        type enumeration {
            enum "full"                         { value 1; }
            enum "half"                         { value 2; }
        }
        description "Specifies the configurable duplex mode.";
    }

    typedef oper-duplex-mode {
        type enumeration {
            enum "not-applicable"               { value 0; }
            enum "full"                         { value 1; }
            enum "half"                         { value 2; }
        }
        description "Specifies the operational duplex mode.";
    }

    typedef ethernet-encap-type {
        type enumeration {
            enum "null"                         { value 1; }
            enum "dot1q"                        { value 2; }
            enum "qinq"                         { value 10; }
        }
        description
            "The type of encapsulation protocol configured on an
             ethernet port.

             When the encap type has a value of 'null', 
             frames received will not carry any tags
             or labels and as a result only one service can be
             configured on this port.  Sometimes this is referred to
             as raw Ethernet packets.

             When the encap type has a value of 'dot1q', ingress frames
             carry 802.1q tags where each different tag can signify a
             different service.

             When the encap type has a value of 'qinq', ingress frames
             can carry two 802.1q tags on a single frame.";
    }

    typedef ethernet-monitor-report-status {
        type bits {
            bit sd-threshold-exceeded          { position 0; }
            bit sf-threshold-exceeded          { position 1; }
        }
        description
            "Specifies a bitmask that describes alarms that can be raised/cleared
             on an Ethernet port used in Monitoring.";
    }

    typedef ethernet-oper-tx-clock {
        type enumeration {
            enum "not-applicable"               { value 0; }
            enum "master"                       { value 1; }
            enum "slave"                        { value 2; }
        }
        description
            "Indicates the result of the master/slave resolution on copper
             based Ethernet ports.";
    }

    typedef ethernet-report-alarms {
        type bits {
            bit signal-fail                    { position 1; }
            bit remote                         { position 2; }
            bit local                          { position 3; }
            bit frame-not-locked               { position 4; }
            bit high-ber                       { position 5; }
            bit block-not-locked               { position 6; }
            bit alignment-marker-not-locked    { position 7; }
            bit duplicate-lane                 { position 8; }
        }
        description
            "Specifies a bitmask that describes the alarms that can be
             raised/cleared on an Ethernet port.";
    }

    typedef coherent-optical-alarm {
        type bits {
            bit modflt                         { position 0; }
            bit mod                            { position 1; }
            bit netrx                          { position 2; }
            bit nettx                          { position 3; }
            bit hosttx                         { position 4; }
        }
        description
            "Specifies the type of coherent optical alarm currently active on the
             port.";
    }

    typedef coherent-optical-defect-point {
        type bits {
            bit over-temp                      { position 0; }
            bit hw-post                        { position 1; }
            bit pld-flash-init                 { position 2; }
            bit power-supply                   { position 3; }
            bit check-sum                      { position 4; }
            bit ref-clock-in                   { position 5; }
            bit tx-jit-pll-lol                 { position 6; }
            bit tx-cmu-lol                     { position 7; }
            bit tx-loss-func                   { position 8; }
            bit host-tx-lol                    { position 9; }
            bit net-rx-lol                     { position 10; }
            bit host-tx-skew-high              { position 11; }
            bit net-tx-tec                     { position 12; }
            bit net-tx-wave-unlk               { position 13; }
            bit net-tx-losf                    { position 14; }
            bit net-rx-los                     { position 15; }
            bit net-rx-fifo-err                { position 16; }
            bit net-rx-tec                     { position 17; }
            bit net-tx-out-of-align            { position 18; }
            bit net-tx-cmu-lock                { position 19; }
            bit net-tx-ref-clk                 { position 20; }
            bit net-rx-modem-sync-det          { position 21; }
            bit net-rx-modem-lock              { position 22; }
            bit host-tx-lane-fifo-err          { position 23; }
            bit host-tx-deskew                 { position 24; }
            bit host-rx-corr                   { position 25; }
            bit host-rx-uncorr                 { position 26; }
            bit comm-fail                      { position 27; }
        }
        description
            "Specifies the type of coherent optical defects currently
             active on the port.

                 over-temp             - Module over safe operating temperature.
                 hw-post               - Hardware fault detected during power-on
                                         self-test.
                 pld-flash-init        - PLD (Programmable Logic Device), CPLD
                                         (Complex Programmable Logic Device), or FPGA
                                         (Field Programmable Gate Array)
                                         initialization fault.
                 power-supply          - Power supply is out of range.
                 chk-sum               - CFP (C Form factor Pluggable) table checksum
                                         fault.
                 ref-clk-in            - Loss of reference clock.
                 tx-jit-pll-lol        - TX jitter PLL (Phase-Locked Loop) loss of
                                         lock.
                 tx-cmu-lol            - TX CMU (Clock Multiplier Unit) loss of lock.
                 tx-loss-func          - TX loss of signal functionality.
                 host-tx-lol           - TX IC (Integrated Circuit) lock indicator.
                 net-rx-lol            - RX IC lock indicator.
                 host-tx-skew-high     - Host lane skew out of alignment.
                 net-tx-tec            - Lane TX thermo-electric cooler fault.
                 net-tx-wave-unlk      - Lane wavelength unlocked.
                 net-tx-losf           - Lane TX loss of signal functionality
                 net-rx-los            - Lane RX loss of signal.
                 net-rx-fifo-err       - Lane RX FIFO error.
                 net-rx-tec            - Lane RX thermo-electric cooler fault.
                 net-tx-out-of-align   - Out of alignment.
                 net-tx-cmu-lock       - CMU lock fault.
                 net-tx-ref-clk        - Reference clock fault.
                 net-rx-modem-sync-det - Modem sync detect fault.
                 net-rx-modem-lock     - Modem lock fault.
                 host-tx-lane-fifo-err - Lane TX FIFO error.
                 host-tx-deskew        - Deskew lock fault.
                 host-rx-corr          - Host Rx FEC corrected bits detected.
                 host-rx-uncorr        - Host Rx FEC uncorrectable error detected.
                 comm-fail             - Communication failure.";
    }

    typedef connector-type {
        type enumeration {
            enum "unassigned"                   { value 1; }
            enum "rj-45"                        { value 2; }
            enum "bnc-coax"                     { value 3; }
            enum "mini-mt-rj"                   { value 4; }
            enum "sc-duplex"                    { value 5; }
            enum "sfp"                          { value 6; }
            enum "lc-duplex"                    { value 7; }
            enum "xfp"                          { value 8; }
            enum "sc-simplex"                   { value 9; }
            enum "rj-48c"                       { value 10; }
            enum "cfp"                          { value 11; }
            enum "qsfp"                         { value 12; }
            enum "mrj-21"                       { value 13; }
            enum "cxp"                          { value 14; }
            enum "cfp2"                         { value 15; }
            enum "cfp4"                         { value 16; }
            enum "rj-45/sfp"                    { value 17; }
            enum "sma"                          { value 18; }
            enum "vsr"                          { value 20; }
            enum "cfp8"                         { value 21; }
            enum "qsfp-dd"                      { value 22; }
            enum "sfp-dd"                       { value 24; }
        }
        description "Specifies the connector type used for ports";
    }

    typedef los-reaction {
        type enumeration {
            enum "none"                         { value 0; }
            enum "squelch"                      { value 1; }
        }
        description
            "Specifies the type of action that is taken in the event of a Loss Of
             Signal (LOS). The valid modes are as follows:

                    - none     - Specifies that the port not be taken down on
                                 crossing the optical LOS threshold.
                    - squelch  - Specifies that the port be taken down on
                                 crossing the optical LOS threshold.";
    }

    typedef optical-compatibility-mode {
        type enumeration {
            enum "long-haul"                    { value 0; }
            enum "metro"                        { value 1; }
            enum "access"                       { value 2; }
            enum "interop"                      { value 3; }
            enum "interop2"                     { value 4; }
            enum "interop3"                     { value 5; }
            enum "long-haul-non-differential"   { value 6; }
        }
        description
            "Specifies the optical mode and rate of operation of the
             Coherent port.";
    }

    typedef optical-compliance-extention-type {
        type uint32;
        description
            "Specifies an enumerated integer which extends
             port/transceiver/optical-compliance for a small form factor (SFF) that
             is inserted into the port.";
    }

    typedef optical-dispersion-control-mode {
        type enumeration {
            enum "automatic"                    { value 0; }
            enum "manual"                       { value 1; }
        }
        description
            "Specifies the operational control mode of the dispersion compensation
             module. The valid modes are as follows:
                    - automatic     - The software control loop automatically
                                      determines the dispersion using a FEC
                                      feedback algorithm to find the best
                                      operational dispersion compensation point
                    - manual        - The software control loop is disabled and
                                      the user manually configures the dispersion
                                      compensation.";
    }

    typedef optical-dwdm-channel {
        type uint32 {
            range "17..61|170..610";
        }
        description
            "Specifies the DWDM ITU channel associated with an optical interface.
             It is expressed in a form that is derived from the laser's operational
             frequency. For example 193.40 THz corresponds to DWDM ITU channel 34
             in the 100 GHz grid and 193.45 THz corresponds to DWDM ITU channel 345
             in the 50 GHz grid.

                 Range    ITU Grid
                 -------- ----------------------
                 17-61    100 GHz Grid
                 170-610  50 GHz Grid

             For configurable attributes, the value 0 represents no channel. For
             read-only attributes, the value 0 represents no channel transmitted or
             the interface is not equipped with a laser.";
    }

    typedef optical-dwdm-extended-channel {
        type uint32 {
            range "0|11..62|115..615";
        }
        description
            "Specifies the extended DWDM ITU channel associated with an optical
             interface. It is expressed in a form that is derived from the laser's
             operational frequency. For example 193.40 THz corresponds to DWDM ITU
             channel 34 in the 100 GHz grid and 193.45 THz corresponds to DWDM ITU
             channel 345 in the 50 GHz grid.

                 Range    ITU Grid
                 -------- ----------------------
                 11-62    100 GHz Grid
                 115-615  50 GHz Grid

             For configurable attributes, the value 0 represents no channel. For
             read-only attributes, the value 0 represents no channel transmitted or
             the interface is not equipped with a laser.";
    }

    typedef optical-dwdm-frequency {
        type uint32 {
            range "191100000..196150000";
        }
        units "megahertz";
        description
            "Specifies the frequency of a tuneable DWDM optical interface.

             Note that tunable DWDM optical interfaces operate at specific
             frequencies on grids. Traditionally, these have used the 100 GHz
             or 50 GHz grid but newer interfaces can support other grids such as
             75 GHz, 33 GHz, 25 GHz, 12.5 GHz, 6.25 GHz and 3.125 GHz.   

             In addition, some interfaces allow for fine tuning of the frequency
             to values off grid.";
    }

    typedef otu-fec-mode {
        type enumeration {
            enum "none"                         { value 0; }
            enum "g709"                         { value 1; }
            enum "enhanced"                     { value 2; }
        }
        description "Specifies the FEC mode used on the port.";
    }

    typedef otu2-lan-data-rate {
        type enumeration {
            enum "11.049"                       { value 1; }
            enum "11.096"                       { value 2; }
        }
        description
            "Specifies the allowable data rates for a given OTU2 10GE-LAN
             enabled interface.";
    }

    typedef otu-psi-payload-type {
        type enumeration {
            enum "auto"                         { value 0; }
            enum "experimental"                 { value 1; }
            enum "asynchronous-cbr"             { value 2; }
            enum "bit-synchronous-cbr"          { value 3; }
            enum "atm"                          { value 4; }
            enum "gfp"                          { value 5; }
            enum "vcat"                         { value 6; }
            enum "gmp"                          { value 7; }
            enum "bit-stream-octet"             { value 16; }
            enum "bit-stream-non-octet"         { value 17; }
            enum "odu-mux"                      { value 32; }
            enum "reserved-80"                  { value 128; }
            enum "reserved-81"                  { value 129; }
            enum "reserved-82"                  { value 130; }
            enum "reserved-83"                  { value 131; }
            enum "reserved-84"                  { value 132; }
            enum "reserved-85"                  { value 133; }
            enum "reserved-86"                  { value 134; }
            enum "reserved-87"                  { value 135; }
            enum "reserved-88"                  { value 136; }
            enum "reserved-89"                  { value 137; }
            enum "reserved-8a"                  { value 138; }
            enum "reserved-8b"                  { value 139; }
            enum "reserved-8c"                  { value 140; }
            enum "reserved-8d"                  { value 141; }
            enum "reserved-8e"                  { value 142; }
            enum "reserved-8f"                  { value 143; }
            enum "null-test"                    { value 253; }
            enum "prbs-test"                    { value 254; }
        }
        description
            "Specifies the payload type identifier as defined in table
             15-8 of section 15.9.2.1.1 of ITU-T Rec. G.709.";
    }

    typedef otu-tim-reaction {
        type enumeration {
            enum "squelch-rx"                   { value 1; }
        }
        description
            "Specifies the type of reaction that should be taken in the event
             of Trace Identifier (TTI) Mismatch or Payload Type Mismatch. The
             valid modes are as follows:

                - none           - Specifies that the Received Payload data
                                   should be passed through when a Trace
                                   Identifier Mismatch is detected.
                - squelch-rx     - Specifies that the Received Payload data
                                   should be blocked with a maintenance signal
                                   when a Trace Identifier Mismatch is
                                   detected.";
    }

    typedef otu-sf-sd-method {
        type enumeration {
            enum "fec"                          { value 1; }
            enum "bip8"                         { value 2; }
        }
        description "Specifies the method to determine the SF and SD of the interface.";
    }

    typedef otu-report-alarms {
        type bits {
            bit loc                            { position 0; }
            bit los                            { position 1; }
            bit lof                            { position 2; }
            bit lom                            { position 3; }
            bit otu-ais                        { position 4; }
            bit otu-ber-sf                     { position 5; }
            bit otu-ber-sd                     { position 6; }
            bit otu-bdi                        { position 7; }
            bit otu-tim                        { position 8; }
            bit otu-iae                        { position 9; }
            bit otu-biae                       { position 10; }
            bit fec-sf                         { position 11; }
            bit fec-sd                         { position 12; }
            bit fec-fail                       { position 13; }
            bit fec-uncorr                     { position 14; }
            bit odu-ais                        { position 15; }
            bit odu-oci                        { position 16; }
            bit odu-lck                        { position 17; }
            bit odu-bdi                        { position 18; }
            bit odu-tim                        { position 19; }
            bit opu-plm                        { position 21; }
        }
        description
            "Specifies a bitmask that describes the alarms that can be
             raised/cleared on an OTU port.";
    }

    typedef pae-controlled-port-status {
        type enumeration {
            enum "authorized"                   { value 1; }
            enum "unauthorized"                 { value 2; }
        }
        description
            "Specifies the status values of the Authenticator PAE
             controlled Port.";
    }

    typedef pae-controlled-port-control {
        type enumeration {
            enum "force-unauthorized"           { value 1; }
            enum "auto"                         { value 2; }
            enum "force-authorized"             { value 3; }
        }
        description
            "Specifies the control values of the Authenticator PAE
             controlled Port.";
    }

    typedef sff-status {
        type enumeration {
            enum "not-equipped"                 { value 0; }
            enum "operational"                  { value 1; }
            enum "read-error"                   { value 2; }
            enum "data-corrupt"                 { value 3; }
            enum "ddm-corrupt"                  { value 4; }
            enum "unsupported"                  { value 5; }
            enum "culprit"                      { value 6; }
            enum "blocked"                      { value 7; }
        }
        description
            "Specifies the operational status of the small form
             factor (SFF) that is inserted into the port. If the SFF is removed
             from the port, the value will be 'not-equipped', otherwise
             'operational' if no failure is detected.

             A failure to read the SFF data will result in a 'read-error',
             while corrupted information on the SFF will result in either
             'data-corrupt', or 'ddm-corrupt' if an SFF read results in
             invalid data or DDM information respectively.  An insertion of an
             unsupported SFF will result in 'unsupported'. An insertion of
             an SFF device that is preventing other devices from being read will
             result in the state 'culprit' for the offending device, and
             'blocked' for the other devices.

             A trap will be raised if the value of indicates a failure; that is
             the value is neither 'not-equipped', nor 'operational'.";
    }

    typedef sonet-path-encap-type {
        type enumeration {
            enum "bcp-null"                     { value 4; }
            enum "bcp-dot1q"                    { value 5; }
            enum "ipcp"                         { value 6; }
            enum "ppp-auto"                     { value 8; }
            enum "wan-mirror"                   { value 11; }
            enum "cem"                          { value 13; }
        }
        description
            "The type of encapsulation protocol configured on an
             SONET/SDH path.

             When the encap type has a value of 'bcp-null', BCP is used on the SONET
             path as the Network Control Protocol (NCP). The BCP IEEE 802 Tagged Frame
             Configuration Option (type 8) is negotiated to 'enabled'. VLAN tagged
             frames are allowed into the SONET path. Only a single SAP can be
             associated with the SONET path.

             When the encap type has a value of 'bcp-dot1q', BCP is used as the
             Network Control Protocol (NCP). The BCP IEEE 802 tagged Frame Configuration
             Option (type 8) is negotiated to 'enabled'. VLAN tagged frames are allowed
             on the SONET path. This encapsulation type is required when multiple SAPs are
             defined on the SONET path where each one is service delimited by a
             provisioned Dot1q tag. When 'bcp-dot1q' is specified, BCP does not enter the
             'open' state unless the far end peer also supports 'bcp-dot1q'. This allows
             an LCP negotiation to transmit configuration request and confirmation
             messages to enable this feature.

             When the encap type has a value of 'ipcp', BCP will not be used on this SONET
             path. Internet Protocol Control Protocol (IPCP) is used instead.

             When the encap type has a value of 'frame-relay', Frame Relay is the expected
             encapsulation.

             When the encap type has a value of 'ppp-auto', IPCP is automatically enabled.
             This encap type is only valid on ports/paths in network mode.

             When the encap type has a value of 'atm', the encapsulation on the port is
             ATM. The 'atm' encap type is also used when mirroring ATM ports.

             When the encap type has a value of 'wan-mirror', the port is used for
             mirroring of frame-relay and POS ports. On such ports no link management
             protocol would run.

             When the encap type has a value of 'cisco-hdlc', the Cisco HDLC encapsulation
             is applied.";
    }

    typedef network-interface-encap-type {
        type enumeration {
            enum "unknown"                      { value 0; }
            enum "null"                         { value 1; }
            enum "dot1q"                        { value 2; }
            enum "mpls"                         { value 3; }
            enum "bcp-null"                     { value 4; }
            enum "bcp-dot1q"                    { value 5; }
            enum "ipcp"                         { value 6; }
            enum "ppp-auto"                     { value 8; }
            enum "qinq"                         { value 10; }
            enum "wan-mirror"                   { value 11; }
            enum "cem"                          { value 13; }
            enum "reserved14"                   { value 14; }
            enum "raw"                          { value 15; }
            enum "cellular"                     { value 16; }
            enum "wlan"                         { value 17; }
        }
        description
            "The type of encapsulation protocol configured on a
             port's network interface.

             When the encap type has a value of 'null',
             frames received will not carry any tags
             or labels and as a result only one service can be
             configured on this port.  Sometimes this is referred to
             as raw Ethernet packets.

             When the encap type has a value of 'dot1q', ingress frames
             carry 802.1q tags where each different tag can signify a
             different service.

              When the encap type has a value of 'bcp-null', BCP is used on the SONET
              path as the Network Control Protocol (NCP). The BCP IEEE 802 Tagged Frame
              Configuration Option (type 8) is negotiated to 'enabled'. VLAN tagged
              frames are allowed into the SONET path. Only a single SAP can be
              associated with the SONET path.

              When the encap type has a value of 'bcp-dot1q', BCP is used as the
              Network Control Protocol (NCP). The BCP IEEE 802 tagged Frame Configuration
              Option (type 8) is negotiated to 'enabled'. VLAN tagged frames are allowed
              on the SONET path. This encapsulation type is required when multiple SAPs are
              defined on the SONET path where each one is service delimited by a
              provisioned Dot1q tag. When 'bcp-dot1q' is specified, BCP does not enter the
              'open' state unless the far end peer also supports 'bcp-dot1q'. This allows
              an LCP negotiation to transmit configuration request and confirmation
              messages to enable this feature.

              When the encap type has a value of 'ipcp', BCP will not be used on this SONET
              path. Internet Protocol Control Protocol (IPCP) is used instead.

              When the encap type has a value of 'frame-relay', Frame Relay is the expected
              encapsulation.

              When the encap type has a value of 'ppp-auto', IPCP is automatically enabled.
              This encap type is only valid on ports/paths in network mode.

              When the encap type has a value of 'atm', the encapsulation on the port is
              ATM. The 'atm' encap type is also used when mirroring ATM ports.

              When the encap type has a value of 'wan-mirror', the port is used for
              mirroring of frame-relay and POS ports. On such ports no link management
              protocol would run.

              When the encap type has a value of 'cisco-hdlc', the Cisco HDLC encapsulation
              is applied.

             When the encap type has a value of 'cem', encapsulation of
             frames will be circuit emulation.  This is used to support transparent
             transmission of frames.  This encap type is only valid
             on 'tdm' or 'sonet' ports in access mode.

             When the encap type has a value of 'raw', data does not
             necessarily carry any tags, headers or any other form of delimiter.
             This encap type is only valid on access ports supporting serial data.

             When the encap type has a value of 'cellular', packets on the
             port use cellular encapsulation.  This encapsulation is only valid
             on cellular ports.";
    }

    typedef sdh-group-index {
        type string;
        description "A SDH group index.";
    }

    typedef sonet-path-index {
        type string;
        description "A SONET/SDH path index.";
    }

    typedef sonet-report-alarms {
        type bits {
            bit loc                            { position 1; }
            bit lais                           { position 2; }
            bit lrdi                           { position 3; }
            bit ss1f                           { position 4; }
            bit sb1err                         { position 5; }
            bit lb2er-sd                       { position 6; }
            bit lb2er-sf                       { position 7; }
            bit slof                           { position 8; }
            bit slos                           { position 9; }
            bit stxptr                         { position 10; }
            bit srxptr                         { position 11; }
            bit lrei                           { position 12; }
        }
        description
            "Specifies a bitmask that describes the SONET alarms.

                loc         Indicates a loss of clock which causes the operational
                            state of the port to be downed.
                lais        Indicates line alarm indication signal errors.
                lrdi        Indicates line remote defect indication errors.  LRDIs
                            are caused by remote LOF, LOC, and LOS.
                ss1f        Indicates section synchronization failure as reported by
                            the S1 byte.
                sb1err      Indicates section B1 errors.
                lb2er-sd    Indicates line signal degradation BER errors.
                lb2er-sf     Indicates line signal failure BER errors.
                slof        Indicates section loss of frame errors.
                slos        Indicates section loss of signal errors.
                stxptr      Indicates a section synchronization error on the
                            transmit side. Indicates if there is a positive or
                            negative justification count per channel.
                srxptr      Indicates a section synchronization error on the receive
                            side.  Indicates if there is a positive or negative
                            justification count per sonet path.
                lrei        Indicates a line error condition raised by the remote
                            as a result of B1 errors received from this node.";
    }

    typedef tdm-ds1-index {
        type string;
        description "A TDM DS1 index.";
    }

    typedef tdm-ds3-index {
        type string;
        description "A TDM DS3 index.";
    }

    typedef tdm-e3-index {
        type string;
        description "A TDM E3 index.";
    }

    typedef tdm-e1-index {
        type string;
        description "A TDM E1 index.";
    }

    typedef tdm-dsx-bert-oper-status {
        type enumeration {
            enum "none"                         { value 0; }
            enum "active"                       { value 1; }
            enum "idle"                         { value 2; }
            enum "no-mda-resources"             { value 3; }
        }
        description "Indicates the status of Bit Error Rate Test (BERT).";
    }

    typedef tdm-dsx-bert-pattern {
        type enumeration {
            enum "ones"                         { value 1; }
            enum "zeros"                        { value 2; }
            enum "alternating"                  { value 3; }
            enum "2e3"                          { value 4; }
            enum "2e9"                          { value 5; }
            enum "2e15"                         { value 6; }
            enum "2e20"                         { value 7; }
            enum "2e11"                         { value 8; }
            enum "2e20q"                        { value 9; }
            enum "2e23"                         { value 10; }
        }
        description "Indicates the pattern used for the Bit Error Rate Test (BERT).";
    }

    typedef tdm-dsx-clock-sync-state {
        type enumeration {
            enum "unknown"                      { value 0; }
            enum "normal"                       { value 1; }
            enum "hold-over"                    { value 2; }
            enum "free-run"                     { value 3; }
        }
        description
            "Indicates the clock synchronization state on a DS3 or DS1 channel.

             Values:
               unknown   - Unsupported or unknown state
               normal    - Normal (locked) state
               hold-over - Synchronization with reference has been lost
               free-run  - Synchronized with internal reference";
    }

    typedef tdm-report-alarm {
        type bits {
            bit ais                            { position 1; }
            bit los                            { position 2; }
            bit oof                            { position 3; }
            bit rai                            { position 4; }
            bit looped                         { position 5; }
            bit ber-sd                         { position 6; }
            bit ber-sf                         { position 7; }
        }
        description
            "Specifies a bitmask of TDM alarms.

                 ais    - alarm indication signal errors
                 los    - loss of signal errors
                 oof    - out-of-frame errors
                 rai    - resource availability indicator events
                 looped - far end wants the read end to loopback
                 ber-sd - DSX bit error signal degradation
                 ber-sf - DSX bit error signal failure";
    }

    typedef tdm-dsx-idle-cycle-flag {
        type enumeration {
            enum "flags"                        { value 1; }
            enum "ones"                         { value 2; }
        }
        description
            "Indicates the value that the DS3/DS1 port/channel or a DS0 channel
             group transmits during idle cycle.";
    }

    typedef transceiver-ddm-failure-bits {
        type bits {
            bit unknown                        { position 0; }
            bit temperature-low-warning        { position 1; }
            bit temperature-low-alarm          { position 2; }
            bit temperature-high-warning       { position 3; }
            bit temperature-high-alarm         { position 4; }
            bit supply-voltage-low-warning     { position 5; }
            bit supply-voltage-low-alarm       { position 6; }
            bit supply-voltage-high-warning    { position 7; }
            bit supply-voltage-high-alarm      { position 8; }
            bit tx-bias-current-low-warning    { position 9; }
            bit tx-bias-current-low-alarm      { position 10; }
            bit tx-bias-current-high-warning   { position 11; }
            bit tx-bias-current-high-alarm     { position 12; }
            bit tx-output-power-low-warning    { position 13; }
            bit tx-output-power-low-alarm      { position 14; }
            bit tx-output-power-high-warning   { position 15; }
            bit tx-output-power-high-alarm     { position 16; }
            bit rx-optical-power-low-warning   { position 17; }
            bit rx-optical-power-low-alarm     { position 18; }
            bit rx-optical-power-high-warning  { position 19; }
            bit rx-optical-power-high-alarm    { position 20; }
            bit aux1-low-warning               { position 21; }
            bit aux1-low-alarm                 { position 22; }
            bit aux1-high-warning              { position 23; }
            bit aux1-high-alarm                { position 24; }
            bit aux2-low-warning               { position 25; }
            bit aux2-low-alarm                 { position 26; }
            bit aux2-high-warning              { position 27; }
            bit aux2-high-alarm                { position 28; }
        }
        description
            "Specifies the state of the Digital Diagnostic Monitoring (DDM) transceiver thresholds.
             For each monitored attribute a low-warning, low-alarm, high-warning, and high-alarm are
             recorded.

             A set bit indicates the object is in a failed state, a cleared bit
             indicates the object has not exceeded the threshold.";
    }

    typedef transceiver-auxiliary-type {
        type enumeration {
            enum "none"                         { value 0; }
            enum "adp-bias-voltage"             { value 1; }
            enum "reserved-2"                   { value 2; }
            enum "tec-current"                  { value 3; }
            enum "laser-temp"                   { value 4; }
            enum "laser-wavelength"             { value 5; }
            enum "voltage-50"                   { value 6; }
            enum "voltage-33"                   { value 7; }
            enum "voltage-18"                   { value 8; }
            enum "voltage-52"                   { value 9; }
            enum "current-50"                   { value 10; }
            enum "reserved-11"                  { value 11; }
            enum "reserved-12"                  { value 12; }
            enum "current-33"                   { value 13; }
            enum "current-18"                   { value 14; }
            enum "current-52"                   { value 15; }
        }
        description
            "Indicates the measurement type of the manufacturer specific auxiliary
             information of the transceiver.

             Values:
                 none             (0)  - not specified.
                 adp-bias-voltage (1)  - LSB is 10mV.
                 reserved-2       (2)  - reserved for future use.
                 tec-current      (3)  - LSB is 100uA.
                 laser-temp       (4)  - degrees Celsius(C).
                 laser-wavelength (5)  - LSB is 0.05 nm.
                 voltage-50       (6)  - 5.0 supply voltage, LSB=100uV.
                 voltage-33       (7)  - 3.3 supply voltage, LSB=100uV.
                 voltage-18       (8)  - 1.8 supply voltage, LSB=100uV,
                 voltage-52       (9)  - -5.2 supply voltage, LSB=100uV.
                 current-50      (10)  - 5.0V supply current, LSB=100uA.
                 reserved-11     (11)  - reserved for future use.
                 reserved-12     (12)  - reserved for future use.
                 current-33      (13)  - 3.3V supply current, LSB=100uA.
                 current-18      (14)  - 1.8V supply current, LSB=100uA.
                 current-52      (15)  - -5.2V supply current, LSB=100uA.";
    }

    typedef if-index {
        type int32 {
            range "1..2147483647";
        }
        description
            "A a unique, non-zero number to identify an interface or
             subinterface within a system.  This corresponds to
             InterfaceIndex type of the SNMP IF-MIB of RFC 2863 and
             is intended for use in the YANG models for any leaf that
             correspond to an ifIndex MIB object for interfaces.";
    }

    typedef gnss-antenna-status {
        type enumeration {
            enum "unknown"                      { value 0; }
            enum "unsupported"                  { value 1; }
            enum "ok"                           { value 2; }
            enum "over-current"                 { value 3; }
            enum "under-current"                { value 4; }
            enum "no-bias-voltage"              { value 5; }
        }
        description "The status of the GNSS receiver module's antenna.";
    }

    typedef gnss-sync-status {
        type enumeration {
            enum "unknown"                      { value 0; }
            enum "locked"                       { value 1; }
            enum "not-locked"                   { value 2; }
        }
        description
            "The status of the GNSS receiver module with respect to generating
             a sync-worthy clock signal.";
    }

}
