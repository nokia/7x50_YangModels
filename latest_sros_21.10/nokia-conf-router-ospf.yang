submodule nokia-conf-router-ospf {

    yang-version "1.1";

    belongs-to nokia-conf { prefix "conf"; }

    import nokia-sros-yang-extensions     { prefix "sros-ext"; }
    import nokia-types-igp                { prefix "types-igp"; }
    import nokia-types-ospf               { prefix "types-ospf"; }
    import nokia-types-router             { prefix "types-router"; }
    import nokia-types-sros               { prefix "types-sros"; }

    include nokia-conf-groups;
    include nokia-conf-policy-options;
    include nokia-conf-router;
    include nokia-conf-router-bier;
    include nokia-conf-routing-options;
    include nokia-conf-system;
    include nokia-conf-system-security;


    sros-ext:sros-major-release "rel21";

    organization "Nokia";

    contact
        "Nokia SR OS Support
         Web: <http://www.nokia.com>";

    description
        "Nokia YANG Data model to configure router ospf protocol attributes on SR OS based routers.

         Copyright 2016 Nokia. All rights reserved. Reproduction of this document
         is authorized on the condition that the foregoing copyright notice is included.

         This nokia-conf-router-ospf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-29";

    grouping conf-router-ospf {
        list ospf {
            key "ospf-instance";
            max-elements 32;
            description "Enter the ospf list instance";

            leaf ospf-instance {
                type uint32 {
                    range "0..31";
                }
                description "Value for the integrated OSPF instance";
            }

            leaf admin-state {
                type types-sros:admin-state;
                default "disable";
                description "Administrative state of the OSPF instance";
            }

            leaf router-id {
                type types-igp:router-id;
                sros-ext:auto-restart-to-modify;
                description "Unique router ID for the OSPF instance";
            }

            leaf advertise-router-capability {
                type types-ospf:advertise-router-capability-type;
                default "false";
                description "Allow router advertisement capabilities";
            }

            leaf advertise-tunnel-link {
                type boolean;
                default "false";
                description "Allow router advertisement capabilities";
            }

            leaf external-preference {
                type int32 {
                    range "1..255";
                }
                default "150";
                description "Preference for OSPF external routes";
            }

            leaf-list export-policy {
                type leafref {
                    path "../../../policy-options/policy-statement/name";
                }
                max-elements 5;
                ordered-by user;
                description "Export policies that determine exported routes";
            }

            leaf-list import-policy {
                type leafref {
                    path "../../../policy-options/policy-statement/name";
                }
                max-elements 5;
                ordered-by user;
                description "Import policy names for routes from IGP to route table";
            }

            leaf ldp-over-rsvp {
                type boolean;
                default "false";
                description "Allow LSP over RSVP in this OSPF instance";
            }

            leaf ldp-sync {
                type boolean;
                default "true";
                description "Configure IGP-LDP synchronization for interfaces";
            }

            leaf multicast-import {
                type boolean;
                default "false";
                description "Submit routes into the multicast Route Table Manager";
            }

            leaf overload-include-ext-1 {
                type boolean;
                default "false";
                description "Advertise routes with maximum metric value for overload";
            }

            leaf overload-include-ext-2 {
                type boolean;
                default "false";
                description "Advertise routes with maximum metric value for overload";
            }

            leaf overload-include-stub {
                type boolean;
                default "false";
                description "Advertise all stub interfaces with max metric value";
            }

            leaf overload {
                type boolean;
                default "false";
                description "Change local router state to appear overloaded";
            }

            leaf preference {
                type int32 {
                    range "1..255";
                }
                default "10";
                description "Preference for OSPF internal routes";
            }

            leaf reference-bandwidth {
                type types-sros:reference-bandwidth-ext;
                units "kilobps";
                default "100000000";
                description "Bandwidth to reference default costing of interfaces";
            }

            leaf traffic-engineering {
                type boolean;
                default "false";
                description "Calculate traffic engineering route";
            }

            leaf unicast-import {
                type boolean;
                default "true";
                description "Submit routes into the unicast Route Table Manager";
            }

            leaf compatible-rfc1583 {
                type boolean;
                default "true";
                description "OSPF summary and external route calculations";
            }

            leaf multi-instance {
                type boolean;
                default "false";
                description "Enable OSPF Multi Instance Extensions";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container external-db-overflow {
                presence "Enable the external-db-overflow context";
                description "Enable the external-db-overflow context";

                leaf limit {
                    type uint32 {
                        range "0..2147483647";
                    }
                    default "0";
                    description "Number of external LSA at which overload is triggered";
                }

                leaf interval {
                    type uint32 {
                        range "0..2147483647";
                    }
                    units "seconds";
                    default "0";
                    description "Time during which the router operates in overload";
                }

            } // container external-db-overflow

            container export-limit {
                presence "Enable the export-limit context";
                description "Enable the export-limit context";

                leaf number {
                    type uint32 {
                        range "1..max";
                    }
                    mandatory true;
                    description "Maximum routes or prefixes exported from route table";
                }

                leaf log-percent {
                    type uint32 {
                        range "1..100";
                    }
                    description "Export limit before warning and SNMP notification sent";
                }

            } // container export-limit

            container overload-on-boot {
                presence "Enable the overload-on-boot context";
                description "Enable the overload-on-boot context";

                leaf timeout {
                    type uint32 {
                        range "1..1800";
                    }
                    units "seconds";
                    description "Time during which the router operates in overload state";
                }

            } // container overload-on-boot

            container rib-priority {
                description "Enter the rib-priority context";

                container high {
                    description "Enter the high context";

                    leaf prefix-list {
                        type leafref {
                            path "../../../../../policy-options/prefix-list/name";
                        }
                        description "Higher priority list used during OSPF route calculation";
                    }

                } // container high

            } // container rib-priority

            container rtr-adv-lsa-limit {
                presence "Enable the rtr-adv-lsa-limit context";
                description "Enable the rtr-adv-lsa-limit context";

                leaf max-lsa-count {
                    type uint32 {
                        range "1..max";
                    }
                    mandatory true;
                    description "Max number of LSAs one router can advertise";
                }

                leaf log-only {
                    type boolean;
                    default "false";
                    description "Log the event without triggering overload";
                }

                leaf warning-threshold {
                    type uint32 {
                        range "0..100";
                    }
                    units "percent";
                    default "0";
                    description "Percentage of the max LSA count that causes a warning";
                }

                leaf overload-timeout {
                    type types-igp:overload-timeout;
                    default "forever";
                    description "Maximum time in overload after LSA limit is reached";
                }

            } // container rtr-adv-lsa-limit

            container graceful-restart {
                presence "Enable the graceful-restart context";
                description "Enable the graceful-restart context";

                leaf helper-mode {
                    type boolean;
                    default "true";
                    description "Enable graceful restart helper for OSPF";
                }

                leaf strict-lsa-checking {
                    type boolean;
                    default "true";
                    description "Perform strict LSA checking during graceful restart";
                }

            } // container graceful-restart

            container traffic-engineering-options {
                description "Enter the traffic-engineering-options context";

                leaf sr-te {
                    type enumeration {
                        enum "false"                        { value 0; }
                        enum "legacy"                       { value 1; }
                        enum "application-specific-link-attributes" { value 2; }
                    }
                    default "false";
                    description "Advertisement of link attributes for SR-TE";
                }

            } // container traffic-engineering-options

            container timers {
                description "Enter the timers context";

                leaf incremental-spf-wait {
                    type uint32 {
                        range "0..1000";
                    }
                    units "milliseconds";
                    default "1000";
                    description "Delay time before an incremental SPF calculation starts";
                }

                leaf lsa-accumulate {
                    type uint32 {
                        range "0..1000";
                    }
                    units "milliseconds";
                    default "1000";
                    description "Delay to gather LSAs before advertising to neighbors";
                }

                leaf lsa-arrival {
                    type uint32 {
                        range "0..600000";
                    }
                    units "milliseconds";
                    default "1000";
                    description "Min delay between receipt of same LSAs from neighbors";
                }

                leaf redistribute-delay {
                    type uint32 {
                        range "0..1000";
                    }
                    units "milliseconds";
                    default "1000";
                    description "Hold down timer for external routes into OSPF";
                }

                container lsa-generate {
                    description "Enter the lsa-generate context";

                    leaf max-lsa-wait {
                        type uint32 {
                            range "10..600000";
                        }
                        units "milliseconds";
                        default "5000";
                        description "Max time between two LSAs being generated";
                    }

                    leaf lsa-initial-wait {
                        type uint32 {
                            range "10..600000";
                        }
                        units "milliseconds";
                        default "5000";
                        description "First wait period between OSPF LSA generation";
                    }

                    leaf lsa-second-wait {
                        type uint32 {
                            range "10..600000";
                        }
                        units "milliseconds";
                        default "5000";
                        description "Hold time between the first and second LSA generation";
                    }

                } // container lsa-generate

                container spf-wait {
                    description "Enter the spf-wait context";

                    leaf spf-max-wait {
                        type uint32 {
                            range "10..120000";
                        }
                        units "milliseconds";
                        default "10000";
                        description "Max interval between two consecutive SPF calculations";
                    }

                    leaf spf-initial-wait {
                        type uint32 {
                            range "10..100000";
                        }
                        units "milliseconds";
                        default "1000";
                        description "Initial SPF calculation delay after a topology change";
                    }

                    leaf spf-second-wait {
                        type uint32 {
                            range "10..100000";
                        }
                        units "milliseconds";
                        default "1000";
                        description "Hold time between the first and second SPF calculation";
                    }

                } // container spf-wait

            } // container timers

            container loopfree-alternate {
                presence "Enable the loopfree-alternate context";
                description "Enable the loopfree-alternate context";

                leaf augment-route-table {
                    type boolean;
                    default "false";
                    description "Attach remote LFA information to RTM entries";
                }

                container exclude {
                    description "Enter the exclude context";

                    leaf-list prefix-policy {
                        type leafref {
                            path "../../../../../policy-options/policy-statement/name";
                        }
                        max-elements 5;
                        ordered-by user;
                        description "Policy to exclude prefixes from LFA SPF calculation";
                    }

                } // container exclude

                container remote-lfa {
                    presence "Enable the remote-lfa context";
                    description "Enable the remote-lfa context";

                    leaf max-pq-cost {
                        type uint32;
                        default "65535";
                        description "Destination max cost for reverse SPF calculation";
                    }

                    container node-protect {
                        presence "Enable the node-protect context";
                        description "Enter the node-protect context";

                        leaf max-pq-nodes {
                            type uint32 {
                                range "1..32";
                            }
                            default "16";
                            description "Maximum number of PQ nodes found in the LFA SPFs";
                        }

                    } // container node-protect

                } // container remote-lfa

                container ti-lfa {
                    presence "Enable the ti-lfa context";
                    description "Enable the ti-lfa context";

                    leaf max-sr-frr-labels {
                        type uint32 {
                            range "0..3";
                        }
                        default "2";
                        description "Maximum number of labels the TI-LFA backup path can use";
                    }

                    container node-protect {
                        presence "Enable the node-protect context";
                        description "Enter the node-protect context";

                    } // container node-protect

                } // container ti-lfa

            } // container loopfree-alternate

            container database-export {
                presence "Enable the database-export context";
                description "Enable the database-export context";

                leaf igp-identifier {
                    type uint64;
                    description "IGP instance in the BGP-LS NLRI";
                }

                container bgp-ls-identifier {
                    presence "Enable the bgp-ls-identifier context";
                    description "Enable the bgp-ls-identifier context";

                    leaf value {
                        type uint32;
                        default "0";
                        description "BGP-LS identifier sent in the BGP-LS NLRI";
                    }

                } // container bgp-ls-identifier

            } // container database-export

            container asbr {
                presence "Enable the asbr context";
                description "Enable the asbr context";

                leaf trace-path {
                    type union {
                        type int32 {
                            range "0..31";
                        }
                        type enumeration {
                            enum "none"                         { value -1; }
                        }
                    }
                    default "none";
                    description "Domain identity";
                }

            } // container asbr

            container entropy-label {
                description "Enter the entropy-label context";

                leaf override-tunnel-elc {
                    type boolean;
                    default "false";
                    description "Enable override of received ELC advertisements";
                }

            } // container entropy-label

            container segment-routing {
                description "Enter the segment-routing context";

                leaf admin-state {
                    type types-sros:admin-state;
                    default "disable";
                    description "Administrative state of segment routing";
                }

                leaf adj-sid-hold {
                    type types-igp:adj-sid-hold-type;
                    units "seconds";
                    default "15";
                    description "Adjacency SID hold time";
                }

                leaf entropy-label {
                    type boolean;
                    description "Enable processing of received ELC signaled in the IGP";
                }

                leaf export-tunnel-table {
                    type types-igp:export-tunnel-table-type;
                    description "Export tunnel table";
                }

                leaf srlb {
                    type leafref {
                        path "../../../mpls-labels/reserved-label-block/label-block-name";
                    }
                    description "Segment routing local block";
                }

                leaf tunnel-mtu {
                    type types-router:ip-mtu-ext;
                    description "Tunnel MTU size";
                }

                leaf tunnel-table-pref {
                    type uint32 {
                        range "1..255";
                    }
                    default "10";
                    description "Preference of SR tunnels created by the IGP instance";
                }

                leaf class-forwarding {
                    type boolean;
                    default "false";
                    description "Allow CBF with ECMP over RSVP-TE LSPs as IGP shortcuts";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container prefix-sid-range {
                    presence "Enable the prefix-sid-range context";
                    description "Enable the prefix-sid-range context";

                    choice type {
                        case global {

                            leaf global {
                                type empty;
                                description "BGP global SR range allocation";
                            }

                        }
                        case local {

                            leaf start-label {
                                type uint32 {
                                    range "0..524287";
                                }
                                sros-ext:auto-restart-to-modify;
                                default "0";
                                description "Lower bound value for the local label offset";
                            }

                            leaf max-index {
                                type uint32 {
                                    range "0..524287";
                                }
                                sros-ext:auto-restart-to-modify;
                                default "1";
                                description "Upper bound value for the local SID index";
                            }

                        }
                    }
                } // container prefix-sid-range

                container backup-node-sid {
                    presence "Enable the backup-node-sid context";
                    description "Enable the backup-node-sid context";

                    leaf ip-prefix {
                        type types-sros:ipv4-unicast-prefix;
                        description "IP prefix and prefix length for the backup node SID";
                    }

                    choice type {
                        case label {

                            leaf label {
                                type int64 {
                                    range "1..4294967295";
                                }
                                description "Label value for the node SID";
                            }

                        }
                        case index {

                            leaf index {
                                type int64 {
                                    range "0..4294967295";
                                }
                                description "Node SID index for this interface";
                            }

                        }
                    }
                } // container backup-node-sid

                container egress-statistics {
                    description "Enter the egress-statistics context";

                    leaf adj-set {
                        type boolean;
                        default "false";
                        description "Enable the allocation of statistics on adjacency sets";
                    }

                    leaf adj-sid {
                        type boolean;
                        default "false";
                        description "Enable the allocation of statistics on adjacency SIDs";
                    }

                    leaf node-sid {
                        type boolean;
                        default "false";
                        description "Enable the allocation of statistics on node SIDs";
                    }

                } // container egress-statistics

                container ingress-statistics {
                    description "Enter the ingress-statistics context";

                    leaf adj-set {
                        type boolean;
                        default "false";
                        description "Enable the allocation of statistics on adjacency sets";
                    }

                    leaf adj-sid {
                        type boolean;
                        default "false";
                        description "Enable the allocation of statistics on adjacency SIDs";
                    }

                    leaf node-sid {
                        type boolean;
                        default "false";
                        description "Enable the allocation of statistics on node SIDs";
                    }

                } // container ingress-statistics

                container maximum-sid-depth {
                    description "Enter the maximum-sid-depth context";

                    leaf override-bmi {
                        type int32 {
                            range "0..12";
                        }
                        description "Value to override the announced node MSD-BMI value";
                    }

                    leaf override-erld {
                        type int32 {
                            range "0..15";
                        }
                        description "Value to override the announced node MSD-ERLD value";
                    }

                } // container maximum-sid-depth

                list adjacency-set {
                    key "id";
                    description "Enter the adjacency-set list instance";

                    leaf id {
                        type uint32 {
                            range "1..max";
                        }
                        description "Non-zero identifier for a given adjacency set";
                    }

                    leaf parallel {
                        type boolean;
                        default "true";
                        description "Require adjacency members to terminate on same neighbor";
                    }

                    leaf advertise {
                        type boolean;
                        default "true";
                        description "Advertise adjacency for links terminating on same node";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container sid {
                        presence "Enable the sid context";
                        description "Enable the sid context";

                        choice type {
                            case label {

                                leaf label {
                                    type int64 {
                                        range "1..1048575";
                                    }
                                    description "Adjacency SID label";
                                }

                            }
                        }
                    } // container sid

                } // list adjacency-set

                container mapping-server {
                    description "Enter the mapping-server context";

                    leaf admin-state {
                        type types-sros:admin-state;
                        default "disable";
                        description "Administrative state of the OSPF mapping server";
                    }

                    list node-sid-map {
                        key "sid-index";
                        description "Enter the node-sid-map list instance";

                        leaf sid-index {
                            type uint32;
                            description "Start SID index for the node SID mapping";
                        }

                        leaf range {
                            type uint32 {
                                range "1..65535";
                            }
                            sros-ext:immutable;
                            default "1";
                            description "Number of prefixes mapped by Extended Range Prefix TLV";
                        }

                        leaf ip-prefix {
                            type types-sros:ipv4-prefix;
                            sros-ext:immutable;
                            mandatory true;
                            description "Starting prefix of the mapping";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container scope {
                            description "Enter the scope context";

                            choice scope {
                                default "as";
                                case area {

                                    leaf area {
                                        type leafref {
                                            path "../../../../../area/area-id";
                                        }
                                        description "Area ID in which the advertise Extended Range TLV is advertised";
                                    }

                                }
                                case as {

                                    leaf as {
                                        type empty;
                                        description "Advertise Extended Range TLV in whole autonomous system";
                                    }

                                }
                            }
                        } // container scope

                    } // list node-sid-map

                } // container mapping-server

            } // container segment-routing

            container flexible-algorithms {
                description "Enter the flexible-algorithms context";

                leaf admin-state {
                    type types-sros:admin-state;
                    default "disable";
                    description "Administrative state of flexible algorithm support";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list flex-algo {
                    key "flex-algo-id";
                    max-elements 7;
                    description "Enter the flex-algo list instance";

                    leaf flex-algo-id {
                        type uint32 {
                            range "128..255";
                        }
                        description "Flexible algorithm ID";
                    }

                    leaf participate {
                        type boolean;
                        default "false";
                        description "Allow participation in the Flexible Algorithm";
                    }

                    leaf advertise {
                        type leafref {
                            path "../../../../../routing-options/flexible-algorithm-definitions/flex-algo/flex-algo-name";
                        }
                        description "Flexible Algorithm Definition advertisement";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container loopfree-alternate {
                        presence "Enable the loopfree-alternate context";
                        description "Enter the loopfree-alternate context";

                    } // container loopfree-alternate

                } // list flex-algo

            } // container flexible-algorithms

            container igp-shortcut {
                description "Enter the igp-shortcut context";

                leaf admin-state {
                    type types-sros:admin-state;
                    default "disable";
                    description "Administrative state of the IGP shortcuts";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container tunnel-next-hop {
                    description "Enter the tunnel-next-hop context";

                    list family {
                        key "family-type";
                        description "Enter the family list instance";

                        leaf family-type {
                            type types-igp:tunn-next-hop-family-type-v4-only;
                            description "Address family type for tunnel next-hop";
                        }

                        leaf resolution {
                            type types-sros:resolution-type;
                            description "Resolution state for IGP shortcut tunnels";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container resolution-filter {
                            description "Enter the resolution-filter context";

                            leaf rsvp {
                                type boolean;
                                default "false";
                                description "Use RSVP tunneling for next-hop resolution";
                            }

                            leaf sr-te {
                                type boolean;
                                default "false";
                                description "Use SR-TE tunneling for next-hop resolution";
                            }

                        } // container resolution-filter

                    } // list family

                } // container tunnel-next-hop

            } // container igp-shortcut

            list area {
                key "area-id";
                description "Enter the area list instance";

                leaf area-id {
                    type types-sros:ipv4-address;
                    description "Area-ID attribute";
                }

                leaf advertise-router-capability {
                    type boolean;
                    default "true";
                    description "Allow router advertisement capabilities";
                }

                leaf blackhole-aggregate {
                    type boolean;
                    default "true";
                    description "Install a low priority blackhole route to avoid loops";
                }

                leaf-list export-policy {
                    type leafref {
                        path "../../../../policy-options/policy-statement/name";
                    }
                    max-elements 5;
                    ordered-by user;
                    description "Type 3 Summary-LSA/OSPFv3 inter-area-prefix-LSA route";
                }

                leaf-list import-policy {
                    type leafref {
                        path "../../../../policy-options/policy-statement/name";
                    }
                    max-elements 5;
                    ordered-by user;
                    description "Route imported as Summary Type 3/Inter-Area-Prefix-LSA";
                }

                leaf loopfree-alternate-exclude {
                    type boolean;
                    default "false";
                    description "Exclude interfaces in OSPF areas in SPF LFA computation";
                }

                leaf database-export-exclude {
                    type boolean;
                    default "false";
                    description "Exclude IGP link-state OSPF area info into TE-DB";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container stub {
                    presence "Enable the stub context";
                    description "Enable the stub context";

                    leaf default-metric {
                        type uint32 {
                            range "1..16777214";
                        }
                        default "1";
                        description "Metric used by ABR for default route into the stub area";
                    }

                    leaf summaries {
                        type boolean;
                        default "true";
                        description "Send summary (Type 3) LSAs into the stub area on an ABR";
                    }

                } // container stub

                container bier {
                    description "Enter the bier context";

                    leaf admin-state {
                        type types-sros:admin-state;
                        default "disable";
                        description "Administrative state of BIER";
                    }

                    leaf template {
                        type leafref {
                            path "../../../../bier/template/template-name";
                        }
                        description "BIER template name";
                    }

                } // container bier

                container nssa {
                    presence "Enable the nssa context";
                    description "Enable the nssa context";

                    leaf redistribute-external {
                        type boolean;
                        default "true";
                        description "Redistribute external routes into the NSSA";
                    }

                    leaf summaries {
                        type boolean;
                        default "true";
                        description "Send summary (Type 3) LSAs into the NSSA on an ABR";
                    }

                    list area-range {
                        key "ip-prefix-mask";
                        description "Enter the area-range list instance";

                        leaf ip-prefix-mask {
                            type types-sros:ipv4-unicast-prefix;
                            description "IP prefix and subnet mask for the range used by the ABR";
                        }

                        leaf advertise {
                            type boolean;
                            default "true";
                            description "Advertise summarized range of addresses to other areas";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list area-range

                    container originate-default-route {
                        presence "Enable the originate-default-route context";
                        description "Enable the originate-default-route context";

                        leaf type-nssa {
                            type boolean;
                            default "false";
                            description "Generate a default route using NSSA-LSA type";
                        }

                        leaf adjacency-check {
                            type boolean;
                            default "true";
                            description "Default route to remove if there is no adjacency";
                        }

                    } // container originate-default-route

                } // container nssa

                list area-range {
                    key "ip-prefix-mask";
                    description "Enter the area-range list instance";

                    leaf ip-prefix-mask {
                        type types-sros:ipv4-unicast-prefix;
                        description "IP prefix and subnet mask for the range used by the ABR";
                    }

                    leaf advertise {
                        type boolean;
                        default "true";
                        description "Advertise summarized range of addresses to other areas";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list area-range

                list interface {
                    key "interface-name";
                    description "Enter the interface list instance";

                    leaf interface-name {
                        type types-sros:interface-name;
                        description "Router interface name";
                    }

                    leaf advertise-router-capability {
                        type boolean;
                        default "true";
                        description "Allow router advertisement capabilities";
                    }

                    leaf advertise-subnet {
                        type boolean;
                        default "true";
                        description "Advertise point-to-point interfaces as subnet routes";
                    }

                    leaf interface-type {
                        type types-ospf:interface-type;
                        sros-ext:immutable;
                        description "Interface type";
                    }

                    leaf lsa-filter-out {
                        type types-ospf:lsa-filter-out;
                        default "none";
                        description "LSA flooding reduction";
                    }

                    leaf metric {
                        type uint32 {
                            range "1..65535";
                        }
                        description "Route cost metric for the interface";
                    }

                    leaf mtu {
                        type types-router:ip-mtu-ext;
                        description "MTU for the OSPF to use on the interface";
                    }

                    leaf passive {
                        type boolean;
                        description "Advertise passive interfaces as OSPF interfaces";
                    }

                    leaf poll-interval {
                        type uint32;
                        units "seconds";
                        default "120";
                        description "Interval for Hellos to non-adjacent OSPF NBMA neighbor";
                    }

                    leaf priority {
                        type uint16 {
                            range "0..255";
                        }
                        default "1";
                        description "Interface priority in the DR election on the subnet";
                    }

                    leaf rib-priority {
                        type types-ospf:rib-priority;
                        description "RIB priority for OSPF";
                    }

                    leaf load-balancing-weight {
                        type uint32 {
                            range "1..max";
                        }
                        description "Load balancing weight for an OSPF interface";
                    }

                    leaf admin-state {
                        type types-sros:admin-state;
                        default "enable";
                        description "Administrative state of the OSPF interface";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        description "OSPF wait time for Hellos before neighbor declared down";
                    }

                    leaf retransmit-interval {
                        type uint32 {
                            range "1..1800";
                        }
                        units "seconds";
                        default "5";
                        description "Time before OSPF retransmits an unacknowledged LSA";
                    }

                    leaf transit-delay {
                        type uint32 {
                            range "1..1800";
                        }
                        units "seconds";
                        default "1";
                        description "Required LSA transmit time";
                    }

                    leaf authentication-keychain {
                        type leafref {
                            path "../../../../../system/security/keychains/keychain/keychain-name";
                        }
                        description "TCP authentication keychain for the session";
                    }

                    leaf authentication-key {
                        type types-sros:encrypted-leaf {
                            length "1..38";
                        }
                        description "Authentication key";
                    }

                    leaf authentication-type {
                        type types-ospf:authentication-type;
                        description "Authentication type used on OSPF interface";
                    }

                    leaf sid-protection {
                        type boolean;
                        default "true";
                        description "Allow adjacency SID protection by LFA and remote LFA";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container bfd-liveness {
                        presence "Enable the bfd-liveness context";
                        description "Enable the bfd-liveness context";

                        leaf remain-down-on-failure {
                            type boolean;
                            default "false";
                            description "Force adjacency down on failure until session returns";
                        }

                    } // container bfd-liveness

                    container loopfree-alternate {
                        description "Enter the loopfree-alternate context";

                        leaf exclude {
                            type boolean;
                            default "false";
                            description "Enable fast reroute at OSPF primary interface level";
                        }

                        container policy-map {
                            presence "Enable the policy-map context";
                            description "Enter the policy-map context";

                            leaf route-nh-template {
                                type leafref {
                                    path "../../../../../../../routing-options/route-next-hop-policy/template/template-name";
                                }
                                mandatory true;
                                description "Route next hop policy template name";
                            }

                        } // container policy-map

                    } // container loopfree-alternate

                    container node-sid {
                        presence "Enable the node-sid context";
                        description "Enable the node-sid context";

                        leaf clear-n-flag {
                            type boolean;
                            default "false";
                            description "Clear the N-flag in an OSPF prefix";
                        }

                        choice type {
                            case label {

                                leaf label {
                                    type int64 {
                                        range "1..4294967295";
                                    }
                                    description "Label value for the node SID";
                                }

                            }
                            case index {

                                leaf index {
                                    type int64 {
                                        range "0..4294967295";
                                    }
                                    description "Node SID index for this interface";
                                }

                            }
                        }
                    } // container node-sid

                    container adjacency-sid {
                        presence "Enable the adjacency-sid context";
                        description "Enable the adjacency-sid context";

                        choice type {
                            case label {

                                leaf label {
                                    type int64 {
                                        range "1..1048575";
                                    }
                                    description "Adjacency SID label";
                                }

                            }
                        }
                    } // container adjacency-sid

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 hash key";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list message-digest-key

                    list neighbor {
                        key "address";
                        description "Add a list entry for neighbor";

                        leaf address {
                            type types-sros:ipv4-unicast-address;
                            description "IPv4 address of the OSPFv2 neighbor";
                        }

                    } // list neighbor

                    list adjacency-set {
                        key "id";
                        max-elements 1024;
                        description "Add a list entry for adjacency-set";

                        leaf id {
                            type leafref {
                                path "../../../../segment-routing/adjacency-set/id";
                            }
                            description "Adjacency set identity";
                        }

                    } // list adjacency-set

                    list flex-algo {
                        key "flex-algo-id";
                        max-elements 7;
                        description "Enter the flex-algo list instance";

                        leaf flex-algo-id {
                            type uint32 {
                                range "128..255";
                            }
                            description "Flexible algorithm ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container node-sid {
                            presence "Enable the node-sid context";
                            description "Enter the node-sid context";

                            choice type {
                                case label {

                                    leaf label {
                                        type int64 {
                                            range "1..4294967295";
                                        }
                                        description "Label value for the node SID";
                                    }

                                }
                                case index {

                                    leaf index {
                                        type int64 {
                                            range "0..4294967295";
                                        }
                                        description "Node SID index for this interface";
                                    }

                                }
                            }
                        } // container node-sid

                    } // list flex-algo

                } // list interface

                list virtual-link {
                    key "router-id transit-area";
                    description "Enter the virtual-link list instance";

                    leaf router-id {
                        type types-sros:ipv4-address;
                        description "Router identity of the virtual link neighbor";
                    }

                    leaf transit-area {
                        type leafref {
                            path "../../../area/area-id";
                        }
                        description "Transit area linking the backbone to not-connected area";
                    }

                    leaf admin-state {
                        type types-sros:admin-state;
                        default "enable";
                        description "Administrative state of the OSPF interface";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        description "OSPF wait time for Hellos before neighbor declared down";
                    }

                    leaf retransmit-interval {
                        type uint32 {
                            range "1..1800";
                        }
                        units "seconds";
                        default "5";
                        description "Time before OSPF retransmits an unacknowledged LSA";
                    }

                    leaf transit-delay {
                        type uint32 {
                            range "1..1800";
                        }
                        units "seconds";
                        default "1";
                        description "Required LSA transmit time";
                    }

                    leaf authentication-keychain {
                        type leafref {
                            path "../../../../../system/security/keychains/keychain/keychain-name";
                        }
                        description "TCP authentication keychain for the session";
                    }

                    leaf authentication-key {
                        type types-sros:encrypted-leaf {
                            length "1..38";
                        }
                        description "Authentication key";
                    }

                    leaf authentication-type {
                        type types-ospf:authentication-type;
                        description "Authentication type used on OSPF interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 hash key";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list message-digest-key

                } // list virtual-link

            } // list area

        } // list ospf

    } // grouping conf-router-ospf

}
