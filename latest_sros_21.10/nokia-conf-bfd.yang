submodule nokia-conf-bfd {

    yang-version "1.1";

    belongs-to nokia-conf { prefix "conf"; }

    import nokia-sros-yang-extensions     { prefix "sros-ext"; }
    import nokia-types-sros               { prefix "types-sros"; }

    include nokia-conf-groups;


    sros-ext:sros-major-release "rel21";

    organization "Nokia";

    contact
        "Nokia SR OS Support
         Web: <http://www.nokia.com>";

    description
        "Nokia YANG Data model to configure BFD protocol on SR OS based routers.

         Copyright 2016 Nokia. All rights reserved. Reproduction of this document
         is authorized on the condition that the foregoing copyright notice is included.

         This nokia-conf-bfd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-09-02";

    grouping conf-bfd {
        container bfd {
            description "Enter the bfd context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list bfd-template {
                key "name";
                description "Enter the bfd-template list instance";

                leaf name {
                    type types-sros:named-item;
                    description "BFD template name";
                }

                leaf echo-receive {
                    type uint32 {
                        range "100..100000";
                    }
                    units "milliseconds";
                    default "100";
                    description "Echo receive interval";
                }

                leaf multiplier {
                    type uint32 {
                        range "1..20";
                    }
                    default "3";
                    description "Detection multiplier value";
                }

                leaf receive-interval {
                    type uint32 {
                        range "10..100000";
                    }
                    units "milliseconds";
                    default "100";
                    description "Receive interval";
                }

                leaf transmit-interval {
                    type uint32 {
                        range "10..100000";
                    }
                    units "milliseconds";
                    default "100";
                    description "Transmit interval";
                }

                leaf type {
                    type enumeration {
                        enum "cpm-np"                       { value 1; }
                    }
                    description "Local termination point for the BFD session";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list bfd-template

            container seamless-bfd {
                description "Enter the seamless-bfd context";

                list reflector {
                    key "name";
                    max-elements 1;
                    description "Enter the reflector list instance";

                    leaf name {
                        type types-sros:named-item;
                        description "S-BFD reflector name";
                    }

                    leaf admin-state {
                        type types-sros:admin-state;
                        default "disable";
                        description "Administrative state of the seamless BFD reflector";
                    }

                    leaf discriminator {
                        type uint32 {
                            range "524288..526335";
                        }
                        description "Discriminator of the seamless BFD reflector";
                    }

                    leaf description {
                        type types-sros:description;
                        description "Text description";
                    }

                    leaf local-state {
                        type enumeration {
                            enum "admin-down"                   { value 0; }
                            enum "up"                           { value 3; }
                        }
                        default "up";
                        description "Local state of the seamless BFD reflector";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list reflector

            } // container seamless-bfd

        } // container bfd

    } // grouping conf-bfd

}
