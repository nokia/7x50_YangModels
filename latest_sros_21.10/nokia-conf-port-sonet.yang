submodule nokia-conf-port-sonet {

    yang-version "1.1";

    belongs-to nokia-conf { prefix "conf"; }

    import ietf-yang-types                { prefix "yang"; }
    import nokia-sros-yang-extensions     { prefix "sros-ext"; }
    import nokia-types-port               { prefix "types-port"; }
    import nokia-types-qos                { prefix "types-qos"; }
    import nokia-types-sros               { prefix "types-sros"; }
    import nokia-types-subscriber-mgmt    { prefix "types-submgt"; }

    include nokia-conf-groups;
    include nokia-conf-log;
    include nokia-conf-qos;


    sros-ext:sros-major-release "rel21";

    organization "Nokia";

    contact
        "Nokia SR OS Support
         Web: <http://www.nokia.com>";

    description
        "Nokia YANG Data model to configure SONET/SDH ports on SR OS based routers.

         Copyright 2016 Nokia. All rights reserved. Reproduction of this document
         is authorized on the condition that the foregoing copyright notice is included.

         This nokia-conf-port-sonet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-26";

    grouping conf-port-sonet-sonet-sdh {
        container sonet-sdh {
            description "Enter the sonet-sdh context";

            leaf clock-source {
                type enumeration {
                    enum "loop-timed"                   { value 1; }
                    enum "node-timed"                   { value 2; }
                }
                description "Clock used for transmitted data";
            }

            leaf framing {
                type enumeration {
                    enum "sonet"                        { value 2; }
                    enum "sdh"                          { value 3; }
                }
                sros-ext:immutable;
                default "sonet";
                description "SONET or SDH framing";
            }

            leaf loopback {
                type enumeration {
                    enum "line"                         { value 1; }
                    enum "internal"                     { value 2; }
                }
                description "Loopback to activate on SONET port";
            }

            leaf reset-port-on-path-down {
                status obsolete;
                type boolean;
                default "false";
                description "Reset port when path goes operationally down";
            }

            leaf sd-threshold {
                type uint32 {
                    range "3..9";
                }
                default "6";
                description "Threshold for line signal failure BER";
            }

            leaf sf-threshold {
                type uint32 {
                    range "3..6";
                }
                default "3";
                description "Threshold for line signal failure BER";
            }

            leaf single-fiber {
                type boolean;
                default "false";
                description "Allow packet gathering and redirection of IP packets from a single fiber (RX) port";
            }

            leaf speed {
                type enumeration {
                    enum "oc3"                          { value 1; }
                    enum "oc12"                         { value 2; }
                    enum "oc48"                         { value 3; }
                    enum "oc192"                        { value 4; }
                    enum "oc768"                        { value 5; }
                    enum "oc1"                          { value 6; }
                }
                sros-ext:immutable;
                description "SONET/SDH port speed";
            }

            leaf suppress-low-order-alarms {
                type boolean;
                default "false";
                description "Suppress low order alarms";
            }

            leaf tx-dus {
                type boolean;
                default "false";
                description "Force the QL value to be set to QL-DUS/QL-DNU";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container hold-time {
                description "Enter the hold-time context";

                leaf up {
                    type uint32 {
                        range "0..100";
                    }
                    units "deciseconds";
                    default "5";
                    description "Hold timer for link up event dampening";
                }

                leaf down {
                    type uint32 {
                        range "0..100";
                    }
                    units "deciseconds";
                    description "Hold timer for link down event dampening";
                }

            } // container hold-time

            container report-alarm {
                description "Enter the report-alarm context";

                leaf loc {
                    type boolean;
                    default "true";
                    description "Report alarm for a loss of clock that causes the port to shut down";
                }

                leaf lais {
                    type boolean;
                    default "false";
                    description "Report Line Indication Signal Errors alarm";
                }

                leaf lrdi {
                    type boolean;
                    default "true";
                    description "Report Line Remote Defect Indication Errors alarm";
                }

                leaf ss1f {
                    type boolean;
                    default "false";
                    description "Report alarm for section synchronization failure";
                }

                leaf lb2er-sd {
                    type boolean;
                    default "false";
                    description "Report alarm for line signal degradation BER (bit interleaved parity) errors";
                }

                leaf lb2er-sf {
                    type boolean;
                    default "true";
                    description "Report alarm line signal failure BER errors";
                }

                leaf slof {
                    type boolean;
                    default "true";
                    description "Report alarm for section loss of frame errors";
                }

                leaf slos {
                    type boolean;
                    default "true";
                    description "Report alarm for section loss of signal error on the transmit side";
                }

                leaf lrei {
                    type boolean;
                    default "false";
                    description "Report alarm for a line error condition";
                }

            } // container report-alarm

            container section-trace {
                description "Enter the section-trace context";

                choice section-trace {
                    default "byte";
                    case increment-z0 {

                        leaf increment-z0 {
                            type empty;
                            description "Configure incrementing STM ID instead of a static value";
                        }

                    }
                    case byte {

                        leaf byte {
                            type string {
                                length "1..4";
                            }
                            default "1";
                            description "Section trace bytes in the SONET section header";
                        }

                    }
                    case string {

                        leaf string {
                            type string {
                                length "0..16";
                            }
                            description "Text string that identifies the section";
                        }

                    }
                }
            } // container section-trace

            list group {
                key "group-index";
                description "Enter the group list instance";

                leaf group-index {
                    type types-port:sdh-group-index;
                    description "Components making up the specified SONET/SDH path";
                }

                leaf payload {
                    type types-port:sonet-group-payload-type;
                    default "tu3";
                    description "SONET/SDH group payload";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list group

            list path {
                key "path-index";
                description "Enter the path list instance";

                leaf path-index {
                    type types-port:sonet-path-index;
                    description "SONET/SDH path index";
                }

                leaf admin-state {
                    type types-sros:admin-state;
                    default "disable";
                    description "Administrative state of the SONET/SDH path";
                }

                leaf crc {
                    type uint32 {
                        range "16|32";
                    }
                    description "Cyclic redundancy check";
                }

                leaf description {
                    type types-sros:long-description;
                    description "Text description";
                }

                leaf load-balancing-algorithm {
                    type types-port:load-balancing-algorithm;
                    description "Load balancing algorithm";
                }

                leaf mac-address {
                    type yang:mac-address;
                    default "00:00:00:00:00:00";
                    description "MAC address for the SONET/SDH path";
                }

                leaf mode {
                    type enumeration {
                        enum "access"                       { value 1; }
                        enum "network"                      { value 2; }
                    }
                    sros-ext:auto-restart-to-modify;
                    description "Operation port mode for the SONET/SDH path";
                }

                leaf encap-type {
                    type types-port:sonet-path-encap-type;
                    sros-ext:auto-restart-to-modify;
                    description "Configure an encap method.";
                }

                leaf mtu {
                    type uint32 {
                        range "512..9208";
                    }
                    units "bytes";
                    description "Maximum payload MTU size";
                }

                leaf payload {
                    type types-port:sonet-path-payload-type;
                    sros-ext:immutable;
                    description "SONET/SDH path payload";
                }

                leaf scramble {
                    type boolean;
                    description "Enable SONET/SDH payload scrambling";
                }

                leaf signal-label {
                    type string {
                        length "1..4";
                    }
                    description "C2 byte value that communicates the payload type";
                }

                leaf trace-string {
                    type union {
                        type enumeration {
                            enum "zeros"                        { value 0; }
                        }
                        type string {
                            length "0..62";
                        }
                    }
                    description "J1 path-trace string that identifies the circuit";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container report-alarm {
                    description "Enter the report-alarm context";

                    leaf pais {
                        type boolean;
                        default "false";
                        description "Report path alarm indication signal errors";
                    }

                    leaf plop {
                        type boolean;
                        default "true";
                        description "Report path loss of pointer errors as a trap";
                    }

                    leaf prdi {
                        type boolean;
                        default "false";
                        description "Report path remote defect indication errors";
                    }

                    leaf pplm {
                        type boolean;
                        default "true";
                        description "Report a path payload mismatch trap";
                    }

                    leaf prei {
                        type boolean;
                        default "false";
                        description "Report a path error condition as a result of b3 error";
                    }

                    leaf puneq {
                        type boolean;
                        default "true";
                        description "Report path unequipped errors";
                    }

                    leaf plcd {
                        type boolean;
                        default "false";
                        description "Report path loss of code group delineation errors";
                    }

                } // container report-alarm

                container egress {
                    description "Enter the egress context";

                    container port-scheduler-policy {
                        description "Enter the port-scheduler-policy context";

                        leaf policy-name {
                            type leafref {
                                path "../../../../../../qos/port-scheduler-policy/name";
                            }
                            description "Port egress scheduler policy name";
                        }

                        container overrides {
                            presence "Enable the overrides context";
                            description "Enter the overrides context";

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container max-rate {
                                description "Enter the max-rate context";

                                choice rate-or-percent-rate {
                                    case rate {

                                        leaf rate {
                                            type types-qos:scheduler-pir-rate;
                                            units "kilobps";
                                            default "max";
                                            description "PIR";
                                        }

                                    }
                                    case percent-rate {

                                        leaf percent-rate {
                                            type decimal64 {
                                                range "0.01..100";
                                                fraction-digits 2;
                                            }
                                            units "percent";
                                            default "100";
                                            description "PIR";
                                        }

                                    }
                                }
                            } // container max-rate

                            list level {
                                key "priority-level";
                                description "Enter the level list instance";

                                leaf priority-level {
                                    type uint32 {
                                        range "1..8";
                                    }
                                    description "Port priority levels override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                choice rate-or-percent-rate {
                                    case rate {

                                        container rate {
                                            description "Enter the rate context";

                                            leaf pir {
                                                type types-qos:scheduler-pir-rate;
                                                units "kilobps";
                                                default "max";
                                                description "PIR for the priority level";
                                            }

                                            leaf cir {
                                                type types-qos:scheduler-cir-rate;
                                                units "kilobps";
                                                default "max";
                                                description "CIR for the priority level";
                                            }

                                        } // container rate

                                    }
                                    case percent-rate {

                                        container percent-rate {
                                            description "Enter the percent-rate context";

                                            leaf pir {
                                                type decimal64 {
                                                    range "0.01..100";
                                                    fraction-digits 2;
                                                }
                                                units "percent";
                                                default "100";
                                                description "PIR for the priority level";
                                            }

                                            leaf cir {
                                                type decimal64 {
                                                    range "0..100";
                                                    fraction-digits 2;
                                                }
                                                units "percent";
                                                default "100";
                                                description "CIR for the priority level";
                                            }

                                        } // container percent-rate

                                    }
                                }
                            } // list level

                        } // container overrides

                    } // container port-scheduler-policy

                } // container egress

                container network {
                    description "Enter the network context";

                    leaf accounting-policy {
                        type leafref {
                            path "../../../../../log/accounting-policy/policy-id";
                        }
                        description "Accounting policy";
                    }

                    leaf collect-stats {
                        type boolean;
                        default "false";
                        description "Collect accounting and statistical data";
                    }

                    leaf queue-policy {
                        type leafref {
                            path "../../../../../qos/network-queue/network-queue-policy";
                        }
                        description "Queue policy on the SONET/SDH network path";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container network

                container ppp {
                    description "Enter the ppp context";

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container keepalive {
                        description "Enter the keepalive context";

                        leaf drop-count {
                            type uint32 {
                                range "1..255";
                            }
                            default "3";
                            description "Consecutive missed keepalives before port is taken down";
                        }

                        leaf interval {
                            type union {
                                type uint32 {
                                    range "1..60";
                                }
                                type enumeration {
                                    enum "none"                         { value 0; }
                                }
                            }
                            units "seconds";
                            default "10";
                            description "Interval at which keepalive messages are issued";
                        }

                    } // container keepalive

                } // container ppp

            } // list path

        } // container sonet-sdh

    } // grouping conf-port-sonet-sonet-sdh

}
