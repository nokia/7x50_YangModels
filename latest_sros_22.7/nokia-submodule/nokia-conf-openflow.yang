submodule nokia-conf-openflow {

    yang-version "1.1";

    belongs-to nokia-conf { prefix "conf"; }

    import nokia-sros-yang-extensions     { prefix "sros-ext"; }
    import nokia-types-services           { prefix "types-services"; }
    import nokia-types-sros               { prefix "types-sros"; }

    include nokia-conf-groups;
    include nokia-conf-system;
    include nokia-conf-system-security;
    include nokia-conf-system-security-tls;


    sros-ext:sros-major-release "rel22";

    organization "Nokia";

    contact
        "Nokia SR OS Support
         Web: <http://www.nokia.com>";

    description
        "Nokia YANG Data model to configure openflow parameters on SR OS based routers.

         Copyright 2016 Nokia. All rights reserved. Reproduction of this document
         is authorized on the condition that the foregoing copyright notice is included.

         This nokia-conf-openflow YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-07";

    grouping conf-openflow {
        container openflow {
            description "Enter the openflow context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list of-controller {
                key "controller-id";
                max-elements 1;
                description "Enter the of-controller list instance";

                leaf controller-id {
                    type uint32;
                    description "OpenFlow controller ID";
                }

                leaf admin-state {
                    type types-sros:admin-state;
                    default "disable";
                    description "Administrative state of OpenFlow controller instance";
                }

                leaf description {
                    type types-sros:description;
                    description "Text description";
                }

                leaf version {
                    type enumeration {
                        enum "version-1-3-1"                { value 4; }
                    }
                    default "version-1-3-1";
                    description "Version negotiated between OF controller and switch";
                }

                leaf address {
                    type types-sros:ipv4-address;
                    sros-ext:auto-restart-to-modify;
                    description "Local IPv4 address for the OpenFlow controller";
                }

                leaf echo-interval {
                    type uint32 {
                        range "10..3600";
                    }
                    units "seconds";
                    default "10";
                    description "Interval for monitoring OpenFlow control channels";
                }

                leaf echo-multiple {
                    type uint32 {
                        range "3..100";
                    }
                    default "3";
                    description "Consecutive lost messages before channel declared down";
                }

                leaf tls-server-profile {
                    type leafref {
                        path "../../../system/security/tls/server-tls-profile/server-profile-name";
                    }
                    sros-ext:auto-restart-to-modify;
                    description "Profile name used by the controller";
                }

                leaf role {
                    type enumeration {
                        enum "equal"                        { value 0; }
                    }
                    default "equal";
                    description "Role when multiple controllers connected to OF switch";
                }

                leaf ipv6-address {
                    type types-sros:ipv6-unicast-address;
                    description "IPv6 address for the OpenFlow channel to the controller";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list of-controller

            list of-switch {
                key "name";
                max-elements 8;
                description "Enter the of-switch list instance";

                leaf name {
                    type types-sros:named-item;
                    description "OpenFlow switch name";
                }

                leaf admin-state {
                    type types-sros:admin-state;
                    default "disable";
                    description "Administrative state of the OpenFlow switch instance";
                }

                leaf description {
                    type types-sros:very-long-description;
                    description "Text description";
                }

                leaf ofs-id {
                    type uint32 {
                        range "1..8";
                    }
                    sros-ext:immutable;
                    description "OFS switch ID";
                }

                leaf echo-interval {
                    type uint32 {
                        range "1..3600";
                    }
                    units "seconds";
                    default "10";
                    description "Interval for monitoring OpenFlow control channels";
                }

                leaf echo-multiple {
                    type uint32 {
                        range "3..100";
                    }
                    default "3";
                    description "Consecutive lost messages before channel declared down";
                }

                leaf aux-channel {
                    type boolean;
                    default "false";
                    description "Enable the auxiliary connection for the H-OFS instance";
                }

                leaf-list logical-port-status {
                    type enumeration {
                        enum "rsvp-te"                      { value 1; }
                        enum "mpls-tp"                      { value 2; }
                        enum "sr-te"                        { value 3; }
                    }
                    max-elements 3;
                    description "Logical port type for status change reporting";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list flowtable {
                    key "table-id";
                    max-elements 1;
                    description "Enter the flowtable list instance";

                    leaf table-id {
                        type uint32;
                        description "OpenFlow table ID";
                    }

                    leaf max-size {
                        type uint32 {
                            range "1..524288";
                        }
                        default "1000";
                        description "Maximum size of the flow table";
                    }

                    leaf mismatch-action {
                        type enumeration {
                            enum "drop"                         { value 1; }
                            enum "fall-through"                 { value 2; }
                            enum "packet-in"                    { value 3; }
                        }
                        default "fall-through";
                        description "Action taken when no match entries found in flow table";
                    }

                    leaf switch-defined-cookie {
                        type boolean;
                        default "false";
                        description "Enable switch-defined cookie encoding";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list flowtable

                list controller {
                    key "address port";
                    max-elements 2;
                    description "Enter the controller list instance";

                    leaf address {
                        type types-sros:ip-unicast-address;
                        description "IP address of the OpenFlow channel to the controller";
                    }

                    leaf port {
                        type uint32 {
                            range "1..65535";
                        }
                        description "Controller port ID";
                    }

                    leaf tls-client-profile {
                        type leafref {
                            path "../../../../system/security/tls/client-tls-profile/client-profile-name";
                        }
                        description "TLS profile name for use on the control channel";
                    }

                    leaf service-name {
                        type types-services:service-name;
                        description "Administrative service name";
                    }

                    leaf ofc-loopback {
                        type types-sros:ip-unicast-address;
                        description "Loopback IP address in the VPRN";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list controller

            } // list of-switch

        } // container openflow

    } // grouping conf-openflow

}
