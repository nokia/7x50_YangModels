submodule nokia-conf-saa {

    yang-version "1.1";

    belongs-to nokia-conf { prefix "conf"; }

    import ietf-yang-types                { prefix "yang"; }
    import nokia-sros-yang-extensions     { prefix "sros-ext"; }
    import nokia-types-oam                { prefix "types-oam"; }
    import nokia-types-sros               { prefix "types-sros"; }

    include nokia-conf-groups;
    include nokia-conf-log;


    sros-ext:sros-major-release "rel22";

    organization "Nokia";

    contact
        "Nokia SR OS Support
         Web: <http://www.nokia.com>";

    description
        "Nokia YANG Data model to configure Service Assurance Agent (SAA) on SR OS based routers.

         Copyright 2016 Nokia. All rights reserved. Reproduction of this document
         is authorized on the condition that the foregoing copyright notice is included.

         This nokia-conf-saa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-06-07";

    grouping conf-saa {
        container saa {
            description "Enter the saa context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list owner {
                key "owner-name test";
                description "Enter the owner list instance";

                leaf owner-name {
                    type types-sros:named-item;
                    description "Owner name of the SAA operation";
                }

                leaf test {
                    type types-sros:named-item;
                    description "SAA test name";
                }

                leaf admin-state {
                    type types-sros:admin-state;
                    default "disable";
                    description "Administrative state of the SAA test";
                }

                leaf description {
                    type types-sros:description;
                    description "Text description";
                }

                leaf accounting-policy {
                    type leafref {
                        path "../../../log/accounting-policy/policy-id";
                    }
                    sros-ext:auto-restart-to-modify;
                    description "Accounting policy associated with the SAA test";
                }

                leaf continuous {
                    type boolean;
                    sros-ext:auto-restart-to-modify;
                    default "false";
                    description "Execute the SAA tests as continuous";
                }

                leaf probe-history {
                    type enumeration {
                        enum "keep"                         { value 1; }
                        enum "drop"                         { value 2; }
                        enum "auto"                         { value 3; }
                    }
                    sros-ext:auto-restart-to-modify;
                    default "auto";
                    description "History probe behavior";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list jitter-event {
                    key "direction threshold-type";
                    description "Enter the jitter-event list instance";

                    leaf direction {
                        type types-oam:saa-threshold-direction;
                        description "Direction for OAM ping responses for OAM ping test run";
                    }

                    leaf threshold-type {
                        type enumeration {
                            enum "rising"                       { value 1; }
                            enum "falling"                      { value 2; }
                        }
                        description "Threshold type";
                    }

                    leaf threshold {
                        type uint32 {
                            range "0..2147483647";
                        }
                        units "microseconds";
                        mandatory true;
                        description "Threshold jitter value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list jitter-event

                list latency-event {
                    key "direction threshold-type";
                    description "Enter the latency-event list instance";

                    leaf direction {
                        type types-oam:saa-threshold-direction;
                        description "Direction for OAM ping responses for OAM ping test run";
                    }

                    leaf threshold-type {
                        type enumeration {
                            enum "rising"                       { value 1; }
                            enum "falling"                      { value 2; }
                        }
                        description "Threshold type";
                    }

                    leaf threshold {
                        type uint32 {
                            range "0..2147483647";
                        }
                        units "microseconds";
                        mandatory true;
                        description "Threshold latency value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list latency-event

                list loss-event {
                    key "direction threshold-type";
                    description "Enter the loss-event list instance";

                    leaf direction {
                        type types-oam:saa-threshold-direction;
                        description "Direction for OAM ping responses for OAM ping test run";
                    }

                    leaf threshold-type {
                        type enumeration {
                            enum "rising"                       { value 1; }
                            enum "falling"                      { value 2; }
                        }
                        description "Threshold type";
                    }

                    leaf threshold {
                        type uint32 {
                            range "0..2147483647";
                        }
                        units "packets";
                        mandatory true;
                        description "Threshold loss event value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list loss-event

                container type {
                    description "Enter the type context";

                    choice saa-types {
                        case saa-icmp-ping {

                            container icmp-ping {
                                presence "Enable the icmp-ping context";
                                description "Enable the icmp-ping context";

                                leaf destination-address {
                                    type union {
                                        type types-sros:ip-address;
                                        type types-sros:string-not-all-spaces {
                                            length "1..128";
                                        }
                                    }
                                    mandatory true;
                                    description "Far-end IP address or DNS name to send the ping request";
                                }

                                leaf count {
                                    type uint32 {
                                        range "1..100000";
                                    }
                                    units "packets";
                                    default "5";
                                    description "Number of ICMP Echo Request packets to send";
                                }

                                leaf do-not-fragment {
                                    type boolean;
                                    default "false";
                                    description "Set the DF bit in the ICMP ping packet";
                                }

                                leaf interval {
                                    type union {
                                        type uint32 {
                                            range "1..10000";
                                        }
                                        type decimal64 {
                                            range "0.01..100.00";
                                            fraction-digits 2;
                                        }
                                    }
                                    units "seconds";
                                    default "1";
                                    description "Minimum time to expire before message request is sent";
                                }

                                leaf pattern {
                                    type types-oam:padding-pattern;
                                    default "sequential";
                                    description "Pattern to fill the data portion in a ping packet";
                                }

                                leaf router-instance {
                                    type string;
                                    default "Base";
                                    description "Router name or VPRN service name";
                                }

                                leaf size {
                                    type uint32 {
                                        range "0..16384";
                                    }
                                    units "bytes";
                                    default "56";
                                    description "Request packet size";
                                }

                                leaf source-address {
                                    type types-sros:ip-address;
                                    description "Source IP address";
                                }

                                leaf timeout {
                                    type uint32 {
                                        range "1..10";
                                    }
                                    units "seconds";
                                    default "5";
                                    description "Time router waits for a reply after sending last probe";
                                }

                                leaf ttl {
                                    type uint32 {
                                        range "1..128";
                                    }
                                    default "64";
                                    description "TTL value for the MPLS label";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                choice saa-icmp-ping-routing {
                                    default "case-bypass-routing";
                                    case case-bypass-routing {

                                        leaf bypass-routing {
                                            type boolean;
                                            default "false";
                                            description "Bypass the routing table when sending a ping request";
                                        }

                                    }
                                    case case-interface {

                                        leaf interface {
                                            type types-sros:interface-name;
                                            description "Interface name";
                                        }

                                    }
                                    case case-next-hop-address {

                                        leaf next-hop-address {
                                            type types-sros:ip-address;
                                            description "Next-hop IP address to display static routes";
                                        }

                                    }
                                }
                                container qos {
                                    description "Enter the qos context";

                                    leaf fc {
                                        type types-sros:fc-name;
                                        default "nc";
                                        description "Forwarding class of the SAA";
                                    }

                                    leaf tos {
                                        type uint32 {
                                            range "0..255";
                                        }
                                        default "0";
                                        description "Service type";
                                    }

                                } // container qos

                            } // container icmp-ping

                        }
                    }
                } // container type

            } // list owner

        } // container saa

    } // grouping conf-saa

}
