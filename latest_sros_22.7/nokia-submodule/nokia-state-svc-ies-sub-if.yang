submodule nokia-state-svc-ies-sub-if {

    yang-version "1.1";

    belongs-to nokia-state { prefix "state"; }

    import ietf-yang-types                { prefix "yang"; }
    import nokia-sros-yang-extensions     { prefix "sros-ext"; }
    import nokia-types-card               { prefix "types-card"; }
    import nokia-types-eth-cfm            { prefix "types-eth-cfm"; }
    import nokia-types-qos                { prefix "types-qos"; }
    import nokia-types-services           { prefix "types-services"; }
    import nokia-types-sros               { prefix "types-sros"; }
    import nokia-types-subscriber-mgmt    { prefix "types-submgt"; }

    include nokia-state-eth-cfm;
    include nokia-state-svc-ies-grp-if-wlangw;
    include nokia-state-svc-ies-sub-if-wlangw;


    sros-ext:sros-major-release "rel22";

    organization "Nokia";

    contact
        "Nokia SR OS Support
         Web: <http://www.nokia.com>";

    description
        "Nokia YANG Data model with operational state for ies service subscriber interfaces on SR OS based routers.

         Copyright 2016 Nokia. All rights reserved. Reproduction of this document
         is authorized on the condition that the foregoing copyright notice is included.

         This nokia-state-svc-ies-sub-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-05-09";

    grouping state-svc-ies-sub-if-subscriber-interface {
        list subscriber-interface {
            key "interface-name";
            description "Enter the subscriber-interface list instance";

            leaf interface-name {
                type types-sros:interface-name;
                description "Subscriber interface name";
            }

            leaf if-index {
                type int32;
                description "The interface index.";
            }

            leaf system-if-index {
                type int32;
                description "The interface system index.";
            }

            container ipv4 {
                description "Enter the ipv4 context";

                leaf oper-state {
                    type types-sros:oper-state;
                    description "The current IPv4 operational status of this router interface.";
                }

                leaf down-reason {
                    type bits {
                        bit admin-disabled                 { position 0; }
                        bit service-admin-disabled         { position 1; }
                        bit port-down                      { position 2; }
                        bit address-or-parent-not-ready    { position 3; }
                        bit associated-object-not-ready    { position 4; }
                        bit rvpls-down                     { position 5; }
                        bit operational-group-down         { position 6; }
                        bit admin-destroy                  { position 7; }
                        bit no-address                     { position 8; }
                        bit no-info                        { position 9; }
                        bit hold-down-timer-running        { position 10; }
                        bit protocol-down                  { position 11; }
                        bit invalid-port-configuration     { position 12; }
                        bit unknown                        { position 13; }
                        bit no-route-distinguisher         { position 14; }
                        bit wlan-gateway-redundancy-standby { position 15; }
                        bit wlan-gateway-group-degraded    { position 16; }
                        bit ip-control-tunnel-down         { position 17; }
                        bit pdn-address-mismatch           { position 18; }
                        bit ping-check-failure             { position 19; }
                        bit port-internal-loopback         { position 20; }
                    }
                    description "Indicates the reason for why the interface is operationally down. Values: admin-disabled - Administratively disabled. service-admin-disabled - Assiocated service is administratively disabled. port-down - Associated SAP/port is operationally down. address-or-parent-not-ready - Associated address or parent interface is not ready. associated-object-not-ready - Associated object is not ready. rvpls-down - Associated R-VPLS service is operationally down. operational-group-down - Associated operational group is operationally down. admin-destroy - The interface is being destroyed. no-address - There is no address configured. no-info - The interface info is not present. hold-down-timer-running - The hold down timer is running. protocol-down - The protocols are operationally down. invalid-port-configuration - Invalid port configuration. unknown - The interface is operationally down due to some unknown reason. no-route-distinguisher - No route-distinguisher configured in the VRF. wlan-gateway-redundancy-standby - The interface is in standby state for WLAN-GW redundancy. wlan-gateway-group-degraded - The interface associated WLAN-GW group is in a degraded state. ip-control-tunnel-down - The IP tunnel associated to a control-tunnel interface is operationally down. pdn-address-mismatch - The IP address learned from the packet data network does not match the configured primary IP address. ping-check-failure - The IP interface is or went down because of a ping-template failure. port-internal-loopback - The IP interface is bound to a port that has an internal loopback configured.";
                }

                container statistics {
                    description "Enter the statistics context";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                    leaf out-discard-dbcast-packets {
                        type yang:counter64;
                        description "The number of directed-broadcast packets dropped.";
                    }

                    leaf out-discard-dbcast-octets {
                        type yang:counter64;
                        description "The number of directed-broadcast octets dropped.";
                    }

                    leaf in-ip-helper-redirects-packets {
                        type yang:counter64;
                        description "The number of packets redirected to the ip-helper gateway.";
                    }

                    leaf in-ip-helper-redirects-octets {
                        type yang:counter64;
                        description "The number of bytes redirected to the ip-helper gateway.";
                    }

                } // container statistics

                list address {
                    key "ipv4-address";
                    description "Enter the address list instance";

                    leaf ipv4-address {
                        type types-sros:ipv4-unicast-address;
                        description "IP address associated with the subscriber subnet";
                    }

                    leaf oper-address {
                        type types-sros:ip-address;
                        description "Indicates the operational address of this entry.";
                    }

                    leaf creation-origin {
                        type types-sros:creation-origin;
                        description "Indicates the mechanism used to create this entry.";
                    }

                } // list address

                container dhcp {
                    description "Enter the dhcp context";

                    container lease-populate {
                        description "Enter the lease-populate context";

                        leaf current-lease-states {
                            type uint32 {
                                range "0..511999";
                            }
                            description "The number of DHCP lease states currently allocated on this interface.";
                        }

                    } // container lease-populate

                    container statistics {
                        description "Enter the statistics context";

                        container total-rx-packets {
                            description "Enter the total-rx-packets context";

                            leaf received {
                                type yang:counter32;
                                description "The total number of packets received by the DHCP relay agent.";
                            }

                            leaf malformed {
                                type yang:counter32;
                                description "The total number of malformed packets received by the DHCP relay agent.";
                            }

                            leaf untrusted {
                                type yang:counter32;
                                description "The total number of untrusted packets received by the DHCP relay agent.";
                            }

                        } // container total-rx-packets

                        container total-tx-packets {
                            description "Enter the total-tx-packets context";

                            leaf transmitted {
                                type yang:counter32;
                                description "The total number of packets transmitted by the DHCP relay agent.";
                            }

                        } // container total-tx-packets

                        container client-packets {
                            description "Enter the client-packets context";

                            leaf dropped {
                                type yang:counter32;
                                description "The total number of client packets dropped by the DHCP relay agent.";
                            }

                            leaf relayed {
                                type yang:counter32;
                                description "The total number of client packets relayed by the DHCP relay agent.";
                            }

                            leaf snooped {
                                type yang:counter32;
                                description "The total number of client packets snooped by the DHCP relay agent.";
                            }

                            leaf streamed {
                                type yang:counter32;
                                description "The total number of received client packets scheduled for streaming to an external server, by the DHCP proxy function.";
                            }

                            container proxied {
                                description "Enter the proxied context";

                                leaf radius {
                                    type yang:counter32;
                                    description "The total number of client packets proxied by the DHCP relay agent based on data received from a RADIUS server.";
                                }

                                leaf lease-split {
                                    type yang:counter32;
                                    description "The total number of DHCP lease-split. Lease-split allows the DHCP relay agent to assigning a shorter lease time than the actual lease time assigned by the DHCP server. This allows the system to remove disconnected client quickly but ensure that client's shorter DHCP renewal are process by the relay agent and not the DHCP server.";
                                }

                                leaf nasreq {
                                    type yang:counter32;
                                    description "The total number of client packets proxied by the DHCP relay agent based on data received from a Diameter NASREQ server.";
                                }

                                leaf user-db {
                                    type yang:counter32;
                                    description "The total number of client packets proxied by the DHCP relay agent based on the local user database.";
                                }

                            } // container proxied

                        } // container client-packets

                        container server-packets {
                            description "Enter the server-packets context";

                            leaf dropped {
                                type yang:counter32;
                                description "The total number of server packets dropped by the DHCP relay agent.";
                            }

                            leaf relayed {
                                type yang:counter32;
                                description "The total number of server packets relayed by the DHCP relay agent.";
                            }

                            leaf snooped {
                                type yang:counter32;
                                description "The total number of server packets snooped by the DHCP relay agent.";
                            }

                        } // container server-packets

                        container spoofed-packets {
                            description "Enter the spoofed-packets context";

                            leaf release {
                                type yang:counter32;
                                description "The total number of DHCP RELEASE messages spoofed by the DHCP relay agent to the DHCP server.";
                            }

                            leaf force-renews {
                                type yang:counter32;
                                description "The total number of DHCP FORCERENEW messages spoofed by the DHCP relay agent to the DHCP clients.";
                            }

                        } // container spoofed-packets

                    } // container statistics

                } // container dhcp

            } // container ipv4

            container ipv6 {
                description "Enter the ipv6 context";

                leaf oper-state {
                    type types-sros:oper-state;
                    description "The current IPv6 operational status of this router interface.";
                }

                leaf down-reason {
                    type bits {
                        bit admin-disabled                 { position 0; }
                        bit service-admin-disabled         { position 1; }
                        bit port-down                      { position 2; }
                        bit address-or-parent-not-ready    { position 3; }
                        bit associated-object-not-ready    { position 4; }
                        bit rvpls-down                     { position 5; }
                        bit operational-group-down         { position 6; }
                        bit admin-destroy                  { position 7; }
                        bit no-address                     { position 8; }
                        bit no-info                        { position 9; }
                        bit hold-down-timer-running        { position 10; }
                        bit protocol-down                  { position 11; }
                        bit invalid-port-configuration     { position 12; }
                        bit unknown                        { position 13; }
                        bit no-route-distinguisher         { position 14; }
                        bit wlan-gateway-redundancy-standby { position 15; }
                        bit wlan-gateway-group-degraded    { position 16; }
                        bit ip-control-tunnel-down         { position 17; }
                        bit pdn-address-mismatch           { position 18; }
                        bit ping-check-failure             { position 19; }
                        bit port-internal-loopback         { position 20; }
                    }
                    description "Indicates the reason for why the interface is operationally down. Values: admin-disabled - Administratively disabled. service-admin-disabled - Assiocated service is administratively disabled. port-down - Associated SAP/port is operationally down. address-or-parent-not-ready - Associated address or parent interface is not ready. associated-object-not-ready - Associated object is not ready. rvpls-down - Associated R-VPLS service is operationally down. operational-group-down - Associated operational group is operationally down. admin-destroy - The interface is being destroyed. no-address - There is no address configured. no-info - The interface info is not present. hold-down-timer-running - The hold down timer is running. protocol-down - The protocols are operationally down. invalid-port-configuration - Invalid port configuration. unknown - The interface is operationally down due to some unknown reason. no-route-distinguisher - No route-distinguisher configured in the VRF. wlan-gateway-redundancy-standby - The interface is in standby state for WLAN-GW redundancy. wlan-gateway-group-degraded - The interface associated WLAN-GW group is in a degraded state. ip-control-tunnel-down - The IP tunnel associated to a control-tunnel interface is operationally down. pdn-address-mismatch - The IP address learned from the packet data network does not match the configured primary IP address. ping-check-failure - The IP interface is or went down because of a ping-template failure. port-internal-loopback - The IP interface is bound to a port that has an internal loopback configured.";
                }

                container statistics {
                    description "Enter the statistics context";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                    container hosts {
                        description "Enter the hosts context";

                        leaf ipoe-dhcp6 {
                            type yang:gauge32;
                            description "The number of IPoE DHCPv6 hosts.";
                        }

                        leaf ipoe-slaac {
                            type yang:gauge32;
                            description "The number of IPoE SLAAC hosts.";
                        }

                        leaf ppp-dhcp6 {
                            type yang:gauge32;
                            description "The number of PPP DHCPv6 hosts.";
                        }

                        leaf ppp-slaac {
                            type yang:gauge32;
                            description "The number of PPP SLAAC hosts.";
                        }

                        leaf static-enabled {
                            type yang:gauge32;
                            description "The number of IPv6 static IPoE hosts that are enabled.";
                        }

                    } // container hosts

                } // container statistics

                list address {
                    key "ipv6-address";
                    description "Enter the address list instance";

                    leaf ipv6-address {
                        type types-sros:ipv6-address;
                        description "IPv6 address for the subscriber interface";
                    }

                    leaf address-state {
                        type types-sros:address-state;
                        description "Indicates the address state of the IPv6 address of the interface.";
                    }

                    leaf oper-address {
                        type types-sros:ip-address;
                        description "Indicates the operational address of this entry.";
                    }

                    leaf creation-origin {
                        type types-sros:creation-origin;
                        description "Indicates the mechanism used to create this entry.";
                    }

                } // list address

                list prefix {
                    key "ipv6-prefix";
                    description "Enter the prefix list instance";

                    leaf ipv6-prefix {
                        type types-sros:ipv6-prefix;
                        description "IPv6 address for a router interface";
                    }

                    leaf address-state {
                        type types-sros:address-state;
                        description "Indicates the address state of the IPv6 address of the interface.";
                    }

                    leaf oper-address {
                        type types-sros:ip-address;
                        description "Indicates the operational address of this entry.";
                    }

                    leaf creation-origin {
                        type types-sros:creation-origin;
                        description "Indicates the mechanism used to create this entry.";
                    }

                } // list prefix

                container dhcp6 {
                    description "Enter the dhcp6 context";

                    container proxy-server {
                        description "Enter the proxy-server context";

                        container server-id {
                            description "Enter the server-id context";

                            leaf duid-en-number {
                                type uint32;
                                description "The vendor's registered Private Enterprise Number maintained by IANA.";
                            }

                        } // container server-id

                    } // container proxy-server

                } // container dhcp6

            } // container ipv6

            container hold-time {
                description "Enter the hold-time context";

                container ipv4 {
                    description "Enter the ipv4 context";

                    leaf hold-timer {
                        type uint32;
                        units "seconds";
                        description "The hold-timer indicates the time left before the interface comes up or goes down, depending on the ongoing transition state of the interface.";
                    }

                } // container ipv4

                container ipv6 {
                    description "Enter the ipv6 context";

                    leaf hold-timer {
                        type uint32;
                        units "seconds";
                        description "The hold-timer indicates the time left before the interface comes up or goes down, depending on the ongoing transition state of the interface.";
                    }

                } // container ipv6

            } // container hold-time

            list group-interface {
                key "group-interface-name";
                description "Enter the group-interface list instance";

                leaf group-interface-name {
                    type types-sros:interface-name;
                    description "Group interface name";
                }

                leaf if-index {
                    type int32;
                    description "The interface index.";
                }

                leaf system-if-index {
                    type int32;
                    description "The interface system index.";
                }

                container ingress {
                    description "Enter the ingress context";

                    container statistics {
                        description "Enter the statistics context";

                        container policy-accounting {
                            description "Enter the policy-accounting context";

                            list source-class {
                                key "index";
                                description "Enter the source-class list instance";

                                leaf index {
                                    type types-sros:class-index;
                                    description "Source-class index";
                                }

                                leaf forwarded-packets {
                                    type yang:counter64;
                                    units "packets";
                                    description "Indicates the total number of packets received for this class that were forwarded.";
                                }

                                leaf forwarded-bytes {
                                    type yang:counter64;
                                    units "bytes";
                                    description "Indicates the total number of bytes received for this class that were forwarded.";
                                }

                                leaf incomplete-counts {
                                    type boolean;
                                    description "Indicates if the counts are incomplete.";
                                }

                            } // list source-class

                            list destination-class {
                                key "index";
                                description "Enter the destination-class list instance";

                                leaf index {
                                    type types-sros:class-index;
                                    description "Destination-class index";
                                }

                                leaf policer {
                                    type uint32 {
                                        range "1..63";
                                    }
                                    description "Indicates the policer associated with this destination class.";
                                }

                                leaf forwarded-packets {
                                    type yang:counter64;
                                    units "packets";
                                    description "Indicates the total number of packets received for this class that were forwarded.";
                                }

                                leaf forwarded-bytes {
                                    type yang:counter64;
                                    units "bytes";
                                    description "Indicates the total number of bytes received for this class that were forwarded.";
                                }

                                leaf incomplete-counts {
                                    type boolean;
                                    description "Indicates if the counts are incomplete.";
                                }

                            } // list destination-class

                            list policer {
                                key "index";
                                description "Enter the policer list instance";

                                leaf index {
                                    type uint32 {
                                        range "1..63";
                                    }
                                    description "Policer index";
                                }

                                leaf dropped-packets {
                                    type yang:counter64;
                                    units "packets";
                                    description "Indicates the total number of packets that were dropped by this policer.";
                                }

                                leaf dropped-bytes {
                                    type yang:counter64;
                                    units "bytes";
                                    description "Indicates the total number of bytes that were dropped by this policer.";
                                }

                                leaf forwarded-packets {
                                    type yang:counter64;
                                    units "packets";
                                    description "Indicates the total number of packets that were forwarded by this policer.";
                                }

                                leaf forwarded-bytes {
                                    type yang:counter64;
                                    units "bytes";
                                    description "Indicates the total number of bytes that were forwarded by this policer.";
                                }

                                leaf incomplete-counts {
                                    type boolean;
                                    description "Indicates if the counts are incomplete.";
                                }

                            } // list policer

                        } // container policy-accounting

                    } // container statistics

                } // container ingress

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description "Indicates the reason for why the interface is operationally down. Values: admin-disabled - Administratively disabled. service-admin-disabled - Assiocated service is administratively disabled. port-down - Associated SAP/port is operationally down. address-or-parent-not-ready - Associated address or parent interface is not ready. associated-object-not-ready - Associated object is not ready. rvpls-down - Associated R-VPLS service is operationally down. operational-group-down - Associated operational group is operationally down. admin-destroy - The interface is being destroyed. no-address - There is no address configured. no-info - The interface info is not present. hold-down-timer-running - The hold down timer is running. protocol-down - The protocols are operationally down. invalid-port-configuration - Invalid port configuration. unknown - The interface is operationally down due to some unknown reason. no-route-distinguisher - No route-distinguisher configured in the VRF. wlan-gateway-redundancy-standby - The interface is in standby state for WLAN-GW redundancy. wlan-gateway-group-degraded - The interface associated WLAN-GW group is in a degraded state. ip-control-tunnel-down - The IP tunnel associated to a control-tunnel interface is operationally down. pdn-address-mismatch - The IP address learned from the packet data network does not match the configured primary IP address. ping-check-failure - The IP interface is or went down because of a ping-template failure. port-internal-loopback - The IP interface is bound to a port that has an internal loopback configured.";
                    }

                    container icmp {
                        description "Enter the icmp context";

                        container statistics {
                            description "Enter the statistics context";

                            leaf icmp-in-msgs {
                                type yang:counter32;
                                description "Total Number of ICMPv4 messages received by this interface. This includes all those counted by icmp-in-errors. Note that this interface is the interface to which the ICMPv4 messages were addressed which may not be necessarily the input interface for the messages.";
                            }

                            leaf icmp-in-errors {
                                type yang:counter32;
                                description "Number of ICMPv4 errored messages received by this interface. This implies ICMPv4 messages determined as having specific ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description "Total number of ICMPv4 messages this interface attempted to send. This includes all those counted by icmp-out-errors.";
                            }

                            leaf icmp-out-errors {
                                type yang:counter32;
                                description "Number of ICMPv4 messages this interface could not be send due to problems discovered within ICMPv4 such as lack of buffers. This value should not include errors discovered outside the ICMPv4 layer such as the inability of VRtr IPv4 to route the resultant datagram. In some implementations there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                    container arp-host {
                        description "Enter the arp-host context";

                        container statistics {
                            description "Enter the statistics context";

                            leaf hosts {
                                type uint32;
                                description "The number of ARP hosts on this interface.";
                            }

                        } // container statistics

                    } // container arp-host

                    container neighbor-discovery {
                        description "Enter the neighbor-discovery context";

                        list neighbor {
                            key "ipv4-address";
                            description "Enter the neighbor list instance";

                            leaf ipv4-address {
                                type types-sros:ipv4-address;
                                description "IPv4 address that corresponds to the physical address";
                            }

                            leaf oper-state {
                                type types-sros:oper-state;
                                description "Indicates if the ARP entry is being used actively in the ARP table.";
                            }

                            leaf port {
                                type types-sros:port;
                                description "The ID of the port on which this entry was learned.";
                            }

                            leaf encap {
                                type types-sros:encap-val;
                                description "The encap value of the SAP this entry was learned on. If this entry was learned on a network port or null-encap SAP, the value of this object will be zero.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description "Indicates how much longer an ARP entry remains in the ARP cache. When timer has a value of zero, the entry is cleared from the cache.";
                            }

                        } // list neighbor

                    } // container neighbor-discovery

                    container dhcp {
                        description "Enter the dhcp context";

                        container lease-populate {
                            description "Enter the lease-populate context";

                            leaf current-lease-states {
                                type uint32 {
                                    range "0..511999";
                                }
                                description "The number of DHCP lease states currently allocated on this interface.";
                            }

                        } // container lease-populate

                        container statistics {
                            description "Enter the statistics context";

                            container total-rx-packets {
                                description "Enter the total-rx-packets context";

                                leaf received {
                                    type yang:counter32;
                                    description "The total number of packets received by the DHCP relay agent.";
                                }

                                leaf malformed {
                                    type yang:counter32;
                                    description "The total number of malformed packets received by the DHCP relay agent.";
                                }

                                leaf untrusted {
                                    type yang:counter32;
                                    description "The total number of untrusted packets received by the DHCP relay agent.";
                                }

                            } // container total-rx-packets

                            container total-tx-packets {
                                description "Enter the total-tx-packets context";

                                leaf transmitted {
                                    type yang:counter32;
                                    description "The total number of packets transmitted by the DHCP relay agent.";
                                }

                            } // container total-tx-packets

                            container client-packets {
                                description "Enter the client-packets context";

                                leaf dropped {
                                    type yang:counter32;
                                    description "The total number of client packets dropped by the DHCP relay agent.";
                                }

                                leaf relayed {
                                    type yang:counter32;
                                    description "The total number of client packets relayed by the DHCP relay agent.";
                                }

                                leaf snooped {
                                    type yang:counter32;
                                    description "The total number of client packets snooped by the DHCP relay agent.";
                                }

                                leaf streamed {
                                    type yang:counter32;
                                    description "The total number of received client packets scheduled for streaming to an external server, by the DHCP proxy function.";
                                }

                                container proxied {
                                    description "Enter the proxied context";

                                    leaf radius {
                                        type yang:counter32;
                                        description "The total number of client packets proxied by the DHCP relay agent based on data received from a RADIUS server.";
                                    }

                                    leaf lease-split {
                                        type yang:counter32;
                                        description "The total number of DHCP lease-split. Lease-split allows the DHCP relay agent to assigning a shorter lease time than the actual lease time assigned by the DHCP server. This allows the system to remove disconnected client quickly but ensure that client's shorter DHCP renewal are process by the relay agent and not the DHCP server.";
                                    }

                                    leaf nasreq {
                                        type yang:counter32;
                                        description "The total number of client packets proxied by the DHCP relay agent based on data received from a Diameter NASREQ server.";
                                    }

                                    leaf user-db {
                                        type yang:counter32;
                                        description "The total number of client packets proxied by the DHCP relay agent based on the local user database.";
                                    }

                                } // container proxied

                            } // container client-packets

                            container server-packets {
                                description "Enter the server-packets context";

                                leaf dropped {
                                    type yang:counter32;
                                    description "The total number of server packets dropped by the DHCP relay agent.";
                                }

                                leaf relayed {
                                    type yang:counter32;
                                    description "The total number of server packets relayed by the DHCP relay agent.";
                                }

                                leaf snooped {
                                    type yang:counter32;
                                    description "The total number of server packets snooped by the DHCP relay agent.";
                                }

                            } // container server-packets

                            container spoofed-packets {
                                description "Enter the spoofed-packets context";

                                leaf release {
                                    type yang:counter32;
                                    description "The total number of DHCP RELEASE messages spoofed by the DHCP relay agent to the DHCP server.";
                                }

                                leaf force-renews {
                                    type yang:counter32;
                                    description "The total number of DHCP FORCERENEW messages spoofed by the DHCP relay agent to the DHCP clients.";
                                }

                            } // container spoofed-packets

                        } // container statistics

                    } // container dhcp

                } // container ipv4

                container ipv6 {
                    description "Enter the ipv6 context";

                    leaf oper-state {
                        type types-sros:oper-state;
                        description "The current IPv6 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description "Indicates the reason for why the interface is operationally down. Values: admin-disabled - Administratively disabled. service-admin-disabled - Assiocated service is administratively disabled. port-down - Associated SAP/port is operationally down. address-or-parent-not-ready - Associated address or parent interface is not ready. associated-object-not-ready - Associated object is not ready. rvpls-down - Associated R-VPLS service is operationally down. operational-group-down - Associated operational group is operationally down. admin-destroy - The interface is being destroyed. no-address - There is no address configured. no-info - The interface info is not present. hold-down-timer-running - The hold down timer is running. protocol-down - The protocols are operationally down. invalid-port-configuration - Invalid port configuration. unknown - The interface is operationally down due to some unknown reason. no-route-distinguisher - No route-distinguisher configured in the VRF. wlan-gateway-redundancy-standby - The interface is in standby state for WLAN-GW redundancy. wlan-gateway-group-degraded - The interface associated WLAN-GW group is in a degraded state. ip-control-tunnel-down - The IP tunnel associated to a control-tunnel interface is operationally down. pdn-address-mismatch - The IP address learned from the packet data network does not match the configured primary IP address. ping-check-failure - The IP interface is or went down because of a ping-template failure. port-internal-loopback - The IP interface is bound to a port that has an internal loopback configured.";
                    }

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        container hosts {
                            description "Enter the hosts context";

                            leaf ipoe-dhcp6 {
                                type yang:gauge32;
                                description "The number of IPoE DHCPv6 hosts.";
                            }

                            leaf ipoe-slaac {
                                type yang:gauge32;
                                description "The number of IPoE SLAAC hosts.";
                            }

                            leaf ppp-dhcp6 {
                                type yang:gauge32;
                                description "The number of PPP DHCPv6 hosts.";
                            }

                            leaf ppp-slaac {
                                type yang:gauge32;
                                description "The number of PPP SLAAC hosts.";
                            }

                            leaf static-enabled {
                                type yang:gauge32;
                                description "The number of IPv6 static IPoE hosts that are enabled.";
                            }

                        } // container hosts

                    } // container statistics

                    container dhcp6 {
                        description "Enter the dhcp6 context";

                        container proxy-server {
                            description "Enter the proxy-server context";

                            container server-id {
                                description "Enter the server-id context";

                                leaf duid-en-number {
                                    type uint32;
                                    description "The vendor's registered Private Enterprise Number maintained by IANA.";
                                }

                            } // container server-id

                        } // container proxy-server

                    } // container dhcp6

                    container neighbor-discovery {
                        description "Enter the neighbor-discovery context";

                        list neighbor {
                            key "ipv6-address";
                            description "Enter the neighbor list instance";

                            leaf ipv6-address {
                                type types-sros:ipv6-address;
                                description "IPv6 address corresponding to the physical address";
                            }

                            leaf state {
                                type enumeration {
                                    enum "incomplete"                   { value 0; }
                                    enum "reachable"                    { value 1; }
                                    enum "stale"                        { value 2; }
                                    enum "delay"                        { value 3; }
                                    enum "probe"                        { value 4; }
                                }
                                description "The Neighbor Unreachability Detection state for the interface when the address mapping is used.";
                            }

                            leaf is-router {
                                type boolean;
                                description "Indicates whether this entry is a router.";
                            }

                            leaf secure-nd {
                                type enumeration {
                                    enum "not-applicable"               { value 0; }
                                    enum "secure"                       { value 1; }
                                    enum "unsecure"                     { value 2; }
                                }
                                description "Indicates whether the physical address is received via Secured Neighbor Discovery messages.";
                            }

                            leaf mtu {
                                type uint32;
                                description "The MTU of the link attached to this entry.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description "Indicates how much longer an ARP entry remains in the ARP cache. When timer has a value of zero, the entry is cleared from the cache.";
                            }

                        } // list neighbor

                    } // container neighbor-discovery

                } // container ipv6

                list srrp {
                    key "srrp-id";
                    description "Enter the srrp list instance";

                    leaf srrp-id {
                        type uint32 {
                            range "1..4294967295";
                        }
                        description "SRRP instance ID";
                    }

                    leaf oper-gw-mac {
                        type yang:mac-address;
                        description "The operational MAC address of the gateway.";
                    }

                    leaf in-use-priority {
                        type uint32 {
                            range "0..255";
                        }
                        description "The current in-use priority associated with the SRRP instance.";
                    }

                    leaf master-priority {
                        type uint32 {
                            range "0..255";
                        }
                        description "The piority of the SRRP instance which is the current master";
                    }

                    leaf oper-state {
                        type enumeration {
                            enum "disabled"                     { value 0; description "The SRRP instance is administratively down."; }
                            enum "initialize"                   { value 1; description "The SRRP instance is operationally down
                            or is starting to discover its neighbor."; }
                            enum "backup-routing"               { value 2; description "The SRRP instance is in backup mode, but it is
                            still forwarding traffic. The MAC address used
                            to forward traffic is the native MAC address
                            of the interface SRRP is running on."; }
                            enum "backup-shunt"                 { value 3; description "The SRRP instance is in backup mode. Any traffic
                            it receives will be forwarded to the spoke-sdp
                            on the redundant interface tied to the group
                            interface this instance is running on."; }
                            enum "pending-routing"              { value 4; description "The SRRP instance is in backup mode. A transient
                            state when a master/pending-master is preempted
                            and before it is going to backup-routing state.
                            In this state, traffic destined to the SRRP
                            gateway mac address received from a group
                            interface will still be accepted and forwarded."; }
                            enum "pending-shunt"                { value 5; description "The SRRP instance is in backup mode. A transient
                            state when a master/pending-master is preempted
                            and before it is going to backup-shunt state.
                            In this state, traffic destined to the SRRP
                            gateway mac address received from a group
                            interface will still be accepted and forwarded."; }
                            enum "pending-master"               { value 6; description "The SRRP instance is in master mode. All traffic
                            is forwarded using the native MAC address of the
                            interface SRRP is running on."; }
                            enum "master"                       { value 7; description "The SRRP instance is in master mode. All traffic
                            is forwarded using the gateway MAC address of
                            this SRRP instance."; }
                        }
                        description "The current operational state of the SRRP instance. Setting the `admin-state' object initiates transitions in the value of this object.";
                    }

                    leaf master-since {
                        type yang:date-and-time;
                        description "In case of a SRRP instance which is the current master, this is the sysUpTime when operational state (oper-state) of the SRRP instance changed to master. In case of a backup SRRP instance, this value specifies the sysUpTime when it received the first SRRP advertisement message from the srrp instance which is the current master.";
                    }

                    leaf oper-flags {
                        type bits {
                            bit subnet-mismatch                { position 0; }
                            bit srrp-id-mismatch               { position 1; }
                            bit sap-mismatch                   { position 2; }
                            bit sap-tag-mismatch               { position 3; }
                            bit redundant-interface-mismatch   { position 4; }
                            bit dual-master                    { position 5; }
                            bit duplicate-subscriber-interface-address { position 6; }
                            bit private-retail-mismatch        { position 7; }
                        }
                        description "The operating flags generated during SRRP operation.";
                    }

                    leaf master-down-interval {
                        type types-sros:time-duration;
                        units "milliseconds";
                        description "The time interval for the backup SRRP instance to declare the master as down.";
                    }

                    leaf master-down-timer {
                        type types-sros:time-duration;
                        units "milliseconds";
                        description "The current value of the Master Down Timer. When a backup SRRP instance receives a SRRP advertisement from a master, it resets this timer to the value of the Master Down Interval and begins to count down. If the backup SRRP instance does not receive an advertisement till this timer times out, it will assume that the master is down and will declare itself to be the master.";
                    }

                    leaf down-reason {
                        type enumeration {
                            enum "unknown"                      { value 0; }
                            enum "not-active"                   { value 1; }
                            enum "admin-down"                   { value 2; }
                            enum "if-down"                      { value 3; }
                            enum "no-link-lcl-addr-cfg"         { value 4; }
                            enum "rtr-adv-no-proper-cfg"        { value 5; }
                            enum "invalid-mac"                  { value 6; }
                        }
                        description "The reason for the operational state to be 'down'.";
                    }

                    container bfd-liveness {
                        description "Enter the bfd-liveness context";

                        leaf src-ip {
                            type types-sros:ip-address;
                            description "The value indicates the source IP address on the interface running BFD.";
                        }

                        leaf session-state {
                            type enumeration {
                                enum "unknown"                      { value 1; }
                                enum "connected"                    { value 2; }
                                enum "broken"                       { value 3; }
                                enum "peer-detects-down"            { value 4; }
                                enum "not-configured"               { value 5; }
                                enum "no-resources"                 { value 6; }
                            }
                            description "The value indicates the operational state of the BFD session the VRRP is relying upon for its fast triggering mechanism.";
                        }

                    } // container bfd-liveness

                    container statistics {
                        description "Enter the statistics context";

                        leaf become-master {
                            type yang:counter32;
                            description "The total number of times that the SRRP instance state has transitioned to MASTER.";
                        }

                        leaf master-changes {
                            type yang:counter32;
                            description "The total number of times that the SRRP instance has seen the master instance change.";
                        }

                        leaf advertisements-sent {
                            type yang:counter32;
                            description "The total number of SRRP advertisements sent by this SRRP instance.";
                        }

                        leaf advertisements-received {
                            type yang:counter32;
                            description "The total number of SRRP advertisements received by this SRRP instance.";
                        }

                        leaf zero-priority-packets-sent {
                            type yang:counter32;
                            description "The total number of SRRP packets sent by the SRRP instance with a priority of '0'.";
                        }

                        leaf zero-priority-packets-received {
                            type yang:counter32;
                            description "The total number of SRRP packets received by the SRRP instance with a priority of '0'.";
                        }

                        leaf preempt-events {
                            type yang:counter32;
                            description "The total number of times the SRRP instance has preempted another non-owner master with lower priority.";
                        }

                        leaf preempted-events {
                            type yang:counter32;
                            description "The total number of times the SRRP instance has been preempted by another non-owner master with higher priority.";
                        }

                        leaf advertisement-interval-discards {
                            type yang:counter32;
                            description "The total number of SRRP advertisement packets discarded because the advertisement interval in the received packet was different than the one configured for the SRRP instance.";
                        }

                        leaf advertisement-interval-errors {
                            type yang:counter32;
                            description "The total number of SRRP advertisement packets received for which the advertisement interval is different than the one configured for the local SRRP instance.";
                        }

                        leaf become-backup-routing {
                            type yang:counter32;
                            description "The total number of times that the SRRP instance state has transitioned to backup routing state.";
                        }

                        leaf become-backup-shunt {
                            type yang:counter32;
                            description "The total number of times that the SRRP instance state has transitioned to backup shunt.";
                        }

                        leaf become-non-master {
                            type yang:counter32;
                            description "The total number of times that the SRRP instance state has transitioned from master to a non-master state.";
                        }

                    } // container statistics

                } // list srrp

                container bonding-parameters {
                    description "Enter the bonding-parameters context";

                    leaf oper-state {
                        type types-sros:oper-state;
                        description "Operational state of ESM bonding.";
                    }

                } // container bonding-parameters

                container gtp-parameters {
                    description "Enter the gtp-parameters context";

                    leaf oper-state {
                        type types-sros:oper-state;
                        description "Operational state of this GTP Access.";
                    }

                } // container gtp-parameters

                list sap {
                    key "sap-id";
                    description "Enter the sap list instance";

                    leaf sap-id {
                        type types-sros:sap;
                        description "SAP ID";
                    }

                    leaf oper-state {
                        type enumeration {
                            enum "up"                           { value 1; }
                            enum "down"                         { value 2; }
                        }
                        description "Operating state of this SAP";
                    }

                    leaf mirror-state {
                        type enumeration {
                            enum "ingress"                      { value 1; }
                            enum "egress"                       { value 2; }
                            enum "ingress-and-egress"           { value 3; }
                            enum "disabled"                     { value 4; }
                        }
                        description "Indicates whether traffic mirroring has been enabled on this SAP";
                    }

                    leaf oper-flags {
                        type types-services:l3-sap-oper-flags;
                        description "Conditions that affect the operating status of this SAP.";
                    }

                    leaf template-used {
                        type types-sros:named-item-or-empty;
                        description "Name of the sap-template used to create this sap.";
                    }

                    leaf oper-dist-cpu-prot-policy {
                        type types-sros:named-item-or-empty;
                        description "Operational Distributed CPU Protection Policy.";
                    }

                    container statistics {
                        description "Enter the statistics context";

                        container authentication {
                            description "Enter the authentication context";

                            leaf discarded-packets {
                                type yang:counter32;
                                description "The number of DHCP packets discarded as result of authentication.";
                            }

                            leaf success-packets {
                                type yang:counter32;
                                description "The number of DHCP packets successfully authenticated.";
                            }

                        } // container authentication

                        container ipv4-hosts {
                            description "Enter the ipv4-hosts context";

                            leaf lease-allocations {
                                type yang:gauge32;
                                description "The number of DHCP lease states currently allocated on this SAP.";
                            }

                        } // container ipv4-hosts

                        container ipv6-hosts {
                            description "Enter the ipv6-hosts context";

                            leaf ipoe-dhcp6 {
                                type yang:gauge32;
                                description "The number of IPoE DHCPv6 hosts for this SAP.";
                            }

                            leaf ppp-dhcp6 {
                                type yang:gauge32;
                                description "The number of PPP DHCPv6 hosts for this SAP.";
                            }

                            leaf ppp-slaac {
                                type yang:gauge32;
                                description "The number of PPP SLAAC hosts for this SAP.";
                            }

                            leaf ipoe-slaac {
                                type yang:gauge32;
                                description "The number of IPoE SLAAC hosts for this SAP.";
                            }

                            leaf static-enabled {
                                type yang:gauge32;
                                description "The number of IPv6 static IPoE hosts for this SAP where the value of admin-status is equal to 'enable'.";
                            }

                        } // container ipv6-hosts

                    } // container statistics

                    container ingress {
                        description "Enter the ingress context";

                        container qos {
                            description "Enter the qos context";

                            container sap-ingress {
                                description "Enter the sap-ingress context";

                                container forwarding-engine {
                                    description "Enter the forwarding-engine context";

                                    container statistics {
                                        description "Enter the statistics context";

                                        leaf dropped-packets {
                                            type yang:counter64;
                                            description "The number of packets dropped by the ingress packet processor due to: SAP state, ingress MAC, IP or IPv6 filter, same segment discard, bad checksum, etc.";
                                        }

                                        leaf dropped-octets {
                                            type yang:counter64;
                                            description "The number of octets dropped by the ingress packet processor due to: SAP state, ingress MAC, IP or IPv6 filter, same segment discard, bad checksum, etc.";
                                        }

                                        leaf received-valid-packets {
                                            type yang:counter64;
                                            description "The value of received-valid indicates number of received valid packets, as determined by the SAP ingress QoS policy, offered by the packet processor to the traffic manager.";
                                        }

                                        leaf received-valid-octets {
                                            type yang:counter64;
                                            description "The value of received-valid indicates number of received valid octets, as determined by the SAP ingress QoS policy, offered by the packet processor to the traffic manager.";
                                        }

                                        leaf high-priority-offered-packets {
                                            type yang:counter64;
                                            description "The number of high priority packets, as determined by the SAP ingress QoS policy, offered by the packet processor to the traffic manager.";
                                        }

                                        leaf high-priority-offered-octets {
                                            type yang:counter64;
                                            description "The number of high priority octets, as determined by the SAP ingress QoS policy, offered by the packet processor to the traffic manager.";
                                        }

                                        leaf low-priority-offered-packets {
                                            type yang:counter64;
                                            description "The number of low priority packets, as determined by the SAP ingress QoS policy, offered by the packet processor to the traffic manager.";
                                        }

                                        leaf low-priority-offered-octets {
                                            type yang:counter64;
                                            description "The number of low priority octets, as determined by the SAP ingress QoS policy, offered by the packet processor to the traffic manager.";
                                        }

                                        leaf uncolor-offered-packets {
                                            type yang:counter64;
                                            description "The number of uncolored packets, as determined by the SAP ingress QoS policy, offered by the packet processor to the traffic manager.";
                                        }

                                        leaf uncolor-offered-octets {
                                            type yang:counter64;
                                            description "The number of uncolored octets, as determined by the SAP ingress QoS policy, offered by the packet processor to the traffic manager.";
                                        }

                                        leaf managed-offered-packets {
                                            type yang:counter64;
                                            description "The value of managed-offered indicates number of managed multicast packets, as determined by the SAP ingress QoS policy, offered by the packet processor to the traffic manager.";
                                        }

                                        leaf managed-offered-octets {
                                            type yang:counter64;
                                            description "The value of managed-offered indicates number of managed multicast octets, as determined by the SAP ingress QoS policy, offered by the packet processor to the traffic manager.";
                                        }

                                        leaf aggregate-offered-packets {
                                            type yang:counter64;
                                            description "The value of aggregate-offered indicates aggregate number of hi, lo priority and uncolour packets, as determined by the SAP ingress QoS policy, offered by the packet processor to the traffic manager.";
                                        }

                                        leaf aggregate-offered-octets {
                                            type yang:counter64;
                                            description "The value of managed-offered indicates aggregate number of hi, lo priority and uncolour octets, as determined by the SAP ingress QoS policy, offered by the packet processor to the traffic manager.";
                                        }

                                        leaf last-cleared-time {
                                            type yang:date-and-time;
                                            description "Time when the counters in this table were last cleared.";
                                        }

                                    } // container statistics

                                } // container forwarding-engine

                                container traffic-manager {
                                    description "Enter the traffic-manager context";

                                    container statistics {
                                        description "Enter the statistics context";

                                        leaf cpm-packets {
                                            type yang:counter64;
                                            description "The value of cpm-packets indicates ingress traffic in terms of packets destined to CPM associated with this SAP.";
                                        }

                                        leaf cpm-octets {
                                            type yang:counter64;
                                            description "The value of cpm indicates ingress traffic in terms of bytes destined to CPM associated with this SAP.";
                                        }

                                        leaf high-priority-dropped-packets {
                                            type yang:counter64;
                                            description "The number of high priority packets, as determined by the SAP ingress QoS policy, dropped by the traffic manager due to: MBS exceeded, buffer pool limit exceeded, etc.";
                                        }

                                        leaf high-priority-dropped-octets {
                                            type yang:counter64;
                                            description "The number of high priority octets, as determined by the SAP ingress QoS policy, dropped by the traffic manager due to: MBS exceeded, buffer pool limit exceeded, etc.";
                                        }

                                        leaf low-priority-dropped-packets {
                                            type yang:counter64;
                                            description "The number of low priority packets, as determined by the SAP ingress QoS policy, dropped by the traffic manager due to: MBS exceeded, buffer pool limit exceeded, etc.";
                                        }

                                        leaf low-priority-dropped-octets {
                                            type yang:counter64;
                                            description "The number of low priority octets, as determined by the SAP ingress QoS policy, dropped by the traffic manager due to: MBS exceeded, buffer pool limit exceeded, etc.";
                                        }

                                        leaf in-profile-forwarded-packets {
                                            type yang:counter64;
                                            description "The number of in-profile packets (rate below CIR) forwarded by the ingress traffic manager.";
                                        }

                                        leaf in-profile-forwarded-octets {
                                            type yang:counter64;
                                            description "The number of in-profile octets (rate below CIR) forwarded by the ingress traffic manager.";
                                        }

                                        leaf out-profile-forwarded-packets {
                                            type yang:counter64;
                                            description "The number of out-of-profile packets (rate above CIR) forwarded by the ingress traffic manager.";
                                        }

                                        leaf out-profile-forwarded-octets {
                                            type yang:counter64;
                                            description "The number of out-of-profile octets (rate above CIR) forwarded by the ingress traffic manager.";
                                        }

                                        leaf aggregate-forwarded-packets {
                                            type yang:counter64;
                                            description "The aggregate number of in and out-of profile packets forwarded by the ingress traffic manager.";
                                        }

                                        leaf aggregate-forwarded-octets {
                                            type yang:counter64;
                                            description "The aggregate number of in and out-of-profile octets forwarded by the ingress traffic manager.";
                                        }

                                        leaf aggregate-dropped-packets {
                                            type yang:counter64;
                                            description "The aggregate number of in and out-of profile packets, dropped by the traffic manager due to: MBS exceeded, buffer pool limit exceeded, etc.";
                                        }

                                        leaf aggregate-dropped-octets {
                                            type yang:counter64;
                                            description "The aggregate number of in and out-of profile octets, dropped by the traffic manager due to: MBS exceeded, buffer pool limit exceeded, etc.";
                                        }

                                        leaf last-cleared-time {
                                            type yang:date-and-time;
                                            description "Time when the counters in this table were last cleared.";
                                        }

                                    } // container statistics

                                } // container traffic-manager

                                list queue {
                                    key "queue-id";
                                    description "Enter the queue list instance";

                                    leaf queue-id {
                                        type types-qos:ingress-queue-id;
                                        description "The unique identifier for the queue.";
                                    }

                                    container statistics {
                                        description "Enter the statistics context";

                                        choice stat-mode {
                                            case unicast-priority {

                                                container unicast-priority {
                                                    description "Enter the unicast-priority context";

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-priority

                                            }
                                            case unicast-profile {

                                                container unicast-profile {
                                                    description "Enter the unicast-profile context";

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf color-offered-packets {
                                                        type yang:counter64;
                                                        description "The number of color packets offered to traffic manager.";
                                                    }

                                                    leaf color-offered-octets {
                                                        type yang:counter64;
                                                        description "The number of color octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-profile

                                            }
                                            case multipoint-priority {

                                                container multipoint-priority {
                                                    description "Enter the multipoint-priority context";

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf combined-offered-packets {
                                                        type yang:counter64;
                                                        description "The number of combined high and low priority packets offered by packet processor to traffic manager.";
                                                    }

                                                    leaf combined-offered-octets {
                                                        type yang:counter64;
                                                        description "The number of combined high and low priority octets offered by packet processor to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-priority

                                            }
                                            case multipoint-profile {

                                                container multipoint-profile {
                                                    description "Enter the multipoint-profile context";

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf combined-offered-packets {
                                                        type yang:counter64;
                                                        description "The number of combined colored in, out and uncolored packets offered to traffic manager.";
                                                    }

                                                    leaf combined-offered-octets {
                                                        type yang:counter64;
                                                        description "The number of combined colored in, out and uncolored octets offered to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-profile

                                            }
                                            case v4-v6 {

                                                container v4-v6 {
                                                    description "Enter the v4-v6 context";

                                                    leaf ipv4-offered-packets {
                                                        type yang:counter64;
                                                        description "The number of ipv4 packets offered by packet processor to traffic manager.";
                                                    }

                                                    leaf ipv4-offered-octets {
                                                        type yang:counter64;
                                                        description "The number of ipv4 octets offered by packet processor to traffic manager.";
                                                    }

                                                    leaf ipv6-offered-packets {
                                                        type yang:counter64;
                                                        description "The number of ipv6 packets offered by packet processor to traffic manager.";
                                                    }

                                                    leaf ipv6-offered-octets {
                                                        type yang:counter64;
                                                        description "The number of ipv6 octets offered by packet processor to traffic manager.";
                                                    }

                                                    leaf ipv4-dropped-packets {
                                                        type yang:counter64;
                                                        description "The number of ipv4 packets dropped by packet processor to traffic manager.";
                                                    }

                                                    leaf ipv4-dropped-octets {
                                                        type yang:counter64;
                                                        description "The number of ipv4 octets dropped by packet processor to traffic manager.";
                                                    }

                                                    leaf ipv6-dropped-packets {
                                                        type yang:counter64;
                                                        description "The number of ipv6 packets dropped by packet processor to traffic manager.";
                                                    }

                                                    leaf ipv6-dropped-octets {
                                                        type yang:counter64;
                                                        description "The number of ipv6 octets dropped by packet processor to traffic manager.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                    list hardware-queue {
                                        key "source-card source-fp source-tap-offset source-port dest-card dest-fp dest-tap-offset";
                                        description "Enter the hardware-queue list instance";

                                        leaf source-card {
                                            type int32;
                                            description "Card number";
                                        }

                                        leaf source-fp {
                                            type int32;
                                            description "FP number";
                                        }

                                        leaf source-tap-offset {
                                            type int32;
                                            description "Source TAP.";
                                        }

                                        leaf source-port {
                                            type types-sros:port;
                                            description "Port identifier";
                                        }

                                        leaf dest-card {
                                            type int32;
                                            description "Card number";
                                        }

                                        leaf dest-fp {
                                            type int32;
                                            description "Destination FP.";
                                        }

                                        leaf dest-tap-offset {
                                            type int32;
                                            description "Destination TAP.";
                                        }

                                        leaf adapted-admin-mbs {
                                            type int64;
                                            units "bytes";
                                            description "Admin MBS.";
                                        }

                                        leaf adapted-admin-cbs {
                                            type types-qos:bytes;
                                            units "bytes";
                                            description "Admin CBS.";
                                        }

                                        leaf operational-mbs {
                                            type int64;
                                            units "bytes";
                                            description "Oper MBS.";
                                        }

                                        leaf depth {
                                            type union {
                                                type enumeration {
                                                    enum "max"                          { value -1; }
                                                }
                                                type int64;
                                            }
                                            description "Depth CIR.";
                                        }

                                        leaf operational-cir {
                                            type union {
                                                type enumeration {
                                                    enum "max"                          { value -1; }
                                                }
                                                type int64;
                                            }
                                            description "Oper CIR.";
                                        }

                                        leaf operational-fir {
                                            type union {
                                                type enumeration {
                                                    enum "max"                          { value -1; }
                                                }
                                                type int64;
                                            }
                                            description "Oper FIR.";
                                        }

                                        leaf operational-pir {
                                            type union {
                                                type enumeration {
                                                    enum "max"                          { value -1; }
                                                }
                                                type int64;
                                            }
                                            description "Oper PIR.";
                                        }

                                        leaf exceed-droptail {
                                            type union {
                                                type int64 {
                                                    range "0..max";
                                                }
                                                type enumeration {
                                                    enum "auto"                         { value -1; }
                                                }
                                            }
                                            description "Exceed droptail.";
                                        }

                                        leaf high-droptail {
                                            type union {
                                                type int64 {
                                                    range "0..max";
                                                }
                                                type enumeration {
                                                    enum "auto"                         { value -1; }
                                                }
                                            }
                                            description "High droptail.";
                                        }

                                        leaf high-plus-droptail {
                                            type union {
                                                type int64 {
                                                    range "0..max";
                                                }
                                                type enumeration {
                                                    enum "auto"                         { value -1; }
                                                }
                                            }
                                            description "Highplus droptail.";
                                        }

                                        leaf low-droptail {
                                            type union {
                                                type int64 {
                                                    range "0..max";
                                                }
                                                type enumeration {
                                                    enum "auto"                         { value -1; }
                                                }
                                            }
                                            description "Low droptail.";
                                        }

                                    } // list hardware-queue

                                } // list queue

                                list policer {
                                    key "policer-id";
                                    description "Enter the policer list instance";

                                    leaf policer-id {
                                        type types-qos:ingress-policer-id;
                                        description "The unique identifier for the policer.";
                                    }

                                    container statistics {
                                        description "Enter the statistics context";

                                        choice stat-mode {
                                            case minimal {

                                                container minimal {
                                                    description "Enter the minimal context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {
                                                    description "Enter the offered-profile-no-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-priority-no-cir {

                                                container offered-priority-no-cir {
                                                    description "Enter the offered-priority-no-cir context";

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf high-priority-dropped-packets {
                                                        type yang:counter64;
                                                        description "The number of high-priority packets dropped by the packet processor to traffic manager";
                                                    }

                                                    leaf high-priority-dropped-octets {
                                                        type yang:counter64;
                                                        description "The number of high-priority octets dropped by the packet processor to traffic manager";
                                                    }

                                                    leaf low-priority-dropped-packets {
                                                        type yang:counter64;
                                                        description "The number of low-priority packets dropped by the packet processor to traffic manager";
                                                    }

                                                    leaf low-priority-dropped-octets {
                                                        type yang:counter64;
                                                        description "The number of low-priority octets dropped by the packet processor to traffic manager";
                                                    }

                                                    leaf high-priority-forwarded-packets {
                                                        type yang:counter64;
                                                        description "The number of high-priority packets forwarded by the packet processor to traffic manager";
                                                    }

                                                    leaf high-priority-forwarded-octets {
                                                        type yang:counter64;
                                                        description "The number of high-priority octets forwarded by the packet processor to traffic manager";
                                                    }

                                                    leaf low-priority-forwarded-packets {
                                                        type yang:counter64;
                                                        description "The number of low-priority packets forwarded by the packet processor to traffic manager";
                                                    }

                                                    leaf low-priority-forwarded-octets {
                                                        type yang:counter64;
                                                        description "The number of low-priority octets forwarded by the packet processor to traffic manager";
                                                    }

                                                } // container offered-priority-no-cir

                                            }
                                            case offered-profile-cir {

                                                container offered-profile-cir {
                                                    description "Enter the offered-profile-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-priority-cir {

                                                container offered-priority-cir {
                                                    description "Enter the offered-priority-cir context";

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-priority-cir

                                            }
                                            case offered-total-cir {

                                                container offered-total-cir {
                                                    description "Enter the offered-total-cir context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-profile-cir {

                                                container offered-limited-profile-cir {
                                                    description "Enter the offered-limited-profile-cir context";

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-limited-profile-cir

                                            }
                                            case offered-profile-capped-cir {

                                                container offered-profile-capped-cir {
                                                    description "Enter the offered-profile-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-profile-with-discards {

                                                container offered-profile-with-discards {
                                                    description "Enter the offered-profile-with-discards context";

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-profile packets forwarded by the packet processor to traffic manager";
                                                    }

                                                    leaf out-profile-forwarded-octets {
                                                        type yang:counter64;
                                                        description "The number of out-profile octets forwarded by the packet processor to traffic manager";
                                                    }

                                                    leaf dropped-exceed-profile-packets {
                                                        type yang:counter64;
                                                        description "The number of dropped-exceed-profile packets by the packet processor to traffic manager";
                                                    }

                                                    leaf dropped-exceed-profile-octets {
                                                        type yang:counter64;
                                                        description "The number of dropped-exceed-profile octets by the packet processor to traffic manager";
                                                    }

                                                } // container offered-profile-with-discards

                                            }
                                            case offered-limited-capped-cir {

                                                container offered-limited-capped-cir {
                                                    description "Enter the offered-limited-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf uncolor-offered-packets {
                                                        type yang:counter64;
                                                        description "The number of out-of-rofile packets offered by the packet processor to traffic manager";
                                                    }

                                                    leaf uncolor-offered-octets {
                                                        type yang:counter64;
                                                        description "The number of out-of-profile octets offered by the packet processor to traffic manager";
                                                    }

                                                } // container offered-limited-capped-cir

                                            }
                                            case v4-v6 {

                                                container v4-v6 {
                                                    description "Enter the v4-v6 context";

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                        }
                                    } // container statistics

                                    list hardware-policer {
                                        key "hardware-policer-string";
                                        description "Enter the hardware-policer list instance";

                                        leaf hardware-policer-string {
                                            type types-sros:named-item-255;
                                            description "Name of the policer formatted by IOM.";
                                        }

                                        leaf adapted-admin-cbs {
                                            type int64;
                                            units "bytes";
                                            description "Admin CBS.";
                                        }

                                        leaf adapted-admin-mbs {
                                            type int64;
                                            units "bytes";
                                            description "Admin MBS.";
                                        }

                                        leaf adapted-hp-only {
                                            type int64;
                                            units "bytes";
                                            description "Hi Prio Only.";
                                        }

                                        leaf depth {
                                            type int64;
                                            units "bytes";
                                            description "Depth.";
                                        }

                                        leaf operational-cir {
                                            type union {
                                                type enumeration {
                                                    enum "max"                          { value -1; }
                                                }
                                                type int64;
                                            }
                                            description "Oper CIR.";
                                        }

                                        leaf operational-fir {
                                            type union {
                                                type enumeration {
                                                    enum "max"                          { value -1; }
                                                }
                                                type int64;
                                            }
                                            description "Oper FIR.";
                                        }

                                        leaf operational-pir {
                                            type union {
                                                type enumeration {
                                                    enum "max"                          { value -1; }
                                                }
                                                type int64;
                                            }
                                            description "Oper PIR.";
                                        }

                                    } // list hardware-policer

                                } // list policer

                            } // container sap-ingress

                            container policer-control-policy {
                                description "Enter the policer-control-policy context";

                                list arbiter {
                                    key "arbiter-name";
                                    description "Enter the arbiter list instance";

                                    leaf arbiter-name {
                                        type types-sros:named-item;
                                        description "Specifies the arbiter name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list arbiter

                            } // container policer-control-policy

                            container scheduler-policy {
                                description "Enter the scheduler-policy context";

                                list scheduler {
                                    key "scheduler-name";
                                    description "Enter the scheduler list instance";

                                    leaf scheduler-name {
                                        type types-sros:named-item;
                                        description "Specifies the scheduler name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list scheduler

                            } // container scheduler-policy

                        } // container qos

                    } // container ingress

                    container egress {
                        description "Enter the egress context";

                        container qos {
                            description "Enter the qos context";

                            container sap-egress {
                                description "Enter the sap-egress context";

                                container traffic-manager {
                                    description "Enter the traffic-manager context";

                                    container statistics {
                                        description "Enter the statistics context";

                                        leaf in-inplus-profile-dropped-packets {
                                            type yang:counter64;
                                            description "The number of in-profile packets discarded by the egress traffic manager due to: MBS exceeded, buffer pool limit exceeded, etc.";
                                        }

                                        leaf in-inplus-profile-dropped-octets {
                                            type yang:counter64;
                                            description "The number of in-profile octets discarded by the egress traffic manager due to: MBS exceeded, buffer pool limit exceeded, etc.";
                                        }

                                        leaf out-exceed-profile-dropped-packets {
                                            type yang:counter64;
                                            description "The number of out-of-profile packets discarded by the egress traffic manager due to: MBS exceeded, buffer pool limit exceeded, etc.";
                                        }

                                        leaf out-exceed-profile-dropped-octets {
                                            type yang:counter64;
                                            description "The number of out-of-profile packets discarded by the egress traffic manager due to: MBS exceeded, buffer pool limit exceeded, etc.";
                                        }

                                        leaf in-inplus-profile-forwarded-packets {
                                            type yang:counter64;
                                            description "The number of in-profile packets (rate below CIR) forwarded by the egress traffic manager.";
                                        }

                                        leaf in-inplus-profile-forwarded-octets {
                                            type yang:counter64;
                                            description "The number of in-profile octets (rate below CIR) forwarded by the egress traffic manager.";
                                        }

                                        leaf out-exceed-profile-forwarded-packets {
                                            type yang:counter64;
                                            description "The number of out-of-profile packets (rate above CIR) forwarded by the egress traffic manager.";
                                        }

                                        leaf out-exceed-profile-forwarded-octets {
                                            type yang:counter64;
                                            description "The number of out-of-profile octets (rate above CIR) forwarded by the egress traffic manager.";
                                        }

                                        leaf aggregate-forwarded-packets {
                                            type yang:counter64;
                                            description "The aggregate number of in and out-of profile packets forwarded by the egress traffic manager.";
                                        }

                                        leaf aggregate-forwarded-octets {
                                            type yang:counter64;
                                            description "The aggregate number of in and out-of profile octets forwarded by the egress traffic manager.";
                                        }

                                        leaf aggregate-dropped-packets {
                                            type yang:counter64;
                                            description "The aggregate number of in and out-of profile packets discarded by the egress traffic manager due to: MBS exceeded, buffer pool limit exceeded, etc.";
                                        }

                                        leaf aggregate-dropped-octets {
                                            type yang:counter64;
                                            description "The aggregate number of in and out-of profile octets discarded by the egress traffic manager due to: MBS exceeded, buffer pool limit exceeded, etc.";
                                        }

                                        leaf last-cleared-time {
                                            type yang:date-and-time;
                                            description "Time when the counters in this table were last cleared.";
                                        }

                                    } // container statistics

                                } // container traffic-manager

                                list queue {
                                    key "queue-id";
                                    description "Enter the queue list instance";

                                    leaf queue-id {
                                        type types-qos:egress-queue-id;
                                        description "The unique identifier for the queue.";
                                    }

                                    container statistics {
                                        description "Enter the statistics context";

                                        choice stat-mode {
                                            case profile {

                                                container profile {
                                                    description "Enter the profile context";

                                                    leaf in-inplus-profile-forwarded-packets {
                                                        type yang:counter64;
                                                        description "The number of in-profile/in-plus-profile packets (rate below CIR) forwarded.";
                                                    }

                                                    leaf in-inplus-profile-forwarded-octets {
                                                        type yang:counter64;
                                                        description "The number of in-profile/in-plus-profile octets (rate below CIR) forwarded.";
                                                    }

                                                    leaf out-exceed-profile-forwarded-packets {
                                                        type yang:counter64;
                                                        description "The number of out-profile/exceed-profile packets (rate above CIR) forwarded.";
                                                    }

                                                    leaf out-exceed-profile-forwarded-octets {
                                                        type yang:counter64;
                                                        description "The number of out-profile/exceed-profile octets (rate above CIR) forwarded.";
                                                    }

                                                    leaf in-inplus-profile-dropped-packets {
                                                        type yang:counter64;
                                                        description "The number of in-profile/in-plus-profile packets discarded.";
                                                    }

                                                    leaf in-inplus-profile-dropped-octets {
                                                        type yang:counter64;
                                                        description "The number of in-profile/in-plus-profile octets discarded.";
                                                    }

                                                    leaf out-exceed-profile-dropped-packets {
                                                        type yang:counter64;
                                                        description "The number of out-profile/exceed-profile packets discarded.";
                                                    }

                                                    leaf out-exceed-profile-dropped-octets {
                                                        type yang:counter64;
                                                        description "The number of out-profile/exceed-profile octets discarded.";
                                                    }

                                                } // container profile

                                            }
                                            case v4-v6 {

                                                container v4-v6 {
                                                    description "Enter the v4-v6 context";

                                                    leaf ipv4-dropped-packets {
                                                        type yang:counter64;
                                                        description "The number of ipv4 packets discarded.";
                                                    }

                                                    leaf ipv4-dropped-octets {
                                                        type yang:counter64;
                                                        description "The number of ipv4 octets discarded.";
                                                    }

                                                    leaf ipv6-dropped-packets {
                                                        type yang:counter64;
                                                        description "The number of ipv6 packets discarded.";
                                                    }

                                                    leaf ipv6-dropped-octets {
                                                        type yang:counter64;
                                                        description "The number of ipv6 octets discarded.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                    list hardware-queue {
                                        key "source-card source-fp source-port";
                                        description "Enter the hardware-queue list instance";

                                        leaf source-card {
                                            type int32;
                                            description "Card number";
                                        }

                                        leaf source-fp {
                                            type int32;
                                            description "FP number";
                                        }

                                        leaf source-port {
                                            type types-sros:port;
                                            description "Port identifier";
                                        }

                                        leaf adapted-admin-mbs {
                                            type types-qos:bytes;
                                            units "bytes";
                                            description "Admin MBS.";
                                        }

                                        leaf exceed-droptail {
                                            type union {
                                                type int64 {
                                                    range "0..max";
                                                }
                                                type enumeration {
                                                    enum "auto"                         { value -1; }
                                                }
                                            }
                                            description "Exceed droptail.";
                                        }

                                        leaf high-droptail {
                                            type union {
                                                type int64 {
                                                    range "0..max";
                                                }
                                                type enumeration {
                                                    enum "auto"                         { value -1; }
                                                }
                                            }
                                            description "High droptail.";
                                        }

                                        leaf high-plus-droptail {
                                            type union {
                                                type int64 {
                                                    range "0..max";
                                                }
                                                type enumeration {
                                                    enum "auto"                         { value -1; }
                                                }
                                            }
                                            description "Highplus droptail.";
                                        }

                                        leaf low-droptail {
                                            type union {
                                                type int64 {
                                                    range "0..max";
                                                }
                                                type enumeration {
                                                    enum "auto"                         { value -1; }
                                                }
                                            }
                                            description "Low droptail.";
                                        }

                                        leaf operational-cbs {
                                            type types-qos:bytes;
                                            units "bytes";
                                            description "Oper CBS.";
                                        }

                                        leaf operational-cir {
                                            type union {
                                                type enumeration {
                                                    enum "max"                          { value -1; }
                                                }
                                                type int64;
                                            }
                                            description "Oper CIR.";
                                        }

                                        leaf operational-mbs {
                                            type types-qos:bytes;
                                            units "bytes";
                                            description "Oper MBS.";
                                        }

                                        leaf operational-pir {
                                            type union {
                                                type enumeration {
                                                    enum "max"                          { value -1; }
                                                }
                                                type int64;
                                            }
                                            description "Oper PIR.";
                                        }

                                        leaf depth {
                                            type union {
                                                type enumeration {
                                                    enum "max"                          { value -1; }
                                                }
                                                type int64;
                                            }
                                            description "Depth CIR.";
                                        }

                                        container exceed-slope {
                                            description "Enter the exceed-slope context";

                                            leaf current-probability {
                                                type types-sros:percent;
                                                description "Specifies the current probability in percentage";
                                            }

                                        } // container exceed-slope

                                        container high-slope {
                                            description "Enter the high-slope context";

                                            leaf current-probability {
                                                type types-sros:percent;
                                                description "Specifies the current probability in percentage";
                                            }

                                        } // container high-slope

                                        container high-plus-slope {
                                            description "Enter the high-plus-slope context";

                                            leaf current-probability {
                                                type types-sros:percent;
                                                description "Specifies the current probability in percentage";
                                            }

                                        } // container high-plus-slope

                                        container low-slope {
                                            description "Enter the low-slope context";

                                            leaf current-probability {
                                                type types-sros:percent;
                                                description "Specifies the current probability in percentage";
                                            }

                                        } // container low-slope

                                    } // list hardware-queue

                                } // list queue

                                list policer {
                                    key "policer-id";
                                    description "Enter the policer list instance";

                                    leaf policer-id {
                                        type types-qos:sap-egress-policer-id;
                                        description "The unique identifier for the policer.";
                                    }

                                    container statistics {
                                        description "Enter the statistics context";

                                        choice stat-mode {
                                            case minimal {

                                                container minimal {
                                                    description "Enter the minimal context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {
                                                    description "Enter the offered-profile-no-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-profile-cir {

                                                container offered-profile-cir {
                                                    description "Enter the offered-profile-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-total-cir {

                                                container offered-total-cir {
                                                    description "Enter the offered-total-cir context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-capped-cir {

                                                container offered-limited-capped-cir {
                                                    description "Enter the offered-limited-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf out-profile-offered-packets {
                                                        type yang:counter64;
                                                        description "The number of out-of-rofile packets offered by the packet processor to traffic manager";
                                                    }

                                                    leaf out-profile-offered-octets {
                                                        type yang:counter64;
                                                        description "The number of out-of-profile octets offered by the packet processor to traffic manager";
                                                    }

                                                } // container offered-limited-capped-cir

                                            }
                                            case offered-profile-capped-cir {

                                                container offered-profile-capped-cir {
                                                    description "Enter the offered-profile-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-total-cir-exceed {

                                                container offered-total-cir-exceed {
                                                    description "Enter the offered-total-cir-exceed context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-exceed

                                            }
                                            case offered-four-profile-no-cir {

                                                container offered-four-profile-no-cir {
                                                    description "Enter the offered-four-profile-no-cir context";

                                                    leaf inplus-profile-offered-packets {
                                                        type yang:counter64;
                                                        description "The number of inplus-profile packets offered by the packet processor to traffic manager";
                                                    }

                                                    leaf inplus-profile-offered-octets {
                                                        type yang:counter64;
                                                        description "The number of inplus-profile octets offered by the packet processor to traffic manager";
                                                    }

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf exceed-profile-offered-packets {
                                                        type yang:counter64;
                                                        description "The number of exceed-profile packets offered by the packet processor to traffic manager";
                                                    }

                                                    leaf exceed-profile-offered-octets {
                                                        type yang:counter64;
                                                        description "The number of exceed-profile octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-four-profile-no-cir

                                            }
                                            case offered-total-cir-four-profile {

                                                container offered-total-cir-four-profile {
                                                    description "Enter the offered-total-cir-four-profile context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-four-profile

                                            }
                                            case v4-v6 {

                                                container v4-v6 {
                                                    description "Enter the v4-v6 context";

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                            case bonding {

                                                container bonding {
                                                    description "Enter the bonding context";

                                                    leaf connection-1-offered-packets {
                                                        type yang:counter64;
                                                        description "The number of connection-1 packets offered by the packet processor to traffic manager";
                                                    }

                                                    leaf connection-1-offered-octets {
                                                        type yang:counter64;
                                                        description "The number of connection-1 octets offered by the packet processor to traffic manager";
                                                    }

                                                    leaf connection-2-offered-packets {
                                                        type yang:counter64;
                                                        description "The number of connection-2 packets offered by the packet processor to traffic manager";
                                                    }

                                                    leaf connection-2-offered-octets {
                                                        type yang:counter64;
                                                        description "The number of connection-2 octets offered by the packet processor to traffic manager";
                                                    }

                                                    leaf connection-1-dropped-packets {
                                                        type yang:counter64;
                                                        description "The number of connection-1 packets dropped by the packet processor to traffic manager";
                                                    }

                                                    leaf connection-1-dropped-octets {
                                                        type yang:counter64;
                                                        description "The number of connection-1 octets dropped by the packet processor to traffic manager";
                                                    }

                                                    leaf connection-2-dropped-packets {
                                                        type yang:counter64;
                                                        description "The number of connection-2 packets dropped by the packet processor to traffic manager";
                                                    }

                                                    leaf connection-2-dropped-octets {
                                                        type yang:counter64;
                                                        description "The number of connection-2 octets dropped by the packet processor to traffic manager";
                                                    }

                                                    leaf connection-1-forwarded-packets {
                                                        type yang:counter64;
                                                        description "The number of connection-1 packets forwarded by the packet processor to traffic manager";
                                                    }

                                                    leaf connection-1-forwarded-octets {
                                                        type yang:counter64;
                                                        description "The number of connection-1 octets forwarded by the packet processor to traffic manager";
                                                    }

                                                    leaf connection-2-forwarded-packets {
                                                        type yang:counter64;
                                                        description "The number of connection-2 packets forwarded by the packet processor to traffic manager";
                                                    }

                                                    leaf connection-2-forwarded-octets {
                                                        type yang:counter64;
                                                        description "The number of connection-2 octets forwarded by the packet processor to traffic manager";
                                                    }

                                                } // container bonding

                                            }
                                        }
                                    } // container statistics

                                    list hardware-policer {
                                        key "hardware-policer-string";
                                        description "Enter the hardware-policer list instance";

                                        leaf hardware-policer-string {
                                            type types-sros:named-item-255;
                                            description "Name of the policer formatted by IOM.";
                                        }

                                        leaf adapted-admin-cbs {
                                            type int64;
                                            units "bytes";
                                            description "Admin CBS.";
                                        }

                                        leaf adapted-admin-mbs {
                                            type int64;
                                            units "bytes";
                                            description "Admin MBS.";
                                        }

                                        leaf adapted-hp-only {
                                            type int64;
                                            units "bytes";
                                            description "Hi Prio Only.";
                                        }

                                        leaf depth {
                                            type int64;
                                            units "bytes";
                                            description "Depth.";
                                        }

                                        leaf operational-cir {
                                            type union {
                                                type enumeration {
                                                    enum "max"                          { value -1; }
                                                }
                                                type int64;
                                            }
                                            description "Oper CIR.";
                                        }

                                        leaf operational-fir {
                                            type union {
                                                type enumeration {
                                                    enum "max"                          { value -1; }
                                                }
                                                type int64;
                                            }
                                            description "Oper FIR.";
                                        }

                                        leaf operational-pir {
                                            type union {
                                                type enumeration {
                                                    enum "max"                          { value -1; }
                                                }
                                                type int64;
                                            }
                                            description "Oper PIR.";
                                        }

                                    } // list hardware-policer

                                } // list policer

                            } // container sap-egress

                            container policer-control-policy {
                                description "Enter the policer-control-policy context";

                                list arbiter {
                                    key "arbiter-name";
                                    description "Enter the arbiter list instance";

                                    leaf arbiter-name {
                                        type types-sros:named-item;
                                        description "Specifies the arbiter name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list arbiter

                            } // container policer-control-policy

                            container scheduler-policy {
                                description "Enter the scheduler-policy context";

                                list scheduler {
                                    key "scheduler-name";
                                    description "Enter the scheduler list instance";

                                    leaf scheduler-name {
                                        type types-sros:named-item;
                                        description "Specifies the scheduler name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list scheduler

                            } // container scheduler-policy

                        } // container qos

                    } // container egress

                    container lag {
                        description "Enter the lag context";

                        leaf active-port {
                            type types-sros:port;
                            description "Port on the lag associated with this SAP, that is used when lag-per-link-hash is enabled on the lag or when lag-link-map-profile is configured on this SAP.";
                        }

                        container per-link-hash-oper {
                            description "Enter the per-link-hash-oper context";

                            leaf class {
                                type int32;
                                description "Operational value for class associated with this SAP.";
                            }

                            leaf weight {
                                type int32;
                                description "Operational value used for weight associated with this SAP.";
                            }

                            leaf is-overriden {
                                type boolean;
                                description "Whether administrative values, subscriber management determined operational weight and class are used for this SAP.";
                            }

                        } // container per-link-hash-oper

                    } // container lag

                    container distributed-cpu-protection {
                        description "Enter the distributed-cpu-protection context";

                        list static-policer {
                            key "name card fp-number";
                            description "Enter the static-policer list instance";

                            leaf name {
                                type types-sros:named-item;
                                description "Name of static policer.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description "Number of packets exceeding the policing parameters since the given policer was previously declared as conformant or newly instantiated.";
                            }

                            leaf hold-down-remain {
                                type types-services:dist-cpu-prot-action-duration;
                                units "seconds";
                                description "Remaining hold-down period for a given policer.";
                            }

                            leaf detection-time-remain {
                                type uint32;
                                units "seconds";
                                description "Detection time remaining for a given policer.";
                            }

                        } // list static-policer

                        list local-monitor-policer {
                            key "name card fp-number";
                            description "Enter the local-monitor-policer list instance";

                            leaf name {
                                type types-sros:named-item;
                                description "Name of local-monitor policer.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description "Number of packets exceeding the policing parameters since the given policer was previously declared as conformant or newly instantiated.";
                            }

                            leaf all-dynamic-policer-allocation {
                                type boolean;
                                description "All dynamic-policers allocation status";
                            }

                        } // list local-monitor-policer

                        list dynamic-policer {
                            key "protocol card fp-number";
                            description "Enter the dynamic-policer list instance";

                            leaf protocol {
                                type types-sros:dist-cpu-protection-protocol;
                                description "Dynamic policer protocol.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description "Number of packets exceeding the policing parameters since the given policer was previously declared as conformant or newly instantiated.";
                            }

                            leaf hold-down-remain {
                                type types-services:dist-cpu-prot-action-duration;
                                units "seconds";
                                description "Remaining hold-down period for a given policer.";
                            }

                            leaf detection-time-remain {
                                type uint32;
                                units "seconds";
                                description "Detection time remaining for a given policer.";
                            }

                            leaf dynamic-policer-allocation {
                                type boolean;
                                description "Dynamic-policer allocation status";
                            }

                        } // list dynamic-policer

                    } // container distributed-cpu-protection

                    container eth-cfm {
                        description "Enter the eth-cfm context";

                        list mep {
                            key "md-admin-name ma-admin-name mep-id";
                            description "Enter the mep list instance";

                            leaf md-admin-name {
                                type leafref {
                                    path "../../../../../../../../eth-cfm/domain/md-admin-name";
                                }
                                description "Maintenance Domain (MD) name";
                            }

                            leaf ma-admin-name {
                                type leafref {
                                    path "../../../../../../../../eth-cfm/domain[md-admin-name=current()/../md-admin-name]/association/ma-admin-name";
                                }
                                description "Maintenance Association (MA) name";
                            }

                            leaf mep-id {
                                type types-eth-cfm:mep-id-type;
                                description "Maintenance Endpoint (MEP) ID";
                            }

                            leaf if-index {
                                type uint32;
                                description "Port ID of the MEP.";
                            }

                            leaf oper-mac-address {
                                type yang:mac-address;
                                description "Operational MAC address of the MEP.";
                            }

                            container csf {
                                description "Enter the csf context";

                                container received {
                                    description "Enter the received context";

                                    leaf state {
                                        type enumeration {
                                            enum "los"                          { value 0; }
                                            enum "ais"                          { value 1; }
                                            enum "rdi"                          { value 2; }
                                            enum "dci"                          { value 3; }
                                        }
                                        description "Indicates the state of the received CSF frames for the MEP. los (0) - Client Loss of Signal ais (1) - Client Forward Defect Indication rdi (2) - Client Reverse Defect Indication dci (3) - Client Defect Clear Indication.";
                                    }

                                    leaf interval {
                                        type uint32 {
                                            range "1|60";
                                        }
                                        units "seconds";
                                        description "Indicates the CSF Interval received in the most recent CSF frame.";
                                    }

                                } // container received

                            } // container csf

                            container grace {
                                description "Enter the grace context";

                                container transmitted {
                                    description "Enter the transmitted context";

                                    leaf grace-notification {
                                        type enumeration {
                                            enum "no-transmit"                  { value 0; }
                                            enum "grace"                        { value 1; }
                                            enum "eth-ed"                       { value 2; }
                                        }
                                        description "Indicates the state of the MEP grace period PDU transmission.";
                                    }

                                } // container transmitted

                                container received {
                                    description "Enter the received context";

                                    leaf process-grace-notification {
                                        type boolean;
                                        description "Indicates whether the local MEP is receiving and processing grace notifications from one or more peer MEPs. A value of 'true ' indicates the local MEP is receiving and processing grace from at least one peer MEP. A value of 'false' indicates that no peer grace notifications are being received and processed.";
                                    }

                                } // container received

                            } // container grace

                            container ccm-states {
                                description "Enter the ccm-states context";

                                leaf transmit-status {
                                    type enumeration {
                                        enum "no-transmit"                  { value 0; }
                                        enum "transmit"                     { value 1; }
                                        enum "suppressed"                   { value 2; }
                                    }
                                    description "Indicates the state of the MEP CCM PDU transmission. Values: noTransmit (0) - no CCM PDUs are being transmitted by the MEP transmit (1) - MEP is currently transmitting CCM PDUs suppressed (2) - MEP should be transmitting CCM PDUs but is suppressing them due to an internal condition";
                                }

                                leaf sequence-error {
                                    type yang:counter32;
                                    description "The total number of out-of-sequence CCMs received from all remote MEPs.";
                                }

                                leaf fng-state {
                                    type types-eth-cfm:fng-state-type;
                                    description "Current state of the MEP Fault Notification Generator State Machine.";
                                }

                                container transmitted {
                                    description "Enter the transmitted context";

                                    leaf count {
                                        type yang:counter32;
                                        description "Total number of CCMs transmitted.";
                                    }

                                    leaf interface-status {
                                        type types-eth-cfm:interface-status;
                                        description "Indicates the interface status TLV information included in the most recent Connectivity Check Message (CCM) transmission from the local MEP. If the local MEP CCM transmissions are not enabled, or if no interface status TLV was included in the most recent transmission, then ccm-tx-if-status will return a value of is-no-interface-status-tlv (0).";
                                    }

                                    leaf port-status {
                                        type types-eth-cfm:port-status;
                                        description "Indicates the port status TLV information included in the most recent Connectivity Check Message (CCM) transmission from the local MEP. If the local MEP CCM transmissions are not enabled, or if no port status TLV was included in the most recent transmission, then ccm-tx-port-status will return a value of ps-no-port-state-tlv (0).";
                                    }

                                    leaf remote-defect-indicator {
                                        type boolean;
                                        description "Indicates whether or not the Remote Defect Indication (RDI) bit was set on the most recent Connectivity Check Message (CCM) transmission from the local MEP. If the local MEP CCM transmissions are not eanbled, or if the RDI bit was not set in the most recent transmission, then ccm-tx-rdi will return a value of 'false (2)'.";
                                    }

                                } // container transmitted

                                container received {
                                    description "Enter the received context";

                                    leaf highest-priority-defect {
                                        type types-eth-cfm:highest-priority-defect-type;
                                        description "The highest priority defect that has been present since the MEPs Fault Notification Generator State Machine was last in the reset state.";
                                    }

                                    leaf defect-flags {
                                        type types-eth-cfm:mep-defect-flags;
                                        description "A vector of boolean error conditions, any of which may be true.";
                                    }

                                    list remote-mep-peer {
                                        key "remote-mep-id";
                                        description "Enter the remote-mep-peer list instance";

                                        leaf remote-mep-id {
                                            type types-eth-cfm:mep-id-type;
                                            description "The Remote MEP ID within the same Maintenance Association.";
                                        }

                                        leaf auto-discovered {
                                            type boolean;
                                            description "Specifies whether or not the remote peer was automatically discovered ('true') or not. Auto-discovered remote peers are created by the system only, and are of a 'volatile' storage type. Specifying the value of 'false' will mark an auto-discovered remote peer as permanently configured.";
                                        }

                                        leaf receiving-ccm {
                                            type types-eth-cfm:remote-mep-state-type;
                                            description "The operational CCM receiving state of the remote MEP.";
                                        }

                                        leaf ccm-status-since {
                                            type yang:date-and-time;
                                            description "The time at which the Remote MEP last entered either the mep-failed or mep-ok state.";
                                        }

                                        leaf peer-mac-address {
                                            type yang:mac-address;
                                            description "The MAC address of the remote MEP.";
                                        }

                                        leaf receiving-remote-defect-indicator {
                                            type boolean;
                                            description "State of the RDI bit in the last received CCM (true for rdi=1), or false if none has been received.";
                                        }

                                        leaf port-status-tlv {
                                            type types-eth-cfm:port-status;
                                            description "An enumerated value of the Port status TLV received in the last CCM from the remote MEP or the default value ps-no-port-state-tlv indicating either no CCM has been received, or that no port status TLV was received in the last CCM.";
                                        }

                                        leaf interface-status-tlv {
                                            type types-eth-cfm:interface-status;
                                            description "An enumerated value of the Interface status TLV received in the last CCM from the remote MEP or the default value is-no-interface-status-tlv indicating either no CCM has been received, or that no interface status TLV was received in the last CCM.";
                                        }

                                    } // list remote-mep-peer

                                } // container received

                            } // container ccm-states

                            container mc-lag {
                                description "Enter the mc-lag context";

                                leaf inactive-state {
                                    type enumeration {
                                        enum "not-applicable"               { value 0; }
                                        enum "standby"                      { value 1; }
                                        enum "active"                       { value 2; }
                                    }
                                    description "Indicates the MC-LAG inactive state of the mep. The value of system/eth-cfm/redundancy/mc-lag/standby-mep must be 'true (1)' on the node for this leaf to have meaning.";
                                }

                            } // container mc-lag

                            container statistics {
                                description "Enter the statistics context";

                                list opcode {
                                    key "opcode-name";
                                    description "Enter the opcode list instance";

                                    leaf opcode-name {
                                        type types-eth-cfm:statistics-opcode-name;
                                        description "Integer that defines which CFM PDU Opcode the statictics refer to.";
                                    }

                                    leaf transmitted {
                                        type yang:counter32;
                                        description "The total number of PDUs transmitted from the node with the specified Opcode.";
                                    }

                                    leaf received {
                                        type yang:counter32;
                                        description "The total number of PDUs received on the node with the specified Opcode.";
                                    }

                                } // list opcode

                            } // container statistics

                        } // list mep

                    } // container eth-cfm

                    container static-host {
                        description "Enter the static-host context";

                        list ipv4 {
                            key "ip mac";
                            description "Enter the ipv4 list instance";

                            leaf ip {
                                type types-sros:ipv4-unicast-address;
                                description "IPv4 address used by the static host";
                            }

                            leaf mac {
                                type types-sros:mac-unicast-address;
                                description "MAC address used by the static host";
                            }

                            leaf dynamic-mac {
                                type yang:mac-address;
                                description "The dynamically learned MAC address for this host.";
                            }

                            leaf retail-service {
                                type types-services:service-name;
                                description "The service name of the retailer service to which this static host belongs.";
                            }

                            leaf retail-interface {
                                type types-sros:named-item;
                                description "The interface name of the retailer service interface to which this static host belongs.";
                            }

                            leaf forwarding-state {
                                type types-sros:oper-state;
                                description "Forwarding state of this static host.";
                            }

                            leaf oper-rip-policy {
                                type types-sros:named-item;
                                description "RIP policy which is used to set up the RIP listener for this static host.";
                            }

                            leaf esm-rip-status {
                                type enumeration {
                                    enum "not-applicable"               { value 0; }
                                    enum "active"                       { value 1; }
                                    enum "inactive"                     { value 2; }
                                    enum "no-esm"                       { value 3; }
                                    enum "wrong-anti-spoof"             { value 4; }
                                    enum "parent-interface-down"        { value 5; }
                                    enum "host-inactive"                { value 6; }
                                    enum "l2-aware-not-supported"       { value 7; }
                                    enum "gtp-not-supported"            { value 8; }
                                    enum "mc-standby"                   { value 9; }
                                    enum "rip-disabled"                 { value 10; }
                                }
                                description "Indicates the status of the RIP listener.";
                            }

                            container shcv {
                                description "Enter the shcv context";

                                leaf oper-state {
                                    type enumeration {
                                        enum "disabled"                     { value 1; }
                                        enum "down"                         { value 2; }
                                        enum "up"                           { value 3; }
                                    }
                                    description "The state of the subscriber host connectivity check for this static host.";
                                }

                                leaf checks {
                                    type yang:gauge32;
                                    description "The number of connectivity checks for this static host.";
                                }

                                leaf replies {
                                    type yang:gauge32;
                                    description "The number of host replies for this static host.";
                                }

                                leaf reply-time {
                                    type yang:timestamp;
                                    description "The timestamp of the last successful connectivity check for this static host.";
                                }

                            } // container shcv

                            list managed-route {
                                key "prefix";
                                description "Enter the managed-route list instance";

                                leaf prefix {
                                    type types-sros:ipv4-unicast-prefix;
                                    description "Managed route prefix associated with IPv4 static host";
                                }

                                leaf status {
                                    type enumeration {
                                        enum "installed"                    { value 0; }
                                        enum "not-installed"                { value 1; }
                                        enum "wrong-anti-spoof"             { value 2; }
                                        enum "out-of-memory"                { value 3; }
                                        enum "shadowed"                     { value 4; }
                                        enum "route-table-full"             { value 5; }
                                        enum "parent-interface-down"        { value 6; }
                                        enum "host-inactive"                { value 7; }
                                        enum "esm-required"                 { value 8; }
                                        enum "l2-aware-not-supported"       { value 9; }
                                        enum "next-hop-limit-exceeded"      { value 10; }
                                        enum "not-applicable"               { value 11; }
                                        enum "no-next-hop"                  { value 12; }
                                        enum "gtp-not-supported"            { value 13; }
                                        enum "withdrawn"                    { value 14; }
                                    }
                                    description "The state of this managed route.";
                                }

                            } // list managed-route

                        } // list ipv4

                        list ipv6 {
                            key "prefix mac";
                            description "Enter the ipv6 list instance";

                            leaf prefix {
                                type types-sros:ipv6-unicast-prefix;
                                description "IPv6 prefix";
                            }

                            leaf mac {
                                type types-sros:mac-unicast-address;
                                description "MAC address";
                            }

                            leaf dynamic-mac {
                                type yang:mac-address;
                                description "The dynamically learned MAC address for this host.";
                            }

                            leaf retail-service {
                                type types-services:service-name;
                                description "The service name of the retailer service to which this static host belongs.";
                            }

                            leaf retail-interface {
                                type types-sros:named-item;
                                description "The interface name of the retailer service interface to which this static host belongs.";
                            }

                            leaf forwarding-state {
                                type types-sros:oper-state;
                                description "Forwarding state of this static host.";
                            }

                            container shcv {
                                description "Enter the shcv context";

                                leaf oper-state {
                                    type enumeration {
                                        enum "disabled"                     { value 1; }
                                        enum "down"                         { value 2; }
                                        enum "up"                           { value 3; }
                                    }
                                    description "The state of the subscriber host connectivity check for this static host.";
                                }

                                leaf checks {
                                    type yang:gauge32;
                                    description "The number of connectivity checks for this static host.";
                                }

                                leaf replies {
                                    type yang:gauge32;
                                    description "The number of host replies for this static host.";
                                }

                                leaf reply-time {
                                    type yang:timestamp;
                                    description "The timestamp of the last successful connectivity check for this static host.";
                                }

                            } // container shcv

                            list managed-route {
                                key "ipv6-prefix";
                                description "Enter the managed-route list instance";

                                leaf ipv6-prefix {
                                    type types-sros:ipv6-unicast-prefix;
                                    description "Managed route prefix associated with IPv6 static host";
                                }

                                leaf status {
                                    type enumeration {
                                        enum "installed"                    { value 0; }
                                        enum "not-installed"                { value 1; }
                                        enum "wrong-anti-spoof"             { value 2; }
                                        enum "out-of-memory"                { value 3; }
                                        enum "shadowed"                     { value 4; }
                                        enum "route-table-full"             { value 5; }
                                        enum "parent-interface-down"        { value 6; }
                                        enum "host-inactive"                { value 7; }
                                        enum "esm-required"                 { value 8; }
                                        enum "l2-aware-not-supported"       { value 9; }
                                        enum "next-hop-limit-exceeded"      { value 10; }
                                        enum "not-applicable"               { value 11; }
                                        enum "no-next-hop"                  { value 12; }
                                        enum "gtp-not-supported"            { value 13; }
                                        enum "withdrawn"                    { value 14; }
                                    }
                                    description "The state of this managed route.";
                                }

                            } // list managed-route

                        } // list ipv6

                    } // container static-host

                    container igmp-host-tracking {
                        description "Enter the igmp-host-tracking context";

                        leaf group-count {
                            type int32;
                            description "The number of multicast groups which have been learned on this interface.";
                        }

                        list host-statistics {
                            key "host-address";
                            description "Enter the host-statistics list instance";

                            leaf host-address {
                                type types-sros:ipv4-address;
                                description "The IP address of this host.";
                            }

                            leaf v2-reports {
                                type yang:counter32;
                                description "V2 Reports.";
                            }

                            leaf leaves {
                                type yang:counter32;
                                description "V2 Leaves.";
                            }

                            leaf v3-reports {
                                type yang:counter32;
                                description "V3 Reports.";
                            }

                            leaf drops {
                                type yang:counter32;
                                description "Total number of dropped packets.";
                            }

                            leaf group-joins {
                                type yang:counter32;
                                description "Total number of joins.";
                            }

                            leaf group-leaves {
                                type yang:counter32;
                                description "Total number of leaves.";
                            }

                            leaf group-expiries {
                                type yang:counter32;
                                description "Total number of group expiries.";
                            }

                            leaf import-policy-drops {
                                type yang:counter32;
                                description "Number of times we matched the host IP address or group or source addresses specified in the import policy.";
                            }

                            leaf maximum-number-groups-drops {
                                type yang:counter32;
                                description "Number of times a join is dropped because we reached the maximum number of groups.";
                            }

                            leaf maximum-number-sources-drops {
                                type yang:counter32;
                                description "Number of times a join is dropped because we reached the maximum number of sources per group.";
                            }

                            leaf maximum-number-group-sources-drops {
                                type yang:counter32;
                                description "Number of times a join is dropped because we reached the maximum number group-source combinations.";
                            }

                        } // list host-statistics

                        list host-group-sources {
                            key "host-address group-address source-address";
                            description "Enter the host-group-sources list instance";

                            leaf host-address {
                                type types-sros:ipv4-address;
                                description "The IP address of this host.";
                            }

                            leaf group-address {
                                type types-sros:ipv4-multicast-address;
                                description "Group address of static IGMP multicast channel";
                            }

                            leaf source-address {
                                type types-sros:ipv4-address;
                                description "Source address of multicast channel.";
                            }

                            leaf bandwidth {
                                type uint32;
                                units "kilobps";
                                description "The bandwidth allocated to this host for this multicast stream.";
                            }

                            leaf up-time {
                                type uint32;
                                units "seconds";
                                description "The time elapsed since this entry was created.";
                            }

                            leaf expiry-time {
                                type uint32;
                                units "seconds";
                                description "The time remaining before this entry is aged out.";
                            }

                            leaf subscriber-id {
                                type types-submgt:subscriber-id;
                                description "The subscriber identification of this subscriber host.";
                            }

                        } // list host-group-sources

                    } // container igmp-host-tracking

                    container pppoe {
                        description "Enter the pppoe context";

                        container statistics {
                            description "Enter the statistics context";

                            container rx {
                                description "Enter the rx context";

                                leaf padi {
                                    type yang:counter32;
                                    description "Number of PADI (PPPoE Active Discovery Initiation) packets.";
                                }

                                leaf padr {
                                    type yang:counter32;
                                    description "Number of PADR (PPPoE Active Discovery Request) packets.";
                                }

                                leaf padt {
                                    type yang:counter32;
                                    description "Number of PADT (PPPoE Active Discovery Terminate) packets.";
                                }

                                leaf session {
                                    type yang:counter32;
                                    description "Number of PPP session stage packets.";
                                }

                                leaf invalid-version {
                                    type yang:counter32;
                                    description "Number of PPPoE packets with an invalid version field.";
                                }

                                leaf invalid-type {
                                    type yang:counter32;
                                    description "Number of PPPoE packets with an invalid type field.";
                                }

                                leaf invalid-code {
                                    type yang:counter32;
                                    description "Number of PPPoE packets with an invalid code field.";
                                }

                                leaf invalid-session {
                                    type yang:counter32;
                                    description "Number of PPPoE packets with an invalid session-id field.";
                                }

                                leaf invalid-len {
                                    type yang:counter32;
                                    description "Number of PPPoE packets with an invalid length field.";
                                }

                                leaf invalid-tags {
                                    type yang:counter32;
                                    description "Number of PPPoE Active Discovery packets with invalid tags.";
                                }

                                leaf invalid-ac-cookie {
                                    type yang:counter32;
                                    description "Number of PPPoE Active Discovery packets with an invalid AC-Cookie tag.";
                                }

                                leaf invalid-mac {
                                    type yang:counter32;
                                    description "Number of PPPoE packets with an invalid MAC address.";
                                }

                                leaf dropped {
                                    type yang:counter32;
                                    description "Number of dropped PPPoE packets.";
                                }

                            } // container rx

                            container tx {
                                description "Enter the tx context";

                                leaf pado {
                                    type yang:counter32;
                                    description "Number of PADO (PPPoE Active Discovery Offer) packets.";
                                }

                                leaf pads {
                                    type yang:counter32;
                                    description "Number of PADS (PPPoE Active Discovery Session) packets.";
                                }

                                leaf padt {
                                    type yang:counter32;
                                    description "Number of PADT (PPPoE Active Discovery Terminate) packets.";
                                }

                                leaf session {
                                    type yang:counter32;
                                    description "Number of PPP session stage packets.";
                                }

                            } // container tx

                        } // container statistics

                    } // container pppoe

                    container msap {
                        description "Enter the msap context";

                        leaf capture-sap-id {
                            type types-sros:sap;
                            description "SAP identifier of the capture sap that created this MSAP";
                        }

                        leaf capture-service {
                            type types-services:service-name;
                            description "Service identifier of the capture sap that created this MSAP";
                        }

                        leaf msap-policy {
                            type types-sros:named-item;
                            description "The msap-policy used to create this MSAP";
                        }

                        leaf idle {
                            type boolean;
                            description "A managed SAP is considered idle when no hosts are associated with it.";
                        }

                        leaf sticky {
                            type boolean;
                            description "A sticky managed SAP will not be removed automatically.";
                        }

                    } // container msap

                    container data-trigger {
                        description "Enter the data-trigger context";

                        container statistics {
                            description "Enter the statistics context";

                            leaf rx-total {
                                type yang:counter32;
                                description "The total number of data triggers received on this SAP";
                            }

                            leaf rx-dynamic-business-service {
                                type yang:counter32;
                                description "The number of data triggers received on a dynamic business service SAP";
                            }

                            leaf rx-ipv4 {
                                type yang:counter32;
                                description "The number of IPv4 data triggers received on this SAP";
                            }

                            leaf rx-ipv6 {
                                type yang:counter32;
                                description "The number of IPv6 data triggers received on this SAP";
                            }

                            leaf accepted-dynamic-business-service {
                                type yang:counter32;
                                description "The number of data triggers accepted and passed on for further procerssing on a dynamic business service SAP.";
                            }

                            leaf accepted-ipv4 {
                                type yang:counter32;
                                description "The number of IPv4 data triggers accepted and passed on for further procerssing on this SAP.";
                            }

                            leaf accepted-ipv6 {
                                type yang:counter32;
                                description "The number of IPv6 data triggers accepted and passed on for further procerssing on this SAP.";
                            }

                            container dropped {
                                description "Enter the dropped context";

                                leaf invalid-mac {
                                    type yang:counter32;
                                    description "The number of packets dropped because of invalid source or destination MAC address on this SAP";
                                }

                                leaf invalid-ipv6-header {
                                    type yang:counter32;
                                    description "The number of packets dropped because of an invalid IPv6 header on this SAP";
                                }

                                leaf invalid-ipv6-source {
                                    type yang:counter32;
                                    description "The number of packets dropped because of an invalid IPv6 source address on this SAP";
                                }

                                leaf non-existing-ipv6-host {
                                    type yang:counter32;
                                    description "The number of packets dropped because the ipv6 host is unknown in the system";
                                }

                                leaf invalid-ipv4-header {
                                    type yang:counter32;
                                    description "The number of packets dropped because of an invalid IPv4 header on this SAP";
                                }

                                leaf invalid-ipv4-source {
                                    type yang:counter32;
                                    description "The number of packets dropped because of an invalid IPv4 source address on this SAP";
                                }

                                leaf non-existing-ipv4-host {
                                    type yang:counter32;
                                    description "The number of packets dropped because the ipv4 host is unknown in the system";
                                }

                                leaf out-of-memory {
                                    type yang:counter32;
                                    description "The number of packets dropped because the system runs out of processing memory";
                                }

                                leaf unsupported-protocol {
                                    type yang:counter32;
                                    description "The number of packets dropped because the protocol is not supported";
                                }

                            } // container dropped

                        } // container statistics

                    } // container data-trigger

                    container arp-host {
                        description "Enter the arp-host context";

                        container statistics {
                            description "Enter the statistics context";

                            leaf last-cleared-time {
                                type yang:date-and-time;
                                description "The last time that these stats were cleared";
                            }

                            leaf hosts {
                                type yang:gauge32;
                                description "The actual number of ARP hosts on this SAP";
                            }

                            leaf triggers-received {
                                type yang:counter32;
                                description "The number of ARP triggers received on this SAP";
                            }

                            leaf error-triggers-dropped {
                                type yang:counter32;
                                description "ARP triggers that are dropped due to various error conditions";
                            }

                            leaf overload-triggers-dropped {
                                type yang:counter32;
                                description "ARP triggers that are dropped because of too many outstanding requests";
                            }

                            leaf forced-verifications {
                                type yang:counter32;
                                description "The number of times a host connectivity verification was forced";
                            }

                            leaf hosts-created {
                                type yang:counter32;
                                description "The number of times an ARP host was created on this SAP";
                            }

                            leaf hosts-deleted {
                                type yang:counter32;
                                description "The number of times an ARP host was deleted on this SAP";
                            }

                            leaf hosts-updated {
                                type yang:counter32;
                                description "The number of times an ARP host was updated on this SAP";
                            }

                            leaf authentication-requests {
                                type yang:counter32;
                                description "The number of times an authentication request was initiated by the system for an ARP host on this SAP";
                            }

                        } // container statistics

                    } // container arp-host

                    list locked-out-host {
                        key "id";
                        description "Enter the locked-out-host list instance";

                        leaf id {
                            type uint32;
                            description "Id of the locked out host";
                        }

                        leaf mac-address {
                            type yang:mac-address;
                            description "Mac-address of the locked out host";
                        }

                        leaf circuit-id {
                            type binary {
                                length "1..256";
                            }
                            description "Circuit-id of the locked out host";
                        }

                        leaf remote-id {
                            type binary {
                                length "1..256";
                            }
                            description "Remote-id of the locked out host";
                        }

                        leaf elapsed-reset-time {
                            type uint32;
                            units "seconds";
                            description "Elapsed reset time";
                        }

                        leaf elapsed-lock-time {
                            type uint32;
                            units "seconds";
                            description "Elapsed lock time";
                        }

                        leaf current-lock-timeout {
                            type uint32;
                            units "seconds";
                            description "The timeout for the current lock interval";
                        }

                        leaf next-lock-timeout {
                            type uint32;
                            units "seconds";
                            description "The timeout for the next lock interval";
                        }

                        leaf lockout-count {
                            type uint32;
                            description "Number of lockouts";
                        }

                        leaf lockout-state {
                            type enumeration {
                                enum "graceful"                     { value 1; description "The host is allowed to authenticate and the reset timer
                                is running. Another authentication failure for this host
                                while in this state while change the state to active.
                                If the reset timer expires, the lock out for this host
                                is removed."; }
                                enum "active"                       { value 2; description "The host is not allowed to authenticate and the lock-out
                                timer is running. When the timer expires, the state is
                                changed to graceful."; }
                            }
                            description "Lockout state for this host";
                        }

                    } // list locked-out-host

                } // list sap

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

                container subscriber-management {
                    description "Enter the subscriber-management context";

                    container statistics {
                        description "Enter the statistics context";

                        leaf last-reset-peak-values {
                            type yang:date-and-time;
                            description "Timestamp of the last reset of the peak values";
                        }

                        list ipv4-hosts {
                            key "counter";
                            description "Enter the ipv4-hosts list instance";

                            leaf counter {
                                type types-submgt:submgt-statistics-ipv4-type;
                                description "Type of submgt ipv4 hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list ipv4-hosts

                        list ipv6-hosts {
                            key "counter";
                            description "Enter the ipv6-hosts list instance";

                            leaf counter {
                                type types-submgt:submgt-statistics-ipv6-type;
                                description "Type of submgt ipv6 hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list ipv6-hosts

                        list total-hosts {
                            key "counter";
                            description "Enter the total-hosts list instance";

                            leaf counter {
                                type types-submgt:submgt-statistics-total-type;
                                description "Type of submgt total hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list total-hosts

                        list sessions {
                            key "counter";
                            description "Enter the sessions list instance";

                            leaf counter {
                                type types-submgt:submgt-statistics-session-type;
                                description "Type of submgt sessions counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list sessions

                        container forwarding {
                            description "Enter the forwarding context";

                            leaf last-cleared-time {
                                type yang:date-and-time;
                                description "The time when the counters were last cleared.";
                            }

                            leaf ingress-packets {
                                type yang:counter64;
                                description "The number of IP packets sent by hosts on this interface.";
                            }

                            leaf ingress-octets {
                                type yang:counter64;
                                description "The number of octets in IP packets sent by hosts on this interface.";
                            }

                            leaf egress-packets {
                                type yang:counter64;
                                description "The number of IP packets received by hosts on this interface.";
                            }

                            leaf egress-octets {
                                type yang:counter64;
                                description "The number of octets in IP packets received by hosts on this interface.";
                            }

                        } // container forwarding

                    } // container statistics

                } // container subscriber-management

                uses state-svc-ies-grp-if-wlangw-wlan-gw;
            } // list group-interface

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                    container forwarding {
                        description "Enter the forwarding context";

                        leaf last-cleared-time {
                            type yang:date-and-time;
                            description "The time when the counters were last cleared.";
                        }

                        leaf ingress-packets {
                            type yang:counter64;
                            description "The number of IP packets sent by hosts on this interface.";
                        }

                        leaf ingress-octets {
                            type yang:counter64;
                            description "The number of octets in IP packets sent by hosts on this interface.";
                        }

                        leaf egress-packets {
                            type yang:counter64;
                            description "The number of IP packets received by hosts on this interface.";
                        }

                        leaf egress-octets {
                            type yang:counter64;
                            description "The number of octets in IP packets received by hosts on this interface.";
                        }

                    } // container forwarding

                } // container statistics

            } // container subscriber-management

            container statistics {
                description "Enter the statistics context";

                container ip {
                    description "Enter the ip context";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                } // container ip

                list mac {
                    key "mac-address";
                    description "Enter the mac list instance";

                    leaf mac-address {
                        type yang:mac-address;
                        description "Mac-address";
                    }

                    leaf out-packets {
                        type yang:counter64;
                        description "The number of packets sent to the mac address";
                    }

                    leaf out-octets {
                        type yang:counter64;
                        description "The number of bytes sent to the mac address";
                    }

                    leaf in-packets {
                        type yang:counter64;
                        description "The number of packets received from the mac address";
                    }

                    leaf in-octets {
                        type yang:counter64;
                        description "The number of bytes received from the mac address";
                    }

                } // list mac

            } // container statistics

            uses state-svc-ies-sub-if-wlangw-wlan-gw;
        } // list subscriber-interface

    } // grouping state-svc-ies-sub-if-subscriber-interface

}
