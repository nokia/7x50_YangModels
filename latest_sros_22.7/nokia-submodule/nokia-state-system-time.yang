submodule nokia-state-system-time {

    yang-version "1.1";

    belongs-to nokia-state { prefix "state"; }

    import ietf-yang-types                { prefix "yang"; }
    import nokia-sros-yang-extensions     { prefix "sros-ext"; }
    import nokia-types-sros               { prefix "types-sros"; }

    include nokia-state-router;


    sros-ext:sros-major-release "rel22";

    organization "Nokia";

    contact
        "Nokia SR OS Support
         Web: <http://www.nokia.com>";

    description
        "Nokia YANG Data model with operational state for system time parameters on SR OS based routers.

         Copyright 2016 Nokia. All rights reserved. Reproduction of this document
         is authorized on the condition that the foregoing copyright notice is included.

         This nokia-state-system-time YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-07-07";

    grouping state-system-time {
        container time {
            description "Enter the time context";

            leaf zone-type {
                type enumeration {
                    enum "system"                       { value 1; }
                    enum "user"                         { value 2; }
                }
                description "Zone-type will be 'system' if the zone defined by 'zone-name' is a system-defined zone. It will be 'user' if the zone has been defined by the user.";
            }

            container ntp {
                description "Enter the ntp context";

                list server {
                    key "ip-address router-instance";
                    description "Enter the server list instance";

                    leaf ip-address {
                        type union {
                            type types-sros:ip-address;
                            type enumeration {
                                enum "ptp"                          { value 1; }
                            }
                        }
                        description "IP address of an external NTP server";
                    }

                    leaf router-instance {
                        type string;
                        description "Router name or VPRN service name";
                    }

                    leaf association-id {
                        type int32 {
                            range "0..2147483647";
                        }
                        description "Indicates the association identifier of this NTP server.";
                    }

                    leaf authentication-errors {
                        type yang:counter32;
                        description "Indicates the number of authentication check failures for this NTP server.";
                    }

                } // list server

                list peer {
                    key "ip-address router-instance";
                    description "Enter the peer list instance";

                    leaf ip-address {
                        type types-sros:ip-address;
                        description "IP address of the peer for a peering relationship";
                    }

                    leaf router-instance {
                        type string;
                        description "Router name or VPRN service name";
                    }

                    leaf association-id {
                        type int32 {
                            range "0..2147483647";
                        }
                        description "Indicates the association identifier of this NTP server.";
                    }

                    leaf authentication-errors {
                        type yang:counter32;
                        description "Indicates the number of authentication check failures for this NTP server.";
                    }

                } // list peer

                list broadcast {
                    key "router-instance interface-name";
                    description "Enter the broadcast list instance";

                    leaf router-instance {
                        type leafref {
                            path "../../../../../router/router-name";
                        }
                        description "Router name";
                    }

                    leaf interface-name {
                        type types-sros:interface-name;
                        description "Interface to transmit or receive NTP broadcast packets";
                    }

                    leaf association-id {
                        type int32 {
                            range "0..max";
                        }
                        description "Indicates the association identifier of this NTP broadcast server. This is the index value for NTP Peers Association Id of the row in the 'system-time-ntp-peer' table that represents this NTP broadcast server.";
                    }

                    leaf auth-errors {
                        type yang:counter32;
                        description "Indicates the number of times the NTP Authentication Mismatch notification has been generated because of an authentication check failure on this broadcast interface.";
                    }

                } // list broadcast

                list broadcast-client {
                    key "router-instance interface-name";
                    description "Enter the broadcast-client list instance";

                    leaf router-instance {
                        type string;
                        description "Router name or VPRN service name";
                    }

                    leaf interface-name {
                        type types-sros:interface-name;
                        description "Interface to transmit or receive NTP broadcast packets";
                    }

                    leaf association-id {
                        type int32 {
                            range "0..max";
                        }
                        description "Indicates the association identifier of this NTP broadcast server. This is the index value for NTP Peers Association Id of the row in the 'system-time-ntp-peer' table that represents this NTP broadcast server.";
                    }

                    leaf auth-errors {
                        type yang:counter32;
                        description "Indicates the number of times the NTP Authentication Mismatch notification has been generated because of an authentication check failure on this broadcast interface.";
                    }

                } // list broadcast-client

                container multicast {
                    description "Enter the multicast context";

                    leaf association-id {
                        type int32 {
                            range "0..max";
                        }
                        description "Indicates the association identifier of this NTP broadcast server. This is the index value for NTP Peers Association Id of the row in the 'system-time-ntp-peer' table that represents this NTP broadcast server.";
                    }

                    leaf auth-errors {
                        type yang:counter32;
                        description "Indicates the number of times the NTP Authentication Mismatch notification has been generated because of an authentication check failure on this broadcast interface.";
                    }

                } // container multicast

                container multicast-client {
                    description "Enter the multicast-client context";

                    leaf association-id {
                        type int32 {
                            range "0..max";
                        }
                        description "Indicates the association identifier of this NTP broadcast server. This is the index value for NTP Peers Association Id of the row in the 'system-time-ntp-peer' table that represents this NTP broadcast server.";
                    }

                    leaf auth-errors {
                        type yang:counter32;
                        description "Indicates the number of times the NTP Authentication Mismatch notification has been generated because of an authentication check failure on this broadcast interface.";
                    }

                } // container multicast-client

            } // container ntp

            container sntp {
                description "Enter the sntp context";

                leaf oper-state {
                    type types-sros:oper-state;
                    description "Indicates the current operational status of SNTP.";
                }

            } // container sntp

        } // container time

    } // grouping state-system-time

}
