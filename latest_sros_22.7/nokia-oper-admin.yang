module nokia-oper-admin {

    yang-version "1.1";

    namespace "urn:nokia.com:sros:ns:yang:sr:oper-admin";

    prefix "oper-admin";

    import ietf-yang-types                { prefix "yang"; }
    import nokia-conf                     { prefix "conf"; }
    import nokia-sros-yang-extensions     { prefix "sros-ext"; }
    import nokia-state                    { prefix "state"; }
    import nokia-types-card               { prefix "types-card"; }
    import nokia-types-chassis            { prefix "types-chassis"; }
    import nokia-types-operation          { prefix "types-operation"; }
    import nokia-types-security           { prefix "types-security"; }
    import nokia-types-sros               { prefix "types-sros"; }

    sros-ext:sros-major-release "rel22";

    organization "Nokia";

    contact
        "Nokia SR OS Support
         Web: <http://www.nokia.com>";

    description
        "Nokia YANG Data model for admin actions on SR OS based routers.

         Copyright 2016 Nokia. All rights reserved. Reproduction of this document
         is authorized on the condition that the foregoing copyright notice is included.

         This nokia-oper-admin YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2016-01-01";

    typedef configuration-region {
        type enumeration {
            enum "configure"                    { value 0; }
            enum "li"                           { value 1; }
        }
        default "configure";
        description "The configuration region specify region which is used";
    }

    typedef cli-path-type {
        type string;
        description "Path type used for path infrastructure";
    }

    container admin {
        config false;
        description "Enter the administrative context for system operations";

        action disconnect {
            description "Disconnect a user session";

            input {

                leaf op-table-bypass {
                    type types-operation:operation-op-table-bypass;
                    description "Avoid operation ID allocation";
                }

                leaf address {
                    type types-sros:ip-address;
                    description "IP address of the session to disconnect";
                }

                leaf session-id {
                    type uint32 {
                        range "1..4294967295";
                    }
                    description "ID of the session to disconnect";
                }

                leaf session-type {
                    type enumeration {
                        enum "console"                      { value 1; }
                        enum "bluetooth"                    { value 2; }
                        enum "telnet"                       { value 3; }
                        enum "ssh"                          { value 4; }
                        enum "ftp"                          { value 5; }
                        enum "netconf"                      { value 6; }
                        enum "grpc"                         { value 7; }
                        enum "cron-ehs"                     { value 8; }
                    }
                    description "Type of session to disconnect";
                }

                leaf username {
                    type types-sros:named-item;
                    description "Username to disconnect";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        action reboot {
            description "Reboot CPM or force an upgrade of system boot ROMs";

            input {

                leaf now {
                    type empty;
                    description "Reboot immediately without prompts or confirmation";
                }

                leaf card {
                    type enumeration {
                        enum "active"                       { value 1; }
                        enum "standby"                      { value 2; }
                        enum "upgrade"                      { value 3; }
                    }
                    description "Card to reboot";
                }

                leaf hold {
                    type empty;
                    description "Hold a rebooted standby CPM from coming back online";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        container application-assurance {
            description "Enter the application-assurance context";

            action upgrade {
                description "Upgrade to a new isa-aa.tim file";

                output {

                    leaf operation-id {
                        type types-operation:operation-id;
                        description "Operation ID";
                    }

                    leaf start-time {
                        type types-operation:operation-timestamp;
                        description "Time when the operation execution started";
                    }

                    leaf results-path {
                        type types-operation:operation-path;
                        description "Path to the operation results formatted as xpath";
                    }

                    leaf status {
                        type types-operation:operation-status;
                        description "Operation status";
                    }

                    leaf-list error-message {
                        type types-operation:operation-message;
                        description "Error messages reported during operation execution";
                    }

                    leaf-list warning-message {
                        type types-operation:operation-message;
                        description "Warning messages reported during operation execution";
                    }

                    leaf-list info-message {
                        type types-operation:operation-message;
                        description "Info messages reported during operation execution";
                    }

                    leaf end-time {
                        type types-operation:operation-timestamp;
                        description "Time when the operation execution completed";
                    }

                }
            }

            list group {
                key "aa-group-id";
                description "Enter the group list instance";

                leaf aa-group-id {
                    type leafref {
                        path "/state:state/state:application-assurance/state:group/state:aa-group-id";
                    }
                    description "AA group ID";
                }

                list url-list {
                    key "url-list-name";
                    description "Enter the url-list list instance";

                    leaf url-list-name {
                        type leafref {
                            path "/state:state/state:application-assurance/state:group[state:aa-group-id=current()/../../../group/aa-group-id]/state:url-list/state:url-list-name";
                        }
                        description "AA URL list name";
                    }

                    action upgrade {
                        description "Upgrade the referenced URL list";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // list url-list

            } // list group

        } // container application-assurance

        container clear {
            description "Enter the clear context";

            container security {
                description "Enter the security context";

                action lockout {
                    description "Reset the lockout timer";

                    input {

                        choice lockout-options {
                            mandatory true;
                            case user-name {

                                leaf user {
                                    type types-sros:named-item;
                                    description "User to be cleared of lockout";
                                }

                            }
                            case all {

                                leaf all {
                                    type empty;
                                    description "Clear lockout of all users";
                                }

                            }
                        }
                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

                action password-history {
                    description "Clear the password history";

                    input {

                        choice password-history-options {
                            mandatory true;
                            case user-name {

                                leaf user {
                                    type types-sros:named-item;
                                    description "User to be cleared of password history information";
                                }

                            }
                            case all {

                                leaf all {
                                    type empty;
                                    description "Clear password history of all users";
                                }

                            }
                        }
                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

            } // container security

        } // container clear

        container nat {
            description "Enter the nat context";

            action save-deterministic-script {
                description "Save script that computes deterministic NAT map entries";

                output {

                    leaf operation-id {
                        type types-operation:operation-id;
                        description "Operation ID";
                    }

                    leaf start-time {
                        type types-operation:operation-timestamp;
                        description "Time when the operation execution started";
                    }

                    leaf results-path {
                        type types-operation:operation-path;
                        description "Path to the operation results formatted as xpath";
                    }

                    leaf status {
                        type types-operation:operation-status;
                        description "Operation status";
                    }

                    leaf-list error-message {
                        type types-operation:operation-message;
                        description "Error messages reported during operation execution";
                    }

                    leaf-list warning-message {
                        type types-operation:operation-message;
                        description "Warning messages reported during operation execution";
                    }

                    leaf-list info-message {
                        type types-operation:operation-message;
                        description "Info messages reported during operation execution";
                    }

                    leaf end-time {
                        type types-operation:operation-timestamp;
                        description "Time when the operation execution completed";
                    }

                }
            }

        } // container nat

        container redundancy {
            description "Enter the redundancy context";

            action force-switchover {
                description "Force a switchover to the standby CPM";

                input {

                    leaf now {
                        type empty;
                        description "Force the switchover to the standby CPM immediately";
                    }

                    leaf ignore-status {
                        type empty;
                        description "Switch to the standby CPM regardless of its status";
                    }

                }
                output {

                    leaf operation-id {
                        type types-operation:operation-id;
                        description "Operation ID";
                    }

                    leaf start-time {
                        type types-operation:operation-timestamp;
                        description "Time when the operation execution started";
                    }

                    leaf results-path {
                        type types-operation:operation-path;
                        description "Path to the operation results formatted as xpath";
                    }

                    leaf status {
                        type types-operation:operation-status;
                        description "Operation status";
                    }

                    leaf-list error-message {
                        type types-operation:operation-message;
                        description "Error messages reported during operation execution";
                    }

                    leaf-list warning-message {
                        type types-operation:operation-message;
                        description "Warning messages reported during operation execution";
                    }

                    leaf-list info-message {
                        type types-operation:operation-message;
                        description "Info messages reported during operation execution";
                    }

                    leaf end-time {
                        type types-operation:operation-timestamp;
                        description "Time when the operation execution completed";
                    }

                }
            }

            action synchronize {
                description "Synchronize the standby CPM";

                input {

                    choice synchronize {
                        mandatory true;
                        case boot-environment {

                            leaf boot-environment {
                                type empty;
                                description "Synchronize files used in system initialization";
                            }

                        }
                        case configuration {

                            leaf configuration {
                                type empty;
                                description "Synchronize the configuration files only";
                            }

                        }
                    }
                }
                output {

                    leaf operation-id {
                        type types-operation:operation-id;
                        description "Operation ID";
                    }

                    leaf start-time {
                        type types-operation:operation-timestamp;
                        description "Time when the operation execution started";
                    }

                    leaf results-path {
                        type types-operation:operation-path;
                        description "Path to the operation results formatted as xpath";
                    }

                    leaf status {
                        type types-operation:operation-status;
                        description "Operation status";
                    }

                    leaf-list error-message {
                        type types-operation:operation-message;
                        description "Error messages reported during operation execution";
                    }

                    leaf-list warning-message {
                        type types-operation:operation-message;
                        description "Warning messages reported during operation execution";
                    }

                    leaf-list info-message {
                        type types-operation:operation-message;
                        description "Info messages reported during operation execution";
                    }

                    leaf end-time {
                        type types-operation:operation-timestamp;
                        description "Time when the operation execution completed";
                    }

                }
            }

        } // container redundancy

        container satellite {
            description "Perform administrative operations for satellites";

            list ethernet-satellite {
                key "satellite-id";
                description "Enter the ethernet-satellite list instance";

                leaf satellite-id {
                    type leafref {
                        path "/state:state/state:satellite/state:ethernet-satellite/state:satellite-id";
                    }
                    description "Satellite ID";
                }

                action reboot {
                    description "Initiate an administrative reboot of the chassis";

                    input {

                        leaf now {
                            type empty;
                            description "Reboot immediately without prompts or confirmation";
                        }

                        leaf upgrade {
                            type empty;
                            description "Initiate a firmware image update during the reboot";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

                action synchronize {
                    description "Synchronize the chassis to the boot image";

                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

            } // list ethernet-satellite

        } // container satellite

        container set {
            description "Enter the set context";

            action time {
                description "System date and time";

                input {

                    leaf system-time {
                        type yang:date-and-time;
                        mandatory true;
                        description "System date and time";
                    }

                }
                output {

                    leaf operation-id {
                        type types-operation:operation-id;
                        description "Operation ID";
                    }

                    leaf start-time {
                        type types-operation:operation-timestamp;
                        description "Time when the operation execution started";
                    }

                    leaf results-path {
                        type types-operation:operation-path;
                        description "Path to the operation results formatted as xpath";
                    }

                    leaf status {
                        type types-operation:operation-status;
                        description "Operation status";
                    }

                    leaf-list error-message {
                        type types-operation:operation-message;
                        description "Error messages reported during operation execution";
                    }

                    leaf-list warning-message {
                        type types-operation:operation-message;
                        description "Warning messages reported during operation execution";
                    }

                    leaf-list info-message {
                        type types-operation:operation-message;
                        description "Info messages reported during operation execution";
                    }

                    leaf end-time {
                        type types-operation:operation-timestamp;
                        description "Time when the operation execution completed";
                    }

                }
            }

        } // container set

        container system {
            description "Enter the system context";

            container security {
                description "Enter the security context";

                container hash-control {
                    description "Enter the hash-control context";

                    action custom-hash {
                        description "Custom encryption";

                        input {

                            leaf algorithm {
                                type enumeration {
                                    enum "3des"                         { value 0; description "des-ede3-ecb, PKCS#5 padding"; }
                                    enum "aes128"                       { value 1; description "aes-128-ecb, PKCS#7 padding"; }
                                    enum "aes192"                       { value 2; description "aes-192-ecb, PKCS#7 padding"; }
                                    enum "aes256"                       { value 3; description "aes-256-ecb, PKCS#7 padding"; }
                                }
                                mandatory true;
                                description "Algorithm for custom encryption";
                            }

                            leaf key {
                                type string {
                                    length "1..71";
                                }
                                mandatory true;
                                description "Key for encryption algorithm";
                            }

                        }
                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                    action remove-custom-hash {
                        description "Remove the custom encryption";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // container hash-control

            } // container security

            container license {
                description "Enter the license context";

                action activate {
                    description "Load and activate a system license";

                    input {

                        leaf file-url {
                            type string {
                                length "1..256";
                            }
                            description "Location of the license file to activate";
                        }

                        leaf now {
                            type empty;
                            description "Activate the license immediately";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        container results {

                            leaf active-sros-version {
                                type types-sros:description;
                                description "The current software version running on the system";
                            }

                            leaf license-file {
                                type types-sros:url;
                                description "The location of the validated license file";
                            }

                            leaf license-name {
                                type types-sros:description;
                                description "The name of the license";
                            }

                            leaf license-uuid {
                                type types-sros:description;
                                description "The target UUID of the license";
                            }

                            leaf license-secondary-uuid {
                                type types-sros:description;
                                description "The target secondary UUID of the license";
                            }

                            leaf machine-uuid {
                                type types-sros:description;
                                description "The UUID of this machine";
                            }

                            leaf license-description {
                                type types-sros:description;
                                description "The description of the license";
                            }

                            leaf license-product {
                                type types-sros:description;
                                description "The product for which the license was issued";
                            }

                            leaf license-applicable-versions {
                                type types-sros:description;
                                description "The software version(s) supported by the license";
                            }

                            leaf license-issue-time {
                                type yang:date-and-time;
                                description "The date and time at which the license was issued";
                            }

                            leaf license-start-time {
                                type yang:date-and-time;
                                description "The date and time at which the license becomes valid";
                            }

                            leaf license-end-time {
                                type yang:date-and-time;
                                description "The date and time at which the license expires";
                            }

                            leaf license-validation-status {
                                type enumeration {
                                    enum "incompatible-with-standby-cpm" { value -2; }
                                    enum "url-invalid"                  { value -1; }
                                    enum "ok"                           { value 0; }
                                    enum "invalid"                      { value 1; }
                                    enum "reboot-required"              { value 2; }
                                    enum "incompatible"                 { value 3; }
                                    enum "update-required"              { value 4; }
                                }
                                description "The result of the license valdiation";
                            }

                            leaf validation-error-additional-details {
                                type types-sros:very-long-description-or-empty;
                                description "Additional text explaining a problem preventing license validation";
                            }

                        } // container results

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

                action validate {
                    description "Load and validate a system license";

                    input {

                        leaf file-url {
                            type string {
                                length "1..256";
                            }
                            description "Location of the license file to validate";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        container results {

                            leaf active-sros-version {
                                type types-sros:description;
                                description "The current software version running on the system";
                            }

                            leaf license-file {
                                type types-sros:url;
                                description "The location of the validated license file";
                            }

                            leaf license-name {
                                type types-sros:description;
                                description "The name of the license";
                            }

                            leaf license-uuid {
                                type types-sros:description;
                                description "The target UUID of the license";
                            }

                            leaf license-secondary-uuid {
                                type types-sros:description;
                                description "The target secondary UUID of the license";
                            }

                            leaf machine-uuid {
                                type types-sros:description;
                                description "The UUID of this machine";
                            }

                            leaf license-description {
                                type types-sros:description;
                                description "The description of the license";
                            }

                            leaf license-product {
                                type types-sros:description;
                                description "The product for which the license was issued";
                            }

                            leaf license-applicable-versions {
                                type types-sros:description;
                                description "The software version(s) supported by the license";
                            }

                            leaf license-issue-time {
                                type yang:date-and-time;
                                description "The date and time at which the license was issued";
                            }

                            leaf license-start-time {
                                type yang:date-and-time;
                                description "The date and time at which the license becomes valid";
                            }

                            leaf license-end-time {
                                type yang:date-and-time;
                                description "The date and time at which the license expires";
                            }

                            leaf license-validation-status {
                                type enumeration {
                                    enum "incompatible-with-standby-cpm" { value -2; }
                                    enum "url-invalid"                  { value -1; }
                                    enum "ok"                           { value 0; }
                                    enum "invalid"                      { value 1; }
                                    enum "reboot-required"              { value 2; }
                                    enum "incompatible"                 { value 3; }
                                    enum "update-required"              { value 4; }
                                }
                                description "The result of the license valdiation";
                            }

                            leaf validation-error-additional-details {
                                type types-sros:very-long-description-or-empty;
                                description "Additional text explaining a problem preventing license validation";
                            }

                        } // container results

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

            } // container license

            container telemetry {
                description "Enter the telemetry context";

                container grpc {
                    description "Enter the grpc context";

                    action cancel {
                        description "Cancel the gRPC dynamic telemetry subscription";

                        input {

                            choice cancel-options {
                                mandatory true;
                                case subscription {

                                    leaf subscription-id {
                                        type uint32;
                                        description "ID of the telemetry subscription to cancel";
                                    }

                                }
                                case all {

                                    leaf all {
                                        type empty;
                                        description "Cancel gRPC dynamic telemetry for all subscriptions";
                                    }

                                }
                            }
                        }
                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // container grpc

            } // container telemetry

            container management-interface {
                description "Enter the management-interface context";

                container operations {
                    description "Enter the operations context";

                    action delete-operation {
                        description "Stop and remove an operation";

                        input {

                            leaf op-table-bypass {
                                type types-operation:operation-op-table-bypass;
                                description "Avoid operation ID allocation";
                            }

                            leaf delete-id {
                                type types-operation:operation-id;
                                mandatory true;
                                description "ID of the operation to remove";
                            }

                        }
                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                    action stop-operation {
                        description "Stop the execution of an operational command";

                        input {

                            leaf op-table-bypass {
                                type types-operation:operation-op-table-bypass;
                                description "Avoid operation ID allocation";
                            }

                            leaf stop-id {
                                type types-operation:operation-id;
                                mandatory true;
                                description "ID of the operation to stop";
                            }

                        }
                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // container operations

            } // container management-interface

        } // container system

    } // container admin

}
