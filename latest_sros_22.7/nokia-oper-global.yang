module nokia-oper-global {

    yang-version "1.1";

    namespace "urn:nokia.com:sros:ns:yang:sr:oper-global";

    prefix "oper-global";

    import nokia-conf                     { prefix "conf"; }
    import nokia-sros-yang-extensions     { prefix "sros-ext"; }
    import nokia-state                    { prefix "state"; }
    import nokia-types-eth-cfm            { prefix "types-eth-cfm"; }
    import nokia-types-oam                { prefix "types-oam"; }
    import nokia-types-operation          { prefix "types-operation"; }
    import nokia-types-sros               { prefix "types-sros"; }
    import nokia-types-subscriber-mgmt    { prefix "types-submgt"; }

    sros-ext:sros-major-release "rel22";

    organization "Nokia";

    contact
        "Nokia SR OS Support
         Web: <http://www.nokia.com>";

    description
        "Nokia YANG Data model for Nokia global operations on SR OS based routers.

         Copyright 2016 Nokia. All rights reserved. Reproduction of this document
         is authorized on the condition that the foregoing copyright notice is included.

         This nokia-oper-global YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-10-15";

    container global-operations {
        config false;
        description "Enter the global-operations context";

        action md-cli-raw-command {
            description "Trigger MD-CLI command.";

            input {

                leaf md-cli-input-line {
                    type string;
                    mandatory true;
                    description "MD-CLI command to be executed";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                container results {
                    description "Enter the results context";

                    leaf md-cli-output-block {
                        type string;
                        description "Output of executed MD-CLI command";
                    }

                } // container results

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        action md-compare {
            description "Trigger md-compare command.";

            input {

                container path {
                    description "The state of the connection.";

                    choice path-type {
                        case subtree-path {

                            container subtree-path {
                                description "The state of the connection.";

                            } // container subtree-path

                        }
                    }
                } // container path

                leaf configuration-region {
                    type types-sros:configuration-region;
                    description "This parameter contains the configuration region to operate on.";
                }

                container source {
                    description "The source datastore for the compare operation.";

                    choice destination-type {
                        case candidate {

                            leaf candidate {
                                type empty;
                            }

                        }
                        case baseline {

                            leaf baseline {
                                type empty;
                            }

                        }
                        case url {

                            leaf url {
                                type string;
                            }

                        }
                        case running {

                            leaf running {
                                type empty;
                            }

                        }
                        case startup {

                            leaf startup {
                                type empty;
                            }

                        }
                        case booted {

                            leaf booted {
                                type empty;
                            }

                        }
                        case rollback {

                            container rollback {

                                leaf checkpoint-id {
                                    type uint32;
                                }

                            } // container rollback

                        }
                    }
                } // container source

                container destination {
                    description "The destination datastore for the compare operation.";

                    choice destination-type {
                        case candidate {

                            leaf candidate {
                                type empty;
                            }

                        }
                        case baseline {

                            leaf baseline {
                                type empty;
                            }

                        }
                        case url {

                            leaf url {
                                type string;
                            }

                        }
                        case running {

                            leaf running {
                                type empty;
                            }

                        }
                        case startup {

                            leaf startup {
                                type empty;
                            }

                        }
                        case booted {

                            leaf booted {
                                type empty;
                            }

                        }
                        case rollback {

                            container rollback {

                                leaf checkpoint-id {
                                    type uint32;
                                }

                            } // container rollback

                        }
                    }
                } // container destination

                leaf format {
                    type enumeration {
                        enum "xml"                          { value 0; }
                        enum "md-cli"                       { value 1; }
                    }
                    default "xml";
                    description "RPC output format tag.";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                container results {

                    leaf md-compare-output {
                        type string;
                        description "Output of executed md-compare command.";
                    }

                } // container results

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        container oam {
            description "Enter the oam context";

            container eth-cfm {
                description "Enter the eth-cfm context";

                action linktrace {
                    description "Initiate a linktrace test";

                    input {

                        leaf asynchronous {
                            type types-operation:operation-asynchronous;
                            description "Control execution type of the operation";
                        }

                        leaf retention-timeout {
                            type types-operation:operation-timeout;
                            description "Timeout for operation data retention in global operation table.";
                        }

                        leaf destination {
                            type union {
                                type types-sros:mac-unicast-address-no-zero;
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf ttl {
                            type uint32 {
                                range "0..255";
                            }
                            default "64";
                            description "Time to live for a returned linktrace";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

                action loopback {
                    description "Initiate a loopback test";

                    input {

                        leaf asynchronous {
                            type types-operation:operation-asynchronous;
                            description "Control execution type of the operation";
                        }

                        leaf execution-timeout {
                            type types-operation:operation-timeout;
                            description "Timeout for operation execution.";
                        }

                        leaf retention-timeout {
                            type types-operation:operation-timeout;
                            description "Timeout for operation data retention in global operation table.";
                        }

                        leaf destination {
                            type union {
                                type types-sros:mac-unicast-address-no-zero;
                                type enumeration {
                                    enum "multicast"                    { value 0; }
                                }
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf send-count {
                            type int32 {
                                range "1..1024";
                            }
                            default "1";
                            description "Number of loopback messages to send";
                        }

                        leaf size {
                            type uint32 {
                                range "0..1500";
                            }
                            units "bytes";
                            default "0";
                            description "Data portion size of the data TLV, octet string allowed";
                        }

                        leaf priority {
                            type int32 {
                                range "0..7";
                            }
                            description "Frame priority that can be manipulated by QoS policies";
                        }

                        leaf lbm-padding {
                            type uint32 {
                                range "0|3..9778";
                            }
                            default "0";
                            description "Data portion size of the data TLV, no octet string";
                        }

                        leaf timeout {
                            type uint32 {
                                range "1..10";
                            }
                            units "seconds";
                            default "5";
                            description "Wait time for a reply to a sent message request";
                        }

                        leaf interval {
                            type uint32 {
                                range "0..600";
                            }
                            units "deciseconds";
                            default "0";
                            description "Time between probes within the test run";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

            } // container eth-cfm

            container service-activation-testhead {
                description "Start or stop Service Activation Testhead service test";

                list service-test {
                    key "service-test-name";
                    description "Service test name";

                    leaf service-test-name {
                        type leafref {
                            path "/state:state/state:test-oam/state:service-activation-testhead/state:service-test/state:test-name";
                        }
                        description "Name of the Service Test to be started or stopped";
                    }

                    action start {
                        description "Start OAM Service Activation Testhead Service Test";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                    action stop {
                        description "Stop OAM Service Activation Testhead Service Test";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // list service-test

            } // container service-activation-testhead

        } // container oam

        action ping {
            description "Trigger ping of address or dns-name via machine interface";

            input {

                leaf destination {
                    type union {
                        type types-sros:ip-address-with-zone;
                        type types-sros:string-not-all-spaces {
                            length "1..128";
                        }
                    }
                    mandatory true;
                    description "Destination IP address or DNS name";
                }

                choice routing-options {
                    case case-bypass-routing {

                        leaf bypass-routing {
                            type empty;
                            description "Bypass routing table when sending ping request to host";
                        }

                    }
                    case case-interface {

                        leaf interface {
                            type types-sros:interface-name;
                            description "Sending interface name";
                        }

                    }
                    case case-next-hop {

                        leaf next-hop-address {
                            type types-sros:ip-address;
                            description "Next-hop address to send packet, ignoring routing table";
                        }

                    }
                    case case-subscriber {

                        leaf subscriber {
                            type types-submgt:subscriber-id;
                            description "Subscriber ID for sending ICMP Echo Request packets";
                        }

                    }
                }
                leaf count {
                    type uint32 {
                        range "1..100000";
                    }
                    units "packets";
                    default "5";
                    description "Number of ping requests to send to the remote host";
                }

                leaf output-format {
                    type enumeration {
                        enum "summary"                      { value 1; }
                        enum "detail"                       { value 2; }
                    }
                    default "detail";
                    description "Output format";
                }

                leaf do-not-fragment {
                    type empty;
                    description "Do not fragment the request frame";
                }

                leaf fc {
                    type types-sros:fc-name;
                    default "nc";
                    description "Forwarding class option for the transmitted packet";
                }

                leaf interval {
                    type union {
                        type uint32 {
                            range "1..10000";
                        }
                        type decimal64 {
                            range "0.01..100.00";
                            fraction-digits 2;
                        }
                    }
                    units "seconds";
                    default "1";
                    description "Time between consecutive ping requests";
                }

                leaf pattern {
                    type union {
                        type enumeration {
                            enum "sequential"                   { value -1; }
                        }
                        type int32 {
                            range "0..65535";
                        }
                    }
                    default "sequential";
                    description "Pattern string to include in the packet";
                }

                leaf router-instance {
                    type string;
                    default "Base";
                    description "Router name or VPRN service name";
                }

                leaf size {
                    type uint32 {
                        range "0..16384";
                    }
                    units "bytes";
                    default "56";
                    description "Request packet size including ICMP header and payload";
                }

                leaf source-address {
                    type types-sros:ip-address;
                    description "Source IP address used in the ICMP Echo Request message";
                }

                leaf timeout {
                    type uint32 {
                        range "1..10";
                    }
                    units "seconds";
                    default "5";
                    description "Wait time for the ICMP Echo Reply packet";
                }

                leaf tos {
                    type uint32 {
                        range "0..255";
                    }
                    default "0";
                    description "Type-of-Service (ToS) bits in the IP header";
                }

                leaf ttl {
                    type uint32 {
                        range "1..128";
                    }
                    default "64";
                    description "Time To Live (TTL) included in the request packet";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                container results {

                    container test-parameters {

                        leaf destination {
                            type union {
                                type types-sros:ip-address-with-zone;
                                type types-sros:string-not-all-spaces {
                                    length "1..128";
                                }
                            }
                            description "IP address or DNS name that was pinged.";
                        }

                        choice routing-options {
                            case case-bypass-routing {

                                leaf bypass-routing {
                                    type boolean;
                                    description "Bypass the routing table when sending to a host on a directly attached network.";
                                }

                            }
                            case case-interface {

                                leaf interface {
                                    type types-sros:interface-name;
                                    description "Sending interface for the ICMP Echo Request packet(s).";
                                }

                            }
                            case case-next-hop {

                                leaf next-hop-address {
                                    type types-sros:ip-address;
                                    description "Next hop IP address used when sending ICMP Echo Request packet(s).";
                                }

                            }
                            case case-subscriber {

                                leaf subscriber {
                                    type types-submgt:subscriber-id;
                                    description "Subscriber-id used when sending ICMP Echo Request packet(s).";
                                }

                            }
                        }
                        leaf count {
                            type uint32 {
                                range "1..100000";
                            }
                            units "packets";
                            description "Number of ICMP Echo Request packet(s) sent.";
                        }

                        leaf output-format {
                            type enumeration {
                                enum "summary"                      { value 1; }
                                enum "detail"                       { value 2; }
                            }
                            description "If detail output was active, extra information was returned in error cases";
                        }

                        leaf do-not-fragment {
                            type boolean;
                            description "ICMP Echo Request packet(s) were not allowed to be fragmented (valid for IPv4 only).";
                        }

                        leaf fc {
                            type types-sros:fc-name;
                            description "Forwarding Class for the transmitted ICMP Echo Request packet(s).";
                        }

                        leaf interval {
                            type union {
                                type uint32 {
                                    range "1..10000";
                                }
                                type decimal64 {
                                    range "0.01..100.00";
                                    fraction-digits 2;
                                }
                            }
                            units "seconds";
                            description "Interval between ICMP Echo Request packets sent.";
                        }

                        leaf pattern {
                            type union {
                                type enumeration {
                                    enum "sequential"                   { value -1; }
                                }
                                type int32 {
                                    range "0..65535";
                                }
                            }
                            description "Two byte value used to pad the ICMP Echo Request packet(s). 'sequential' indicates bytes increasing by one.";
                        }

                        leaf router-instance {
                            type types-sros:router-instance-base-management-vprn-loose;
                            description "Router used for the test ('Base', 'management', or a VPRN service name).";
                        }

                        leaf size {
                            type uint32 {
                                range "0..16384";
                            }
                            units "bytes";
                            description "Number of bytes in the combined ICMP Header (8 bytes) and ICMP Payload (variable size) of the ICMP Echo Request packet(s).";
                        }

                        leaf source-address {
                            type types-sros:ip-address;
                            description "Source IP address that was loaded into the IP header of the ICMP Echo Request packet(s).";
                        }

                        leaf timeout {
                            type uint32 {
                                range "1..10";
                            }
                            units "seconds";
                            description "Maximum time (in seconds) that was allowed for ICMP Echo Reply packet(s). The timer was started when the last ICMP Echo Request was sent.";
                        }

                        leaf tos {
                            type uint32 {
                                range "0..255";
                            }
                            description "Type of Service value to be loaded into the DSCP and ECN fields of the IP header of the ICMP Echo Request packet(s).";
                        }

                        leaf ttl {
                            type uint32 {
                                range "1..128";
                            }
                            description "Time To Live value (IPv4) or Hop Limit value (IPv6) to be loaded into the IP header of the ICMP Echo Request packet(s).";
                        }

                    } // container test-parameters

                    list probe {
                        key "probe-index";
                        description "Probe data for the specified test run.";

                        leaf probe-index {
                            type uint32 {
                                range "1..max";
                            }
                            description "Index of probes with the specified test run.";
                        }

                        leaf status {
                            type types-oam:response-status;
                            description "The OAM response status code for the specified test.";
                        }

                        leaf round-trip-time {
                            type uint32;
                            units "microseconds";
                            description "Indicates the round trip time for the specified probe.";
                        }

                        container response-packet {
                            description "Data from packet received as a response to transmitted probe.";

                            leaf size {
                                type uint32;
                                units "bytes";
                                description "Indicates the number of bytes in the response packet for the specified probe.";
                            }

                            leaf source-address {
                                type types-sros:ip-address-with-zone;
                                description "Indicates the source address in the response packet for the specified probe.";
                            }

                            leaf icmp-sequence-number {
                                type uint32;
                                description "Indicates the ICMP sequence number in the response packet for the specified probe.";
                            }

                            leaf ttl {
                                type uint32;
                                description "Indicates the time to live in the response packet for the specified probe.";
                            }

                        } // container response-packet

                    } // list probe

                    container summary {
                        description "Test run summary data.";

                        container statistics {
                            description "Test run summary statistics.";

                            container packets {
                                description "Packet statistics for the specified test run.";

                                leaf sent {
                                    type uint32;
                                    units "packets";
                                    description "Indicates the number of packets sent for the specified test run.";
                                }

                                leaf received {
                                    type uint32;
                                    units "packets";
                                    description "Indicates the number of packets received for the specified test run.";
                                }

                                leaf loss {
                                    type decimal64 {
                                        range "0.00..100.00";
                                        fraction-digits 2;
                                    }
                                    units "percent";
                                    description "Indicates the number of packet loss percentage for the specified test run.";
                                }

                            } // container packets

                            container round-trip-time {
                                description "Test run round trip time statistics.";

                                leaf minimum {
                                    type uint32;
                                    units "microseconds";
                                    description "Indicates the minimum round trip time for the specified test run.";
                                }

                                leaf average {
                                    type uint32;
                                    units "microseconds";
                                    description "Indicates the average round trip time for the specified test run.";
                                }

                                leaf maximum {
                                    type uint32;
                                    units "microseconds";
                                    description "Indicates the maximum round trip time for the specified test run.";
                                }

                                leaf standard-deviation {
                                    type uint32;
                                    units "microseconds";
                                    description "Indicates the standard deviation for the round trip times for the specified test run.";
                                }

                            } // container round-trip-time

                        } // container statistics

                    } // container summary

                } // container results

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        action traceroute {
            description "Trigger traceroute of address or dns-name via machine interface";

            input {

                leaf destination {
                    type union {
                        type types-sros:ip-unicast-address;
                        type types-sros:string-not-all-spaces {
                            length "1..128";
                        }
                    }
                    mandatory true;
                    description "Destination IP address or DNS name";
                }

                leaf decode {
                    type enumeration {
                        enum "none"                         { value 0; }
                        enum "original-datagram"            { value 1; }
                    }
                    default "none";
                    description "Decode and display additional fields in replies received";
                }

                leaf dest-port {
                    type uint32 {
                        range "1..65535";
                    }
                    default "33434";
                    description "Transport protocol destination port number";
                }

                leaf dest-port-udp-fixed {
                    type empty;
                    description "Avoid increment of destination port number for UDP test";
                }

                leaf detail {
                    type empty;
                    description "Display MPLS label stack information or TCP port status";
                }

                leaf min-ttl {
                    type uint32 {
                        range "1..255";
                    }
                    default "1";
                    description "First hop traceroute probes using the ttl value";
                }

                leaf ttl {
                    type uint32 {
                        range "1..255";
                    }
                    default "30";
                    description "Maximum number of hops (time-to-live) traceroute probes";
                }

                leaf numeric {
                    type empty;
                    description "Display IP addresses instead of DNS names";
                }

                leaf probe-count {
                    type uint32 {
                        range "1..10";
                    }
                    default "3";
                    description "Number of probes to send per hop";
                }

                leaf protocol {
                    type enumeration {
                        enum "udp"                          { value 1; }
                        enum "tcp"                          { value 2; }
                    }
                    default "udp";
                    description "Packet type to send";
                }

                leaf router-instance {
                    type string;
                    default "Base";
                    description "Router name or VPRN service name";
                }

                leaf size {
                    type uint32 {
                        range "0..9786";
                    }
                    units "bytes";
                    default "0";
                    description "Number of pad bytes in each transmitted packet";
                }

                leaf source-address {
                    type types-sros:ip-address;
                    description "Source address of the probe packets";
                }

                leaf tos {
                    type uint32 {
                        range "0..255";
                    }
                    default "0";
                    description "Type-of-Service (ToS) bits in the IP header";
                }

                leaf wait {
                    type uint32 {
                        range "10..60000";
                    }
                    units "milliseconds";
                    default "5000";
                    description "Time to wait for a response to the probe";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                container results {

                    container test-parameters {

                        leaf destination {
                            type union {
                                type types-sros:ip-address;
                                type types-sros:string-not-all-spaces {
                                    length "1..128";
                                }
                            }
                            description "The destination IP address or DNS name";
                        }

                        leaf decode {
                            type enumeration {
                                enum "none"                         { value 0; }
                                enum "original-datagram"            { value 1; }
                            }
                            description "The state of the connection.";
                        }

                        leaf dest-port {
                            type uint32 {
                                range "1..65535";
                            }
                            description "The destination UDP or TCP port number";
                        }

                        leaf dest-port-udp-fixed {
                            type boolean;
                            description "Avoid increment of destination port number for UDP test";
                        }

                        leaf detail {
                            type boolean;
                            description "Display MPLS label stack information (if available)";
                        }

                        leaf min-ttl {
                            type uint32 {
                                range "1..255";
                            }
                            description "The minimum number of hops (min time-to-live value) traceroute will probe";
                        }

                        leaf ttl {
                            type uint32 {
                                range "1..255";
                            }
                            description "The maximum number of hops (max time-to-live value) traceroute will probe";
                        }

                        leaf numeric {
                            type boolean;
                            description "'true' avoids looking up DNS names when displaying results";
                        }

                        leaf probe-count {
                            type uint32 {
                                range "1..10";
                            }
                            description "The number of probes to send per hop";
                        }

                        leaf protocol {
                            type enumeration {
                                enum "udp"                          { value 1; }
                                enum "tcp"                          { value 2; }
                            }
                            description "Send UDP packets or TCP-SYN packets";
                        }

                        leaf router-instance {
                            type types-sros:router-instance-base-management-vprn-loose;
                            description "The router used for the traceroute (i.e. 'Base', 'management', 'vpls-management' or a VPRN service name)";
                        }

                        leaf size {
                            type uint32 {
                                range "0..9786";
                            }
                            units "bytes";
                            description "The number of pad bytes in each transmitted packet";
                        }

                        leaf source-address {
                            type types-sros:ip-address;
                            description "The node source address to use for the test";
                        }

                        leaf tos {
                            type uint32 {
                                range "0..255";
                            }
                            description "The Type of Service to use for the test";
                        }

                        leaf wait {
                            type uint32 {
                                range "10..60000";
                            }
                            units "milliseconds";
                            description "The time (in milliseconds) to wait for a response to a probe";
                        }

                    } // container test-parameters

                    list hop {
                        key "hop-index";
                        description "Per-hop (also known as per-TTL) test results";

                        leaf hop-index {
                            type uint32 {
                                range "1..max";
                            }
                            description "The hop index of the test results";
                        }

                        list probe {
                            key "probe-index";
                            description "Per-probe test results";

                            leaf probe-index {
                                type uint32 {
                                    range "1..max";
                                }
                                description "Index of the probe within the specified hop for the test";
                            }

                            leaf status {
                                type types-oam:response-status;
                                description "The status of the probe (e.g. response-received, request-timed-out)";
                            }

                            leaf round-trip-time {
                                type uint32;
                                units "microseconds";
                                description "The round trip time for the specified probe and response";
                            }

                            leaf size {
                                type uint32;
                                units "bytes";
                                description "The number of bytes in the request packet (zero if no request packet was sent)";
                            }

                            container response-packet {
                                description "Test results copied (or derived) from a response packet";

                                leaf icmp-type {
                                    type uint32 {
                                        range "0..255";
                                    }
                                    description "The ICMP or ICMPv6 Type in the received response. icmp-type = 0 AND icmp-code = 0 indicates no Type and Code is available";
                                }

                                leaf icmp-code {
                                    type uint32 {
                                        range "0..255";
                                    }
                                    description "The ICMP or ICMPv6 Code in the received response. icmp-type = 0 AND icmp-code = 0 indicates no Type and Code is available";
                                }

                                leaf mtu-exceeded {
                                    type uint32;
                                    units "bytes";
                                    description "The MTU (Maximum Transmission Unit) in the received response. When the MTU is non-zero, it indicates the MTU exceeded by a transmitted packet .";
                                }

                                leaf source-address {
                                    type types-sros:ip-address;
                                    description "The source address in the response packet (i.e. the address of the replying node)";
                                }

                                leaf source-host-name {
                                    type string {
                                        length "0..255";
                                    }
                                    description "The host name looked up (in DNS) using the address of the replying node";
                                }

                                leaf tcp-port-status {
                                    type enumeration {
                                        enum "none"                         { value 1; }
                                        enum "tcp-port-open"                { value 2; }
                                        enum "tcp-port-closed"              { value 3; }
                                    }
                                    description "The operational state of the probed TCP port on the test's destination node. 'none' is returned if the test's protocol is UDP, or the replying node is not the test's destination";
                                }

                                list mpls-label-stack-entry {
                                    key "index";
                                    description "The information read from an RFC 4950 MPLS Label Stack Object in the response packet";

                                    leaf index {
                                        type uint32 {
                                            range "1..max";
                                        }
                                        description "Index of an RFC 4950 MPLS Label Stack Entry within the MPLS Label Stack Object";
                                    }

                                    leaf label {
                                        type types-sros:mpls-label-full-range;
                                        description "The Label field within the specified RFC 4950 MPLS Label Stack Entry";
                                    }

                                    leaf traffic-class {
                                        type uint32 {
                                            range "0..7";
                                        }
                                        description "The Experimental field within the specified RFC 4950 MPLS Label Stack Entry (subsequently renamed to Traffic Class)";
                                    }

                                    leaf bottom-of-stack {
                                        type uint32 {
                                            range "0..1";
                                        }
                                        description "The Bottom of Stack field within the specified RFC 4950 MPLS Label Stack Entry";
                                    }

                                    leaf ttl {
                                        type uint32 {
                                            range "0..255";
                                        }
                                        description "The TTL field within the specified RFC 4950 MPLS Label Stack Entry";
                                    }

                                } // list mpls-label-stack-entry

                                container original-datagram {
                                    description "The state of the connection.";

                                    list header {
                                        key "header-index";
                                        description "The state of the connection.";

                                        leaf header-index {
                                            type uint32 {
                                                range "1..max";
                                            }
                                            description "The state of the connection.";
                                        }

                                        choice header-type-choice {
                                            case ipv6-case {

                                                container ipv6-header {
                                                    description "The state of the connection.";

                                                    leaf destination-address {
                                                        type types-sros:ip-address;
                                                        description "The state of the connection.";
                                                    }

                                                    leaf dscp {
                                                        type types-sros:named-item-or-empty;
                                                        description "The state of the connection.";
                                                    }

                                                    leaf hop-limit {
                                                        type uint32 {
                                                            range "0..255";
                                                        }
                                                        description "The state of the connection.";
                                                    }

                                                    leaf source-address {
                                                        type types-sros:ip-address;
                                                        description "The state of the connection.";
                                                    }

                                                } // container ipv6-header

                                            }
                                            case srv6-case {

                                                container srv6-header {
                                                    description "The state of the connection.";

                                                    leaf segments-left {
                                                        type uint32 {
                                                            range "0..255";
                                                        }
                                                        description "The state of the connection.";
                                                    }

                                                    list segment-list {
                                                        key "segment-index";
                                                        description "The state of the connection.";

                                                        leaf segment-index {
                                                            type uint32;
                                                            description "The state of the connection.";
                                                        }

                                                        leaf segment-address {
                                                            type types-sros:ip-address;
                                                            description "The state of the connection.";
                                                        }

                                                    } // list segment-list

                                                } // container srv6-header

                                            }
                                        }
                                    } // list header

                                } // container original-datagram

                            } // container response-packet

                        } // list probe

                    } // list hop

                } // container results

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

    } // container global-operations

}
