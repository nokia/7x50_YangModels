module nokia-sr-openconfig-system-management-deviations {

    namespace "urn:nokia.com:sros:ns:yang:sr:openconfig-system-management-deviations";

    prefix "nokia-oc-sys-mgmt-devs";

    import nokia-sros-yang-extensions     { prefix "sros-ext"; }
    import openconfig-extensions          { prefix "oc-ext"; }
    import openconfig-inet-types          { prefix "oc-inet"; }
    import openconfig-system              { prefix "oc-sys"; }
    import openconfig-system-management   { prefix "oc-sys-mgmt"; }

    sros-ext:sros-major-release "rel22";

    organization "Nokia";

    contact
        "Nokia SR OS Support
         Web: <http://www.nokia.com>";

    description
        "This module contains the list of deviations against the openconfig-system-management
          module for the Nokia SR OS based routers.

         Copyright 2016 Nokia. All rights reserved. Reproduction of this document
         is authorized on the condition that the foregoing copyright notice is included.

         This nokia-sr-openconfig-system-management-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-08-28";

    deviation /oc-sys:system/oc-sys:grpc-server/oc-sys:config/oc-sys:enable {
        deviate replace {
            default false;
        }
    }

    deviation /oc-sys:system/oc-sys:grpc-server/oc-sys:config/oc-sys:certificate-id {
        deviate replace {
            type string {
                length 1..91;
                pattern "(.*\\S.*)|()";
                pattern "[^\\\\:/]*";
            }
        }
    }

    deviation /oc-sys:system/oc-sys:grpc-server/oc-sys:config/oc-sys:listen-addresses {
        deviate not-supported;
    }

    deviation /oc-sys:system/oc-sys:grpc-server/oc-sys:config/oc-sys:port {
        deviate not-supported;
    }

    deviation /oc-sys:system/oc-sys:grpc-server/oc-sys:state/oc-sys:enable {
        deviate replace {
            default false;
        }
    }

    deviation /oc-sys:system/oc-sys:grpc-server/oc-sys:state/oc-sys:certificate-id {
        deviate replace {
            type string {
                length 1..91;
                pattern "(.*\\S.*)|()";
                pattern "[^\\\\:/]*";
            }
        }
    }

    deviation /oc-sys:system/oc-sys:grpc-server/oc-sys:state/oc-sys:listen-addresses {
        deviate not-supported;
    }

}
