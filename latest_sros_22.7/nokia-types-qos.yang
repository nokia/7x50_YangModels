module nokia-types-qos {

    yang-version "1.1";

    namespace "urn:nokia.com:sros:ns:yang:sr:types-qos";

    prefix "types-qos";

    import nokia-sros-yang-extensions     { prefix "sros-ext"; }

    sros-ext:sros-major-release "rel22";

    organization "Nokia";

    contact
        "Nokia SR OS Support
         Web: <http://www.nokia.com>";

    description
        "Common QoS data types used in the SR OS management system.

         Copyright 2016 Nokia. All rights reserved. Reproduction of this document
         is authorized on the condition that the foregoing copyright notice is included.

         This nokia-types-qos YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-07-15";

    typedef bytes {
        type int32;
        units "bytes";
    }

    typedef kilobytes {
        type int32;
        units "kilobytes";
    }

    typedef kbps {
        type union {
            type enumeration {
                enum "max"                          { value -1; }
            }
            type int64;
        }
        units "kilobps";
    }

    typedef sap-ingress-fc-name {
        type string {
            length "1..32";
            pattern "(be|l2|af|l1|h2|ef|h1|nc)(\\.[a-zA-Z0-9\\s\\p{P}]{1,29})?" {
                error-message "Invalid Forwarding Class (FC) name";
            }
        }
        description
            "Specifies the forwarding class or the sub forwarding class.

             The format of a sub forwarding class is the concatenation of the
             base forwarding class and a sub class identifier in the form:
             'base-fc-name[.sub-fc-name]'.";
    }

    typedef qos-policy-name {
        type string {
            length "1..64";
            pattern "(.*\\S.*)|()" {
                error-message "The given string must not be all spaces.";
            }
        }
        description "The policy name assigned to this QoS policy.";
    }

    typedef fp-resource-policy-name {
        type string {
            length "1..64";
            pattern "(.*\\S.*)|()" {
                error-message "The given string must not be all spaces.";
            }
        }
        description "The policy name assigned to this QoS policy.";
    }

    typedef network-policy-name {
        type string {
            length "1..64";
            pattern "(.*\\S.*)|()" {
                error-message "The given string must not be all spaces.";
            }
        }
        description "The policy name assigned to this QoS policy.";
    }

    typedef qos-policy-id {
        type uint32 {
            range "1..65535";
        }
        description "The identification number of QoS policy.";
    }

    typedef qos-any-policy-id {
        type uint32 {
            range "1..4294967295";
        }
        description
            "The identification number of QoS policy. Any value greater than 65535
             indicates the policy was created by the system.
                         
             The format is:
                +--------------------------------+
                |<----C-----><-B><------A------->|
                +--------------------------------+
                31                               0
                         
             where:
              A (16 bits) is the base policy identifier.
              B (4 bits) is the 'policy type'.
              C (12 bits) is the auxiliary identifier.
                         
             When policy type = 0 (0000b), the acceptable range for base policy
                                          identifier is 1..65535. This is the user
                                          configured values.
             When policy type = 1 (0001b)  [NAT/LNS], the acceptable range for base
                                          policy identifier is 0..2. These policies
                                          are considered 'internal' and cannot be
                                          created or modified by the user.
             When policy type = 2 (0010b)  The auxiliary identifier represents
                                          internal policies that are created
                                          by the system based on dynamic flow based
                                          requests from diameter and cannot be
                                          modified by the user. These polices
                                          ranges from 1..2047. For all other policy
                                          types, the auxiliary identifier must be
                                          zero.";
    }

    typedef item-scope {
        type enumeration {
            enum "exclusive"                    { value 1; }
            enum "template"                     { value 2; }
        }
        description
            "Determines some aspects of an item's behavior regarding creation and use,
             unused entry garbage collection, and automated promulgation by Element
             Management System to other systems in the service domain.

               exclusive:
                 When the scope of an item is defined as exclusive, the item can
                 only be applied once.

               template:
                 When the scope of an item is defined as template, the item can be
                 applied any number of times.";
    }

    typedef priority {
        type enumeration {
            enum "low"                          { value 1; }
            enum "high"                         { value 2; }
            enum "auto"                         { value 3; }
        }
        default "auto";
        description "The priority to apply to a packet.";
    }

    typedef default-priority {
        type enumeration {
            enum "low"                          { value 1; }
            enum "high"                         { value 2; }
        }
        description "The default-priority to apply to a packet.";
    }

    typedef mac-filter-type {
        type enumeration {
            enum "normal"                       { value 1; }
            enum "isid"                         { value 2; }
            enum "vid"                          { value 3; }
        }
        description "Possible types of MAC filters provided by the system.";
    }

    typedef ip-filter-type {
        type enumeration {
            enum "normal"                       { value 1; }
            enum "vxlan-vni"                    { value 2; }
            enum "tagged-entries"               { value 3; }
        }
        description "Possible types of IP filters provided by the system.";
    }

    typedef criteria-action-type {
        type enumeration {
            enum "ignore-match"                 { value 1; }
            enum "accept"                       { value 2; }
        }
        description
            "Specifies the type of action to be taken for traffic that
             matches this criteria entry.

             A value of 'ignore-match' means no action is taken, and the
             packet will continue matching the criteria entries with a
             higher ID (meaning this entry is effectively disabled).

             A value of 'accept' means the packet is not matched against
             the next criteria entries. In this case, every other
             action parameters that is set to a non default value is
             applied.

             If all other action parameters are set to default values,
             a value of 'accept' can be used to prevent the traffic from
             matching entries with a higher ID.";
    }

    typedef vxlan-vni-operator {
        type enumeration {
            enum "eq"                           { value 1; }
            enum "range"                        { value 2; }
        }
        description
            "Specifies the operator value in used while determining valid values
             for start and end port.";
    }

    typedef queue-group-queue-type {
        type enumeration {
            enum "expedited"                    { value 1; }
            enum "best-effort"                  { value 3; }
        }
        description
            "Specifies the priority that this queue should be assigned by the hardware
             level schedulers. 
                         
             This attribute is associated with the queue at the time of creation and 
             cannot be modified thereafter.";
    }

    typedef queue-type {
        type enumeration {
            enum "expedited"                    { value 1; }
            enum "auto-expedited"               { value 2; }
            enum "best-effort"                  { value 3; }
        }
        description
            "Specifies the priority that this queue should be assigned by the hardware
             level schedulers.

             The value 'auto-expedited' implies that this attribute should be
             dynamically updated by looking at the forwarding classes mapping
             into this queue. In such a case the queue is treated as
             'non-expedited' if there is even a single non-expedited forwarding
             class using this queue.

             This attribute is associated with the queue at the time of creation and
             cannot be modified thereafter.";
    }

    typedef queue-mode {
        type enumeration {
            enum "priority"                     { value 1; }
            enum "profile"                      { value 2; }
        }
        description
            "Specifies the mode in which the queue is operating.

             This attribute is associated with the queue at the time of creation and
             cannot be modified thereafter.";
    }

    typedef wred-queue-mode {
        type enumeration {
            enum "native"                       { value 1; }
            enum "pool-per-queue"               { value 2; }
        }
        description
            "Specifies the generic pool association of the queue for the purpose of
             allowing queue-specific WRED slopes.";
    }

    typedef wred-queue-slope-usage {
        type enumeration {
            enum "auto"                         { value 1; }
            enum "exceed-low"                   { value 2; }
        }
        description "Specifies which slopes are active for given slope-mode";
    }

    typedef mac-frame-type {
        type enumeration {
            enum "802dot3"                      { value 0; }
            enum "802dot2-llc"                  { value 1; }
            enum "802dot2-snap"                 { value 2; }
            enum "ethernet-ii"                  { value 3; }
            enum "atm"                          { value 5; }
        }
        description "The type of the frame mac filter match criteria is defined.";
    }

    typedef adaptation-rule {
        type enumeration {
            enum "max"                          { value 1; }
            enum "min"                          { value 2; }
            enum "closest"                      { value 3; }
        }
        description
            "The adaptation rule to be applied to calcluate the operational values
             for the specified entity.";
    }

    typedef adaptation-rule-override {
        type enumeration {
            enum "max"                          { value 1; }
            enum "min"                          { value 2; }
            enum "closest"                      { value 3; }
        }
        description
            "The adaptation rule to be applied to calculate the operational values
             for the specified entity.";
    }

    typedef network-queue-queue-id {
        type int32 {
            range "1..16";
        }
        description "Specifies the identification number of an queue.";
    }

    typedef ingress-queue-id {
        type int32 {
            range "1..32";
        }
        description "Specifies the identification number of an ingress queue.";
    }

    typedef egress-queue-id {
        type int32 {
            range "1..8";
        }
        description "Specifies the identification number of an egress queue.";
    }

    typedef network-ingress-policer-id {
        type int32 {
            range "1..32";
        }
        description "The policer identifier on ingress side.";
    }

    typedef network-egress-policer-id {
        type int32 {
            range "1..8";
        }
        description "The policer identifier on egress side.";
    }

    typedef ingress-policer-id {
        type int32 {
            range "1..63";
        }
        description "The policer identifier on ingress side.";
    }

    typedef sap-egress-policer-id {
        type int32 {
            range "1..63";
        }
        description "The policer identifier on egress side.";
    }

    typedef egress-policer-id {
        type int32 {
            range "1..8";
        }
        description "The policer identifier on egress side.";
    }

    typedef profile-in-out {
        type enumeration {
            enum "in"                           { value 1; }
            enum "out"                          { value 2; }
        }
        description "The Quality of Service profile for the session, restricted to 'in' and 'out' only.";
    }

    typedef profile {
        type enumeration {
            enum "in"                           { value 1; }
            enum "out"                          { value 2; }
            enum "exceed"                       { value 4; }
            enum "inplus"                       { value 5; }
        }
        description "Profile marking of a packet.";
    }

    typedef profile-de {
        type enumeration {
            enum "in"                           { value 1; }
            enum "out"                          { value 2; }
            enum "de"                           { value 3; }
            enum "exceed"                       { value 4; }
            enum "inplus"                       { value 5; }
        }
        description
            "Profile marking of a packet.
             Value of 'in' specifies the in-profile marking.
             Value of 'out' specifies the out-profile marking.
             Value of 'de' specifies that the profile marking will be based on the DE (Drop-Eligible) bit:
                 - DE bit-value of '0' specifies in-profile and DE.
                 - DE bit-value of '1' specifies out-profile marking.";
    }

    typedef egress-profile-de {
        type enumeration {
            enum "in"                           { value 1; }
            enum "out"                          { value 2; }
            enum "de"                           { value 3; }
            enum "exceed"                       { value 4; }
            enum "inplus"                       { value 5; }
        }
        description
            "Profile marking of a packet.
             Value of 'in' specifies the in-profile marking.
             Value of 'out' specifies the out-profile marking.
             Value of 'de' specifies that the profile marking will be based on the DE (Drop-Eligible) bit:
                 - DE bit-value of '0' specifies in-profile and DE.
                 - DE bit-value of '1' specifies out-profile marking.";
    }

    typedef egress-profile {
        type enumeration {
            enum "in"                           { value 1; }
            enum "out"                          { value 2; }
            enum "exceed"                       { value 4; }
            enum "inplus"                       { value 5; }
        }
        description
            "Profile marking of a packet.
             Value of 'in' specifies the in-profile marking.
             Value of 'out' specifies the out-profile marking.";
    }

    typedef ingress-policer-stat-mode {
        type enumeration {
            enum "no-stats"                     { value 0; }
            enum "minimal"                      { value 1; }
            enum "offered-profile-no-cir"       { value 2; }
            enum "offered-total-cir"            { value 3; }
            enum "offered-priority-no-cir"      { value 4; }
            enum "offered-profile-cir"          { value 5; }
            enum "offered-priority-cir"         { value 6; }
            enum "offered-limited-profile-cir"  { value 7; }
            enum "offered-profile-capped-cir"   { value 8; }
            enum "offered-limited-capped-cir"   { value 9; }
        }
        description "Specifies the mode of statistics collected by ingress policer.";
    }

    typedef sap-ingress-policer-stat-mode {
        type enumeration {
            enum "no-stats"                     { value 0; }
            enum "minimal"                      { value 1; }
            enum "offered-profile-no-cir"       { value 2; }
            enum "offered-total-cir"            { value 3; }
            enum "offered-priority-no-cir"      { value 4; }
            enum "offered-profile-cir"          { value 5; }
            enum "offered-priority-cir"         { value 6; }
            enum "offered-limited-profile-cir"  { value 7; }
            enum "offered-profile-capped-cir"   { value 8; }
            enum "offered-limited-capped-cir"   { value 9; }
            enum "offered-profile-with-discards" { value 10; }
        }
        description "Specifies the mode of statistics collected by ingress policer.";
    }

    typedef egress-policer-stat-mode {
        type enumeration {
            enum "no-stats"                     { value 0; }
            enum "minimal"                      { value 1; }
            enum "offered-profile-no-cir"       { value 2; }
            enum "offered-total-cir"            { value 3; }
            enum "offered-profile-cir"          { value 4; }
            enum "offered-limited-capped-cir"   { value 5; }
            enum "offered-profile-capped-cir"   { value 6; }
            enum "offered-total-cir-exceed"     { value 8; }
            enum "offered-four-profile-no-cir"  { value 9; }
            enum "offered-total-cir-four-profile" { value 10; }
        }
        description "Specifies the mode of statistics collected by egress policer.";
    }

    typedef atm-service-category {
        type enumeration {
            enum "cbr"                          { value 2; }
            enum "rt-vbr"                       { value 3; }
            enum "nrt-vbr"                      { value 4; }
            enum "ubr"                          { value 6; }
        }
        description "The service category for a connection.";
    }

    typedef service-access-point {
        type int32 {
            range "0..255";
        }
        description "802.2 LLC SAP value, Source and Destination.";
    }

    typedef entry-id {
        type uint32 {
            range "1..65535";
        }
        description
            "Uniquely identifies an entry in a policy or filter table.
             To facilitate insertion of entries in the tables, we recommend
             assigning entry IDs by 10s:  10, 20, 30, etc.";
    }

    typedef per-packet-offset {
        type int32 {
            range "-32..31";
        }
        description
            "The value, in bytes, of the adjustment to make to the size of each
             packet for accounting.";
    }

    typedef egress-per-packet-offset {
        type int32 {
            range "-64..31";
        }
        description
            "The value, in bytes, of the adjustment to make to the size of each
             outgoing packet for accounting.";
    }

    typedef egress-per-packet-offset-override {
        type int32 {
            range "-64..31";
        }
        description
            "The value, in bytes, of the adjustment to make to the size of each
             outgoing packet for accounting.";
    }

    typedef ingress-per-packet-offset-override {
        type int32 {
            range "-32..31";
        }
        description
            "The value, in bytes, of the adjustment to make to the size of each
             incoming packet for accounting.";
    }

    typedef cir-level {
        type int32 {
            range "0..8";
        }
        description "The cir-level of the specified entity while feeding into the parent.";
    }

    typedef cir-weight {
        type int32 {
            range "0..100";
        }
        description "The cir-weight of the specified entity while feeding into the parent.";
    }

    typedef weight {
        type int32 {
            range "0..100";
        }
        description "The weight of the specified entity while feeding into the parent.";
    }

    typedef weight-override {
        type int32 {
            range "0..100";
        }
        description "The weight of the specified entity while feeding into the parent.";
    }

    typedef hierarchy-level {
        type int32 {
            range "1..8";
        }
        description "The level of the specified entity while feeding into the parent.";
    }

    typedef dot1p-priority {
        type int32 {
            range "0..7";
        }
        description "IEEE 802.1p priority. Zero is lowest, seven is highest.";
    }

    typedef lsp-exp-value {
        type int32 {
            range "0..7";
        }
        description "MPLS Experimental bits.";
    }

    typedef atm-vc-indentifier {
        type int32 {
            range "1..65535";
        }
        description "The VCI value for a VCL.";
    }

    typedef burst-percent {
        type union {
            type int32 {
                range "0..100";
            }
            type enumeration {
                enum "auto"                         { value -1; }
            }
        }
        default "auto";
        description
            "The percentage of buffer space assigned to a queue that is
             reserved for some purpose.
             The value of 'default' means that the actual value is derived
             from the corresponding buffer policy's default value.";
    }

    typedef burst-percent-or-default-override {
        type union {
            type uint32 {
                range "0..100";
            }
            type enumeration {
                enum "auto"                         { value -1; }
            }
        }
        description
            "The percentage of buffer space assigned to a queue that is
             reserved for some purpose.
             The value of 'default' means that the actual value is derived
             from the corresponding buffer policy's default value.";
    }

    typedef de-value {
        type int32 {
            range "0..1";
        }
        description "Specifies the DE (Drop Eligible) bit value.";
    }

    typedef egress-hsmda-counter-id {
        type uint32 {
            range "1..8";
        }
        description "The identification number of a HSMDA egress counter.";
    }

    typedef queue-pir-rate {
        type union {
            type int32 {
                range "1..2000000000";
            }
            type enumeration {
                enum "max"                          { value -1; }
            }
        }
        description "The PIR rate to be used in kbps.";
    }

    typedef hs-pir-rate-override {
        type union {
            type int32 {
                range "1..100000";
            }
            type enumeration {
                enum "max"                          { value -1; }
            }
        }
        description "The HS PIR rate to be used in Mbps.";
    }

    typedef pir-percent-override {
        type decimal64 {
            range "0.01..100.00";
            fraction-digits 2;
        }
        description "The PIR override specified as a percent.";
    }

    typedef pir-rate-override {
        type union {
            type int32 {
                range "1..100000000";
            }
            type enumeration {
                enum "max"                          { value -1; }
            }
        }
        description "The PIR rate to be used in kbps.";
    }

    typedef queue-pir-rate-override {
        type union {
            type int32 {
                range "1..2000000000";
            }
            type enumeration {
                enum "max"                          { value -1; }
            }
        }
        description "The PIR rate to be used in kbps.";
    }

    typedef cir-percent-override {
        type decimal64 {
            range "0.00..100.00";
            fraction-digits 2;
        }
        description "The CIR override specified as a percent.";
    }

    typedef queue-cir-rate {
        type union {
            type int32 {
                range "0..2000000000";
            }
            type enumeration {
                enum "max"                          { value -1; }
            }
        }
        description "The CIR rate to be used in kbps.";
    }

    typedef queue-cir-rate-override {
        type union {
            type int32 {
                range "0..2000000000";
            }
            type enumeration {
                enum "max"                          { value -1; }
            }
        }
        description "The CIR rate to be used in kbps.";
    }

    typedef policer-pir-rate {
        type union {
            type int32 {
                range "1..2000000000";
            }
            type enumeration {
                enum "max"                          { value -1; }
            }
        }
        description "The PIR rate to be used in kbps.";
    }

    typedef policer-pir-rate-override {
        type union {
            type int32 {
                range "1..2000000000";
            }
            type enumeration {
                enum "max"                          { value -1; }
            }
        }
        description "The PIR rate to be used in kbps.";
    }

    typedef isa-policer-pir-rate {
        type union {
            type kilobytes {
                range "1..100000000";
            }
            type enumeration {
                enum "max"                          { value -1; }
            }
        }
        units "kilobps";
        description "Peak Information Rate for an ISA policer";
    }

    typedef policer-cir-rate {
        type union {
            type int32 {
                range "0..2000000000";
            }
            type enumeration {
                enum "max"                          { value -1; }
            }
        }
        description "The CIR rate to be used in kbps.";
    }

    typedef policer-cir-rate-override {
        type union {
            type int32 {
                range "0..2000000000";
            }
            type enumeration {
                enum "max"                          { value -1; }
            }
        }
        description "The CIR rate to be used in kbps.";
    }

    typedef isa-policer-cir-rate {
        type union {
            type kilobytes {
                range "0..100000000";
            }
            type enumeration {
                enum "max"                          { value -1; }
            }
        }
        units "kilobps";
        description "Committed Information Rate for an ISA policer";
    }

    typedef burst-limit-override {
        type union {
            type types-qos:bytes {
                range "1..14000000";
            }
            type enumeration {
                enum "auto"                         { value -1; }
            }
        }
        description "The burst limit override.";
    }

    typedef burst-size-override {
        type union {
            type types-qos:kilobytes {
                range "0..1048576";
            }
            type enumeration {
                enum "auto"                         { value -1; }
            }
        }
        description "The amount of buffer space reserved.";
    }

    typedef plcr-burst-size {
        type union {
            type types-qos:bytes {
                range "0..268435456";
            }
            type enumeration {
                enum "auto"                         { value -1; }
            }
        }
        units "bytes";
        default "auto";
        description "The amount of burst capacity assigned to a policer in bytes.";
    }

    typedef policer-burst-size-override {
        type union {
            type types-qos:bytes {
                range "0..16777216";
            }
            type enumeration {
                enum "auto"                         { value -1; }
            }
        }
        description
            "The amount of buffer space (in bytes) assigned to a queue by
             policer.";
    }

    typedef policer-burst-size-override-max {
        type union {
            type types-qos:bytes {
                range "0..268435456";
            }
            type enumeration {
                enum "auto"                         { value -1; }
            }
        }
        units "bytes";
        description
            "The amount of buffer space (in bytes) assigned to a queue by
             policer.";
    }

    typedef queue-burst-size-override {
        type union {
            type types-qos:bytes {
                range "0..1073741824";
            }
            type enumeration {
                enum "auto"                         { value -1; }
            }
        }
        description "The amount of buffer space (in bytes) assigned to a queue.";
    }

    typedef queue-burst-size-override-max {
        type union {
            type types-qos:bytes {
                range "0..max";
            }
            type enumeration {
                enum "auto"                         { value -1; }
            }
        }
        description "The amount of buffer space (in bytes) assigned to a queue.";
    }

    typedef queue-burst-size-64-override-max {
        type union {
            type int64 {
                range "0..max";
            }
            type enumeration {
                enum "auto"                         { value -1; }
            }
        }
        description "The amount of buffer space (in bytes) assigned to a queue.";
    }

    typedef hsmda-queue-pir-rate {
        type union {
            type int32 {
                range "1..100000000";
            }
            type enumeration {
                enum "max"                          { value -1; }
            }
        }
        description "The HSMDA PIR rate to be used in kbps.";
    }

    typedef hsmda-queue-pir-rate-override {
        type union {
            type int32 {
                range "1..100000000";
            }
            type enumeration {
                enum "max"                          { value -1; }
            }
        }
        description "The HSMDA PIR rate to be used in kbps.";
    }

    typedef hsmda-queue-burst-size {
        type union {
            type types-qos:bytes {
                range "0..2688000";
            }
            type enumeration {
                enum "auto"                         { value -1; }
            }
        }
        default "auto";
        description "The amount of buffer space (in bytes) assigned to an HSMDA queue.";
    }

    typedef hsmda-queue-burst-size-override {
        type union {
            type types-qos:bytes {
                range "0..2688000";
            }
            type enumeration {
                enum "auto"                         { value -1; }
            }
        }
        description "The amount of buffer space (in bytes) assigned to an HSMDA queue.";
    }

    typedef hsmda-wrr-weight {
        type uint32 {
            range "1..32";
        }
        description
            "Specifies the Weighted Round Robin (WRR) weight with which this queue should
             parent into the scheduler.";
    }

    typedef port-qos-policy-wrr-weight {
        type uint32 {
            range "1..255";
        }
        description
            "Specifies the Weighted Round Robin (WRR) weight profile
             with which this queue should parent into the port scheduler.";
    }

    typedef hsmda-wrr-weight-override {
        type int32 {
            range "1..32";
        }
        description
            "Specifies the Weighted Round Robin (WRR) weight with which this queue should
             parent into the scheduler.";
    }

    typedef tcp-udp-match-port {
        type int32 {
            range "0|1..65535";
        }
        description
            "The number of a TCP or UDP port.
             Well known port numbers include ftp-data(20), ftp(21), telnet(23),
             smtp(25), http(80), pop3(110), nntp(119), snmp(161), snmptrap(162), etc.";
    }

    typedef dscp-name {
        type enumeration {
            enum "be"                           { value 0; }
            enum "cp1"                          { value 1; }
            enum "cp2"                          { value 2; }
            enum "cp3"                          { value 3; }
            enum "cp4"                          { value 4; }
            enum "cp5"                          { value 5; }
            enum "cp6"                          { value 6; }
            enum "cp7"                          { value 7; }
            enum "cs1"                          { value 8; }
            enum "cp9"                          { value 9; }
            enum "af11"                         { value 10; }
            enum "cp11"                         { value 11; }
            enum "af12"                         { value 12; }
            enum "cp13"                         { value 13; }
            enum "af13"                         { value 14; }
            enum "cp15"                         { value 15; }
            enum "cs2"                          { value 16; }
            enum "cp17"                         { value 17; }
            enum "af21"                         { value 18; }
            enum "cp19"                         { value 19; }
            enum "af22"                         { value 20; }
            enum "cp21"                         { value 21; }
            enum "af23"                         { value 22; }
            enum "cp23"                         { value 23; }
            enum "cs3"                          { value 24; }
            enum "cp25"                         { value 25; }
            enum "af31"                         { value 26; }
            enum "cp27"                         { value 27; }
            enum "af32"                         { value 28; }
            enum "cp29"                         { value 29; }
            enum "af33"                         { value 30; }
            enum "cp31"                         { value 31; }
            enum "cs4"                          { value 32; }
            enum "cp33"                         { value 33; }
            enum "af41"                         { value 34; }
            enum "cp35"                         { value 35; }
            enum "af42"                         { value 36; }
            enum "cp37"                         { value 37; }
            enum "af43"                         { value 38; }
            enum "cp39"                         { value 39; }
            enum "cs5"                          { value 40; }
            enum "cp41"                         { value 41; }
            enum "cp42"                         { value 42; }
            enum "cp43"                         { value 43; }
            enum "cp44"                         { value 44; }
            enum "cp45"                         { value 45; }
            enum "ef"                           { value 46; }
            enum "cp47"                         { value 47; }
            enum "nc1"                          { value 48; }
            enum "cp49"                         { value 49; }
            enum "cp50"                         { value 50; }
            enum "cp51"                         { value 51; }
            enum "cp52"                         { value 52; }
            enum "cp53"                         { value 53; }
            enum "cp54"                         { value 54; }
            enum "cp55"                         { value 55; }
            enum "nc2"                          { value 56; }
            enum "cp57"                         { value 57; }
            enum "cp58"                         { value 58; }
            enum "cp59"                         { value 59; }
            enum "cp60"                         { value 60; }
            enum "cp61"                         { value 61; }
            enum "cp62"                         { value 62; }
            enum "cp63"                         { value 63; }
        }
        description "The name of Differentiated Services Code Point (DSCP).";
    }

    typedef ingress-queuing-type {
        type enumeration {
            enum "service"                      { value 1; }
            enum "shared"                       { value 2; }
            enum "multipoint-shared"            { value 3; }
        }
        description "The ingress queuing type.";
    }

    typedef hs-wrr-group-id {
        type uint32 {
            range "1..2";
        }
        description "The HS WRR group identifier.";
    }

    typedef hs-class-weight {
        type uint32 {
            range "1|2|4|8";
        }
        description "The HS scheduling class weight.";
    }

    typedef hs-class-weight-override {
        type int32 {
            range "1|2|4|8";
        }
        description "The HS scheduling class weight override.";
    }

    typedef hs-wrr-rate-override {
        type union {
            type uint32 {
                range "1..2000000000";
            }
            type enumeration {
                enum "max"                          { value -1; }
            }
        }
        description "The HS WRR rate override.";
    }

    typedef precedence-value {
        type int32 {
            range "0..7";
        }
        description "The Precedence value for which mapping is done.";
    }

    typedef hs-wrr-weight {
        type uint32 {
            range "1..127";
        }
        description
            "Specifies the Weighted Round Robin (WRR) weight with which this queue should
             parent into the scheduler.";
    }

    typedef hs-wrr-weight-override {
        type int32 {
            range "1..127";
        }
        description
            "Specifies the Weighted Round Robin (WRR) weight with which this queue should
             parent into the scheduler.";
    }

    typedef scheduler-pir-rate {
        type union {
            type uint32 {
                range "1..3200000000";
            }
            type enumeration {
                enum "max"                          { value -1; }
            }
        }
        description "Specifies the PIR rate of a virtual scheduler.";
    }

    typedef scheduler-pir-rate-override {
        type union {
            type uint32 {
                range "1..3200000000";
            }
            type enumeration {
                enum "max"                          { value -1; }
            }
        }
        description "Specifies the PIR rate override of a virtual scheduler.";
    }

    typedef scheduler-cir-rate {
        type union {
            type uint32 {
                range "0..3200000000";
            }
            type enumeration {
                enum "sum"                          { value -3; }
                enum "max"                          { value -1; }
            }
        }
        description "Specifies the CIR rate of a virtual scheduler.";
    }

    typedef scheduler-cir-rate-override {
        type union {
            type uint32 {
                range "0..3200000000";
            }
            type enumeration {
                enum "sum"                          { value -3; }
                enum "max"                          { value -1; }
            }
        }
        description "Specifies the CIR rate override of a virtual scheduler.";
    }

    typedef atm-traffic-descr-idx {
        type int32 {
            range "1..1000";
        }
        description "ATM Traffic Descriptor Identifier.";
    }

    typedef mac-criteria-type {
        type enumeration {
            enum "normal"                       { value 1; }
            enum "vid"                          { value 3; }
        }
        description "Possible types of MAC filters provided by the system.";
    }

    typedef bgp-shared-queue-pir-rate {
        type union {
            type kilobytes {
                range "1..100000000";
            }
            type enumeration {
                enum "max"                          { value -1; }
            }
        }
        units "kilobps";
        description "Peak Information Rate for an vprn bgp shared-queue";
    }

    typedef bgp-shared-queue-cir-rate {
        type union {
            type kilobytes {
                range "0..100000000";
            }
            type enumeration {
                enum "max"                          { value -1; }
            }
        }
        units "kilobps";
        description "Committed Information Rate for an vprn bgp shared-queue";
    }

    typedef class-burst-limit {
        type int32 {
            range "1..327680";
        }
        description
            "An explicit shaping burst size for a class. The default represents that
             the actual value is derived from the corresponding class's default.";
    }

    typedef secondary-shaper-pir-rate {
        type union {
            type kilobytes {
                range "1..10000000";
            }
            type enumeration {
                enum "max"                          { value -1; }
            }
        }
        units "kilobps";
        description "The secondary shaper PIR rate to be used in kbps.";
    }

    typedef secondary-shaper-class-threshold {
        type kilobytes {
            range "0..8190";
        }
        description "The secondary shaper class threshold.";
    }

    typedef internal-scheduler-weight-mode {
        type enumeration {
            enum "auto"                         { value 2; }
            enum "force-equal"                  { value 3; }
            enum "offered-load"                 { value 4; }
            enum "capped-offered-load"          { value 5; }
        }
        description
            "Specifies the weight-mode applied to queues using internal-scheduler.
             Various modes can be enumerated as follows:

                auto                - queues are equally weighted except at ingress
                                      for mixed-speed LAGs without per-fp-inq-queuing
                                      enabled, and at egress for mixed-speed LAGs,
                                      in which cases the queues are weighted based on
                                      port-speed
                force-equal         - all queues are always equally weighted
                offered-load        - queues are weighted based on offered load
                capped-offered-load - queues are weighted based on offered load
                                      capped by admin PIR";
    }

    typedef rate-limit {
        type union {
            type int32 {
                range "0..2147483647";
            }
            type enumeration {
                enum "max"                          { value -1; }
            }
        }
        description "The rate limit applied, in kbps.";
    }

    typedef queue-pir-rate-maximum {
        type union {
            type int64 {
                range "1..6400000000";
            }
            type enumeration {
                enum "max"                          { value -1; }
            }
        }
        description "The PIR rate to be used in kbps.";
    }

    typedef int-max {
        type union {
            type enumeration {
                enum "max"                          { value -1; }
            }
            type int64;
        }
        description "Maximum 64-bit value with max as -1";
    }

    typedef queue-cir-rate-maximum {
        type union {
            type int64 {
                range "0..6400000000";
            }
            type enumeration {
                enum "max"                          { value -1; }
            }
        }
        description "The CIR rate to be used in kbps.";
    }

    typedef queue-fir-rate-maximum {
        type union {
            type int64 {
                range "0..6400000000";
            }
            type enumeration {
                enum "max"                          { value -1; }
            }
        }
        description "The FIR rate to be used in kbps.";
    }

    typedef policer-pir-rate-maximum {
        type union {
            type int64 {
                range "1..6400000000";
            }
            type enumeration {
                enum "max"                          { value -1; }
            }
        }
        description "The PIR rate to be used in kbps.";
    }

    typedef policer-cir-rate-maximum {
        type union {
            type int64 {
                range "0..6400000000";
            }
            type enumeration {
                enum "max"                          { value -1; }
            }
        }
        description "The CIR rate to be used in kbps.";
    }

    typedef sched-cir-percent-rate {
        type union {
            type enumeration {
                enum "sum"                          { value -3; }
            }
            type decimal64 {
                range "0.00..100.00";
                fraction-digits 2;
            }
        }
        description "The CIR percent rate for scheduler policy.";
    }

    typedef max-rate {
        type union {
            type int64 {
                range "1..6400000000";
            }
            type enumeration {
                enum "max"                          { value -1; }
            }
        }
        description "The maximum frame based bandwidth limit.";
    }

    typedef sched-pir-rate {
        type union {
            type int64 {
                range "1..6400000000";
            }
            type enumeration {
                enum "max"                          { value -1; }
            }
        }
        description "Specifies the PIR rate of a virtual scheduler with range of 6400G.";
    }

    typedef sched-cir-rate {
        type union {
            type int64 {
                range "0..6400000000";
            }
            type enumeration {
                enum "sum"                          { value -3; }
                enum "max"                          { value -1; }
            }
        }
        description "Specifies the CIR rate of a virtual scheduler with range of 6400G.";
    }

    typedef sched-pir-rate-ovr {
        type union {
            type int64 {
                range "1..6400000000";
            }
            type enumeration {
                enum "max"                          { value -1; }
            }
        }
        description "Specifies the PIR rate override of a virtual scheduler with range of 6400G.";
    }

    typedef sched-cir-rate-ovr {
        type union {
            type int64 {
                range "0..6400000000";
            }
            type enumeration {
                enum "sum"                          { value -3; }
                enum "max"                          { value -1; }
            }
        }
        description "Specifies the CIR rate override of a virtual scheduler with range of 6400G.";
    }

    typedef ing-class-remark-value {
        type enumeration {
            enum "any"                          { value 1; }
            enum "dot1p-exp"                    { value 2; }
        }
        description "Specifies the ingress classification policy remark values.";
    }

    typedef aggr-policer-rate {
        type union {
            type int32 {
                range "144..1000000000";
            }
            type enumeration {
                enum "max"                          { value -1; }
            }
        }
        description "The rate to be used in kbps. The value -1 means maximum rate.";
    }

    typedef aggr-policer-burst {
        type union {
            type int32 {
                range "1..33292";
            }
            type enumeration {
                enum "default"                      { value -1; }
            }
        }
        description "Specifies the burst to be used. The value -1 means maximum burst.";
    }

    typedef aggr-policer-cir {
        type union {
            type int32 {
                range "0..1000000000";
            }
            type enumeration {
                enum "max"                          { value -1; }
            }
        }
        description
            "The rate to be used in kbps. The value -1 means maximum cir.
             The value of -2 means cir is not configured";
    }

    typedef aggr-policer-cbs {
        type union {
            type int32 {
                range "1..33292";
            }
            type enumeration {
                enum "default"                      { value -1; }
            }
        }
        description
            "Specifies the cbs to be used. The value -1 means maximum cbs,
             the value -2 means cbs is not configured.";
    }

    typedef sap-ingress-policer-alloc {
        type enumeration {
            enum "none"                         { value 1; }
            enum "per-fc"                       { value 2; }
            enum "per-fc-unicast-multipoint"    { value 3; }
            enum "per-fc-unicast-multicast"     { value 4; }
            enum "per-fc-unicast-broadcast-unknown-multicast" { value 5; }
        }
        default "none";
        description "Specifies the fc-policer mapping type for this sap-ingress policy";
    }

    typedef network-ingress-policer-mode {
        type enumeration {
            enum "none"                         { value 1; }
            enum "per-fc"                       { value 2; }
            enum "per-fc-unicast-multicast"     { value 3; }
        }
        default "none";
        description "Specifies the fc-policer mapping type for this network-ingress policy";
    }

    typedef pkt-byte-offset {
        type int32 {
            range "4|8";
        }
        description
            "The number of bytes to add/subtract to accommodate for non-default MPLS header
             depth or asymmetrical VLAN operations.";
    }

    typedef queue-pir-rate-state-maximum {
        type union {
            type int64 {
                range "0..6400000000";
            }
            type enumeration {
                enum "max"                          { value -1; }
            }
        }
        description "The PIR rate to be used in kbps.";
    }

    typedef shaper-max-rate {
        type union {
            type int64 {
                range "1..6400000000";
            }
            type enumeration {
                enum "max"                          { value -1; }
            }
        }
        description "The maximum frame based bandwidth limit.";
    }

    typedef ingress-class-plcy-prof-attach {
        type enumeration {
            enum "any"                          { value 1; }
            enum "non-epipe"                    { value 2; }
        }
        default "any";
        description "Specifies the fc-policer mapping type for this network-ingress policy";
    }

    typedef packet-mode {
        type enumeration {
            enum "data-otw-otw"                 { value 0; }
            enum "lmotw-lmotw-otw-atm"          { value 1; }
            enum "lmotw-lmotw-otw-non-atm"      { value 2; }
            enum "otw-otw-otw"                  { value 3; }
            enum "data-data"                    { value 4; }
        }
        description "Specifies the packet-mode of an aggregate shaper";
    }

    typedef percent-rate-with-hundreds {
        type decimal64 {
            range "0.00..100.00";
            fraction-digits 2;
        }
        description "The percent rate with hundreds fraction";
    }

    typedef qgroup-egress-policer-id {
        type int32 {
            range "1..16";
        }
        description "The policer identifier on egress side.";
    }

    typedef color-oper {
        type enumeration {
            enum "green"                        { value 0; }
            enum "amber"                        { value 1; }
            enum "red"                          { value 2; }
        }
        description "The scaling of hw-agg-shaper members based on type color.";
    }

    typedef reflective-qos-indicator {
        type int32 {
            range "0..1";
        }
        description
            "This data type specifies the Reflective QoS Indicator (RQI) that is
             inserted along with the QoS Flow Identifier (QFI) in the header of
             data packets of a flow.";
    }

    typedef qos-flow-identifier {
        type int32 {
            range "0..63";
        }
        description
            "This data type specifies the QoS Flow Identifier (QFI) that is
             inserted along with the Reflective QoS Indicator (RQI) in the
             header of data packets of a flow.";
    }

    typedef shared-policer-pir-rate-maximum {
        type union {
            type int64 {
                range "0|144..400000000";
            }
            type enumeration {
                enum "max"                          { value -1; }
            }
        }
        description "The PIR rate to be used in kbps.";
    }

    typedef shared-policer-cir-rate-maximum {
        type union {
            type int64 {
                range "0..400000000";
            }
            type enumeration {
                enum "max"                          { value -1; }
            }
        }
        description "The CIR rate to be used in kbps.";
    }

    typedef shared-plcr-burst-size {
        type union {
            type types-qos:bytes {
                range "1..4194304";
            }
            type enumeration {
                enum "auto"                         { value -1; }
            }
        }
        units "bytes";
        default "auto";
        description "The amount of burst capacity assigned to a policer in bytes.";
    }

}
