submodule nokia-conf-svc-cpipe {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }

    include nokia-conf-bfd;
    include nokia-conf-groups;
    include nokia-conf-log;
    include nokia-conf-port;
    include nokia-conf-port-eth-access;
    include nokia-conf-port-ethernet;
    include nokia-conf-qos;
    include nokia-conf-service;
    include nokia-conf-system;
    include nokia-conf-system-security;

    sros-ext:sros-major-release "rel23";
    organization "Nokia";
    contact
        "Nokia SR OS Support
         Web: <http://www.nokia.com>";
    description
        "Nokia YANG Data model to configure cpipe services on SR OS based routers.

         Copyright 2016 Nokia. All rights reserved. Reproduction of this document
         is authorized on the condition that the foregoing copyright notice is included.

         This nokia-conf-svc-cpipe YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-07";

    grouping conf-svc-cpipe {
        ///nokia-conf/configure/service/cpipe
        list cpipe {
            key "service-name";
            description "Enter the cpipe list instance";

            ///nokia-conf/configure/service/cpipe/service-name
            leaf service-name {
                type types-services:service-name;
                description "Administrative service name";
            }

            ///nokia-conf/configure/service/cpipe/service-id
            leaf service-id {
                type types-services:external-service-id;
                sros-ext:immutable;
                description "Service ID";
            }

            ///nokia-conf/configure/service/cpipe/description
            leaf description {
                type types-sros:description;
                description "Text description";
            }

            ///nokia-conf/configure/service/cpipe/customer
            leaf customer {
                type leafref {
                    path "../../customer/customer-name";
                }
                sros-ext:immutable;
                mandatory true;
                description "Service customer ID";
            }

            ///nokia-conf/configure/service/cpipe/admin-state
            leaf admin-state {
                type types-sros:admin-state;
                default "disable";
                description "Administrative state of the service";
            }

            ///nokia-conf/configure/service/cpipe/vpn-id
            leaf vpn-id {
                type types-services:vpn-id;
                sros-ext:immutable;
                description "VPN identifier for the service";
            }

            ///nokia-conf/configure/service/cpipe/vc-type
            leaf vc-type {
                type types-services:cpipe-vc-type;
                sros-ext:immutable;
                description "Circuit emulation service type";
            }

            ///nokia-conf/configure/service/cpipe/vc-switching
            leaf vc-switching {
                type boolean;
                sros-ext:immutable;
                default "false";
                description "Use PW switching signaling for spoke SDPs in service";
            }

            ///nokia-conf/configure/service/cpipe/test
            leaf test {
                type boolean;
                sros-ext:immutable;
                default "false";
                description "Designate as a test service";
            }

            ///nokia-conf/configure/service/cpipe/service-mtu
            leaf service-mtu {
                type int32 {
                    range "1..9194";
                }
                description "MTU size";
            }

            ///nokia-conf/configure/service/cpipe/apply-groups
            leaf-list apply-groups {
                type leafref {
                    path "../../../groups/group/name";
                }
                max-elements 8;
                ordered-by user;
                description "Apply a configuration group at this level";
            }

            ///nokia-conf/configure/service/cpipe/apply-groups-exclude
            leaf-list apply-groups-exclude {
                type leafref {
                    path "../../../groups/group/name";
                }
                max-elements 8;
                ordered-by user;
                description "Exclude a configuration group at this level";
            }

            ///nokia-conf/configure/service/cpipe/endpoint
            list endpoint {
                key "name";
                max-elements 2;
                description "Enter the endpoint list instance";

                ///nokia-conf/configure/service/cpipe/endpoint/name
                leaf name {
                    type types-sros:named-item;
                    description "Service endpoint name";
                }

                ///nokia-conf/configure/service/cpipe/endpoint/description
                leaf description {
                    type types-sros:description;
                    description "Text description";
                }

                ///nokia-conf/configure/service/cpipe/endpoint/revert-time
                leaf revert-time {
                    type types-services:revert-time;
                    default "immediate";
                    description "Time to wait before reverting to primary spoke SDP";
                }

                ///nokia-conf/configure/service/cpipe/endpoint/hold-time-active
                leaf hold-time-active {
                    type types-services:hold-time-active;
                    description "Time before entering standby when MC-LAG SAP goes down";
                }

                ///nokia-conf/configure/service/cpipe/endpoint/standby-signaling
                leaf standby-signaling {
                    type enumeration {
                        enum master                         { value 1; }
                        enum slave                          { value 2; }
                    }
                    description "Status of whether PW standby bit is sent to T-LDP peer";
                }

                ///nokia-conf/configure/service/cpipe/endpoint/apply-groups
                leaf-list apply-groups {
                    type leafref {
                        path "../../../../groups/group/name";
                    }
                    max-elements 8;
                    ordered-by user;
                    description "Apply a configuration group at this level";
                }

                ///nokia-conf/configure/service/cpipe/endpoint/apply-groups-exclude
                leaf-list apply-groups-exclude {
                    type leafref {
                        path "../../../../groups/group/name";
                    }
                    max-elements 8;
                    ordered-by user;
                    description "Exclude a configuration group at this level";
                }

            } // list endpoint

            ///nokia-conf/configure/service/cpipe/sap
            list sap {
                key "sap-id";
                description "Enter the sap list instance";

                ///nokia-conf/configure/service/cpipe/sap/sap-id
                leaf sap-id {
                    type types-sros:sap;
                    description "SAP ID";
                }

                ///nokia-conf/configure/service/cpipe/sap/description
                leaf description {
                    type types-sros:long-description;
                    description "Text description";
                }

                ///nokia-conf/configure/service/cpipe/sap/admin-state
                leaf admin-state {
                    type types-sros:admin-state;
                    default "enable";
                    description "Administrative state of the SAP";
                }

                ///nokia-conf/configure/service/cpipe/sap/accounting-policy
                leaf accounting-policy {
                    type leafref {
                        path "../../../../log/accounting-policy/policy-id";
                    }
                    description "Accounting policy";
                }

                ///nokia-conf/configure/service/cpipe/sap/collect-stats
                leaf collect-stats {
                    type boolean;
                    default "false";
                    description "Collect accounting statistics";
                }

                ///nokia-conf/configure/service/cpipe/sap/dist-cpu-protection
                leaf dist-cpu-protection {
                    type leafref {
                        path "../../../../system/security/dist-cpu-protection/policy/policy-name";
                    }
                    description "Distributed CPU protection policy for SAP";
                }

                ///nokia-conf/configure/service/cpipe/sap/multi-service-site
                leaf multi-service-site {
                    type leafref {
                        path "../../../customer/multi-service-site/multi-service-site-name";
                    }
                    description "Multi service site name";
                }

                ///nokia-conf/configure/service/cpipe/sap/endpoint
                leaf endpoint {
                    type leafref {
                        path "../../endpoint/name";
                    }
                    description "Endpoint name";
                }

                ///nokia-conf/configure/service/cpipe/sap/apply-groups
                leaf-list apply-groups {
                    type leafref {
                        path "../../../../groups/group/name";
                    }
                    max-elements 8;
                    ordered-by user;
                    description "Apply a configuration group at this level";
                }

                ///nokia-conf/configure/service/cpipe/sap/apply-groups-exclude
                leaf-list apply-groups-exclude {
                    type leafref {
                        path "../../../../groups/group/name";
                    }
                    max-elements 8;
                    ordered-by user;
                    description "Exclude a configuration group at this level";
                }

                ///nokia-conf/configure/service/cpipe/sap/ingress
                container ingress {
                    description "Enter the ingress context";

                    ///nokia-conf/configure/service/cpipe/sap/ingress/qos
                    container qos {
                        description "Enter the qos context";

                        ///nokia-conf/configure/service/cpipe/sap/ingress/qos/sap-ingress
                        container sap-ingress {
                            description "Enter the sap-ingress context";

                            ///nokia-conf/configure/service/cpipe/sap/ingress/qos/sap-ingress/policy-name
                            leaf policy-name {
                                type leafref {
                                    path "../../../../../../../qos/sap-ingress/sap-ingress-policy-name";
                                }
                                description "Policy ID";
                            }

                            ///nokia-conf/configure/service/cpipe/sap/ingress/qos/sap-ingress/queuing-type
                            leaf queuing-type {
                                type types-services:services-sap-queuing-type;
                                description "Queuing type";
                            }

                            ///nokia-conf/configure/service/cpipe/sap/ingress/qos/sap-ingress/overrides
                            container overrides {
                                description "Enter the overrides context";

                                ///nokia-conf/configure/service/cpipe/sap/ingress/qos/sap-ingress/overrides/ip-criteria
                                container ip-criteria {
                                    description "Enter the ip-criteria context";

                                    ///nokia-conf/configure/service/cpipe/sap/ingress/qos/sap-ingress/overrides/ip-criteria/activate-entry-tag
                                    leaf activate-entry-tag {
                                        type int32 {
                                            range "1..255";
                                        }
                                        description "Tag ID activated for IPv4 criteria";
                                    }

                                } // container ip-criteria

                                ///nokia-conf/configure/service/cpipe/sap/ingress/qos/sap-ingress/overrides/ipv6-criteria
                                container ipv6-criteria {
                                    description "Enter the ipv6-criteria context";

                                    ///nokia-conf/configure/service/cpipe/sap/ingress/qos/sap-ingress/overrides/ipv6-criteria/activate-entry-tag
                                    leaf activate-entry-tag {
                                        type int32 {
                                            range "1..255";
                                        }
                                        description "Tag ID activated for IPv6 criteria";
                                    }

                                } // container ipv6-criteria

                                ///nokia-conf/configure/service/cpipe/sap/ingress/qos/sap-ingress/overrides/queue
                                list queue {
                                    key "queue-id";
                                    description "Enter the queue list instance";

                                    ///nokia-conf/configure/service/cpipe/sap/ingress/qos/sap-ingress/overrides/queue/queue-id
                                    leaf queue-id {
                                        type leafref {
                                            path "../../../../../../../../../qos/sap-ingress[sap-ingress-policy-name=current()/../../../policy-name]/queue/queue-id";
                                        }
                                        description "Policer unique ID";
                                    }

                                    ///nokia-conf/configure/service/cpipe/sap/ingress/qos/sap-ingress/overrides/queue/cbs
                                    leaf cbs {
                                        type union {
                                            type uint32 {
                                                range "0..1048576";
                                            }
                                            type enumeration {
                                                enum auto                           { value -1; }
                                            }
                                        }
                                        units "kilobytes";
                                        description "CBS";
                                    }

                                    ///nokia-conf/configure/service/cpipe/sap/ingress/qos/sap-ingress/overrides/queue/mbs
                                    leaf mbs {
                                        type union {
                                            type types-qos:bytes {
                                                range "0..1073741824";
                                            }
                                            type enumeration {
                                                enum auto                           { value -1; }
                                            }
                                        }
                                        units "bytes";
                                        description "MBS";
                                    }

                                    ///nokia-conf/configure/service/cpipe/sap/ingress/qos/sap-ingress/overrides/queue/monitor-depth
                                    leaf monitor-depth {
                                        status obsolete;
                                        type boolean;
                                        default "false";
                                        description "Monitor queue depth";
                                    }

                                    ///nokia-conf/configure/service/cpipe/sap/ingress/qos/sap-ingress/overrides/queue/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/ingress/qos/sap-ingress/overrides/queue/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/ingress/qos/sap-ingress/overrides/queue/queue-override-rate
                                    choice queue-override-rate {
                                        ///nokia-conf/configure/service/cpipe/sap/ingress/qos/sap-ingress/overrides/queue/queue-override-rate/rate
                                        case rate {

                                            ///nokia-conf/configure/service/cpipe/sap/ingress/qos/sap-ingress/overrides/queue/queue-override-rate/rate/rate
                                            container rate {
                                                description "Enter the rate context";

                                                ///nokia-conf/configure/service/cpipe/sap/ingress/qos/sap-ingress/overrides/queue/queue-override-rate/rate/rate/pir
                                                leaf pir {
                                                    type types-services:sap-pir-rate-ovr;
                                                    units "kilobps";
                                                    description "PIR rate";
                                                }

                                                ///nokia-conf/configure/service/cpipe/sap/ingress/qos/sap-ingress/overrides/queue/queue-override-rate/rate/rate/cir
                                                leaf cir {
                                                    type types-services:sap-cir-rate-ovr;
                                                    units "kilobps";
                                                    description "CIR rate";
                                                }

                                            } // container rate

                                        }
                                        ///nokia-conf/configure/service/cpipe/sap/ingress/qos/sap-ingress/overrides/queue/queue-override-rate/percent-rate
                                        case percent-rate {

                                            ///nokia-conf/configure/service/cpipe/sap/ingress/qos/sap-ingress/overrides/queue/queue-override-rate/percent-rate/percent-rate
                                            container percent-rate {
                                                description "Enter the percent-rate context";

                                                ///nokia-conf/configure/service/cpipe/sap/ingress/qos/sap-ingress/overrides/queue/queue-override-rate/percent-rate/percent-rate/pir
                                                leaf pir {
                                                    type decimal64 {
                                                        range "0.01..100.00";
                                                        fraction-digits 2;
                                                    }
                                                    description "PIR percent rate";
                                                }

                                                ///nokia-conf/configure/service/cpipe/sap/ingress/qos/sap-ingress/overrides/queue/queue-override-rate/percent-rate/percent-rate/cir
                                                leaf cir {
                                                    type decimal64 {
                                                        range "0.00..100.00";
                                                        fraction-digits 2;
                                                    }
                                                    description "CIR percent rate";
                                                }

                                            } // container percent-rate

                                        }
                                    }
                                    ///nokia-conf/configure/service/cpipe/sap/ingress/qos/sap-ingress/overrides/queue/adaptation-rule
                                    container adaptation-rule {
                                        description "Enter the adaptation-rule context";

                                        ///nokia-conf/configure/service/cpipe/sap/ingress/qos/sap-ingress/overrides/queue/adaptation-rule/pir
                                        leaf pir {
                                            type types-qos:adaptation-rule-override;
                                            description "Constraint used when deriving the operational PIR value";
                                        }

                                        ///nokia-conf/configure/service/cpipe/sap/ingress/qos/sap-ingress/overrides/queue/adaptation-rule/cir
                                        leaf cir {
                                            type types-qos:adaptation-rule-override;
                                            description "Constraint used when deriving the operational CIR value";
                                        }

                                    } // container adaptation-rule

                                    ///nokia-conf/configure/service/cpipe/sap/ingress/qos/sap-ingress/overrides/queue/drop-tail
                                    container drop-tail {
                                        description "Enter the drop-tail context";

                                        ///nokia-conf/configure/service/cpipe/sap/ingress/qos/sap-ingress/overrides/queue/drop-tail/low
                                        container low {
                                            description "Enter the low context";

                                            ///nokia-conf/configure/service/cpipe/sap/ingress/qos/sap-ingress/overrides/queue/drop-tail/low/percent-reduction-from-mbs
                                            leaf percent-reduction-from-mbs {
                                                type types-qos:burst-percent-or-default-override;
                                                description "Percentage reduction from the MBS for a queue drop tail";
                                            }

                                        } // container low

                                    } // container drop-tail

                                    ///nokia-conf/configure/service/cpipe/sap/ingress/qos/sap-ingress/overrides/queue/parent
                                    container parent {
                                        description "Enter the parent context";

                                        ///nokia-conf/configure/service/cpipe/sap/ingress/qos/sap-ingress/overrides/queue/parent/weight
                                        leaf weight {
                                            type types-qos:weight-override;
                                            description "PIR parameter that overrides parent for queue group";
                                        }

                                        ///nokia-conf/configure/service/cpipe/sap/ingress/qos/sap-ingress/overrides/queue/parent/cir-weight
                                        leaf cir-weight {
                                            type types-qos:weight-override;
                                            description "CIR parameter that overrides parent for queue group";
                                        }

                                    } // container parent

                                    ///nokia-conf/configure/service/cpipe/sap/ingress/qos/sap-ingress/overrides/queue/monitor-queue-depth
                                    container monitor-queue-depth {
                                        presence "Enable the monitor-queue-depth context";
                                        description "Enable the monitor-queue-depth context";

                                        ///nokia-conf/configure/service/cpipe/sap/ingress/qos/sap-ingress/overrides/queue/monitor-queue-depth/fast-polling
                                        leaf fast-polling {
                                            type boolean;
                                            default "false";
                                            description "Enable fast polling of the queue depth";
                                        }

                                    } // container monitor-queue-depth

                                } // list queue

                                ///nokia-conf/configure/service/cpipe/sap/ingress/qos/sap-ingress/overrides/policer
                                list policer {
                                    key "policer-id";
                                    description "Enter the policer list instance";

                                    ///nokia-conf/configure/service/cpipe/sap/ingress/qos/sap-ingress/overrides/policer/policer-id
                                    leaf policer-id {
                                        type leafref {
                                            path "../../../../../../../../../qos/sap-ingress[sap-ingress-policy-name=current()/../../../policy-name]/policer/policer-id";
                                        }
                                        description "Policer unique ID";
                                    }

                                    ///nokia-conf/configure/service/cpipe/sap/ingress/qos/sap-ingress/overrides/policer/cbs
                                    leaf cbs {
                                        type types-qos:policer-burst-size-override-max;
                                        description "CBS";
                                    }

                                    ///nokia-conf/configure/service/cpipe/sap/ingress/qos/sap-ingress/overrides/policer/mbs
                                    leaf mbs {
                                        type types-qos:policer-burst-size-override-max;
                                        description "MBS";
                                    }

                                    ///nokia-conf/configure/service/cpipe/sap/ingress/qos/sap-ingress/overrides/policer/packet-byte-offset
                                    leaf packet-byte-offset {
                                        type types-qos:ingress-per-packet-offset-override;
                                        description "Packet size modification for policing information";
                                    }

                                    ///nokia-conf/configure/service/cpipe/sap/ingress/qos/sap-ingress/overrides/policer/stat-mode
                                    leaf stat-mode {
                                        type types-qos:ingress-policer-stat-mode;
                                        description "Mode of statistics collected by the policer";
                                    }

                                    ///nokia-conf/configure/service/cpipe/sap/ingress/qos/sap-ingress/overrides/policer/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/ingress/qos/sap-ingress/overrides/policer/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/ingress/qos/sap-ingress/overrides/policer/policer-override-rate
                                    choice policer-override-rate {
                                        ///nokia-conf/configure/service/cpipe/sap/ingress/qos/sap-ingress/overrides/policer/policer-override-rate/rate
                                        case rate {

                                            ///nokia-conf/configure/service/cpipe/sap/ingress/qos/sap-ingress/overrides/policer/policer-override-rate/rate/rate
                                            container rate {
                                                description "Enter the rate context";

                                                ///nokia-conf/configure/service/cpipe/sap/ingress/qos/sap-ingress/overrides/policer/policer-override-rate/rate/rate/pir
                                                leaf pir {
                                                    type union {
                                                        type int64 {
                                                            range "1..6400000000";
                                                        }
                                                        type enumeration {
                                                            enum max                            { value -1; }
                                                        }
                                                    }
                                                    units "kilobps";
                                                    description "PIR rate";
                                                }

                                                ///nokia-conf/configure/service/cpipe/sap/ingress/qos/sap-ingress/overrides/policer/policer-override-rate/rate/rate/cir
                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        ///nokia-conf/configure/service/cpipe/sap/ingress/qos/sap-ingress/overrides/policer/policer-override-rate/percent-rate
                                        case percent-rate {

                                            ///nokia-conf/configure/service/cpipe/sap/ingress/qos/sap-ingress/overrides/policer/policer-override-rate/percent-rate/percent-rate
                                            container percent-rate {
                                                description "Enter the percent-rate context";

                                                ///nokia-conf/configure/service/cpipe/sap/ingress/qos/sap-ingress/overrides/policer/policer-override-rate/percent-rate/percent-rate/pir
                                                leaf pir {
                                                    type decimal64 {
                                                        range "0.01..100.00";
                                                        fraction-digits 2;
                                                    }
                                                    description "PIR percent rate";
                                                }

                                                ///nokia-conf/configure/service/cpipe/sap/ingress/qos/sap-ingress/overrides/policer/policer-override-rate/percent-rate/percent-rate/cir
                                                leaf cir {
                                                    type decimal64 {
                                                        range "0.00..100.00";
                                                        fraction-digits 2;
                                                    }
                                                    description "CIR percent rate";
                                                }

                                            } // container percent-rate

                                        }
                                    }
                                } // list policer

                            } // container overrides

                        } // container sap-ingress

                        ///nokia-conf/configure/service/cpipe/sap/ingress/qos/policer-control-policy
                        container policer-control-policy {
                            description "Enter the policer-control-policy context";

                            ///nokia-conf/configure/service/cpipe/sap/ingress/qos/policer-control-policy/policy-name
                            leaf policy-name {
                                type leafref {
                                    path "../../../../../../../qos/policer-control-policy/policer-control-policy-name";
                                }
                                description "Policer control policy name";
                            }

                            ///nokia-conf/configure/service/cpipe/sap/ingress/qos/policer-control-policy/overrides
                            container overrides {
                                presence "Enable the overrides context";
                                description "Enable the overrides context";

                                ///nokia-conf/configure/service/cpipe/sap/ingress/qos/policer-control-policy/overrides/apply-groups
                                leaf-list apply-groups {
                                    type leafref {
                                        path "../../../../../../../../groups/group/name";
                                    }
                                    max-elements 8;
                                    ordered-by user;
                                    description "Apply a configuration group at this level";
                                }

                                ///nokia-conf/configure/service/cpipe/sap/ingress/qos/policer-control-policy/overrides/apply-groups-exclude
                                leaf-list apply-groups-exclude {
                                    type leafref {
                                        path "../../../../../../../../groups/group/name";
                                    }
                                    max-elements 8;
                                    ordered-by user;
                                    description "Exclude a configuration group at this level";
                                }

                                ///nokia-conf/configure/service/cpipe/sap/ingress/qos/policer-control-policy/overrides/root
                                container root {
                                    description "Enter the root context";

                                    ///nokia-conf/configure/service/cpipe/sap/ingress/qos/policer-control-policy/overrides/root/max-rate
                                    leaf max-rate {
                                        type types-services:sap-max-rate-ovr;
                                        description "Maximum frame-based bandwidth limit";
                                    }

                                    ///nokia-conf/configure/service/cpipe/sap/ingress/qos/policer-control-policy/overrides/root/priority-mbs-thresholds
                                    container priority-mbs-thresholds {
                                        description "Enter the priority-mbs-thresholds context";

                                        ///nokia-conf/configure/service/cpipe/sap/ingress/qos/policer-control-policy/overrides/root/priority-mbs-thresholds/min-thresh-separation
                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        ///nokia-conf/configure/service/cpipe/sap/ingress/qos/policer-control-policy/overrides/root/priority-mbs-thresholds/priority
                                        list priority {
                                            key "priority-level";
                                            description "Enter the priority list instance";

                                            ///nokia-conf/configure/service/cpipe/sap/ingress/qos/policer-control-policy/overrides/root/priority-mbs-thresholds/priority/priority-level
                                            leaf priority-level {
                                                type types-qos:hierarchy-level;
                                                description "Priority level";
                                            }

                                            ///nokia-conf/configure/service/cpipe/sap/ingress/qos/policer-control-policy/overrides/root/priority-mbs-thresholds/priority/mbs-contribution
                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            ///nokia-conf/configure/service/cpipe/sap/ingress/qos/policer-control-policy/overrides/root/priority-mbs-thresholds/priority/apply-groups
                                            leaf-list apply-groups {
                                                type leafref {
                                                    path "../../../../../../../../../../../groups/group/name";
                                                }
                                                max-elements 8;
                                                ordered-by user;
                                                description "Apply a configuration group at this level";
                                            }

                                            ///nokia-conf/configure/service/cpipe/sap/ingress/qos/policer-control-policy/overrides/root/priority-mbs-thresholds/priority/apply-groups-exclude
                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        ///nokia-conf/configure/service/cpipe/sap/ingress/qos/scheduler-policy
                        container scheduler-policy {
                            description "Enter the scheduler-policy context";

                            ///nokia-conf/configure/service/cpipe/sap/ingress/qos/scheduler-policy/policy-name
                            leaf policy-name {
                                type leafref {
                                    path "../../../../../../../qos/scheduler-policy/scheduler-policy-name";
                                }
                                description "Scheduler policy name";
                            }

                            ///nokia-conf/configure/service/cpipe/sap/ingress/qos/scheduler-policy/overrides
                            container overrides {
                                description "Enter the overrides context";

                                ///nokia-conf/configure/service/cpipe/sap/ingress/qos/scheduler-policy/overrides/scheduler
                                list scheduler {
                                    key "scheduler-name";
                                    description "Enter the scheduler list instance";

                                    ///nokia-conf/configure/service/cpipe/sap/ingress/qos/scheduler-policy/overrides/scheduler/scheduler-name
                                    leaf scheduler-name {
                                        type types-sros:named-item;
                                        description "Scheduler name";
                                    }

                                    ///nokia-conf/configure/service/cpipe/sap/ingress/qos/scheduler-policy/overrides/scheduler/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/ingress/qos/scheduler-policy/overrides/scheduler/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/ingress/qos/scheduler-policy/overrides/scheduler/parent
                                    container parent {
                                        description "Enter the parent context";

                                        ///nokia-conf/configure/service/cpipe/sap/ingress/qos/scheduler-policy/overrides/scheduler/parent/weight
                                        leaf weight {
                                            type types-qos:weight;
                                            description "Relative weight of the scheduler to feed the queue";
                                        }

                                        ///nokia-conf/configure/service/cpipe/sap/ingress/qos/scheduler-policy/overrides/scheduler/parent/cir-weight
                                        leaf cir-weight {
                                            type types-qos:weight;
                                            description "Weight used at the within-CIR port priority level";
                                        }

                                    } // container parent

                                    ///nokia-conf/configure/service/cpipe/sap/ingress/qos/scheduler-policy/overrides/scheduler/rate
                                    container rate {
                                        description "Enter the rate context";

                                        ///nokia-conf/configure/service/cpipe/sap/ingress/qos/scheduler-policy/overrides/scheduler/rate/pir
                                        leaf pir {
                                            type union {
                                                type int64 {
                                                    range "1..6400000000";
                                                }
                                                type enumeration {
                                                    enum max                            { value -1; }
                                                }
                                            }
                                            units "kilobps";
                                            description "PIR at which the queue is to operate";
                                        }

                                        ///nokia-conf/configure/service/cpipe/sap/ingress/qos/scheduler-policy/overrides/scheduler/rate/cir
                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos

                } // container ingress

                ///nokia-conf/configure/service/cpipe/sap/egress
                container egress {
                    description "Enter the egress context";

                    ///nokia-conf/configure/service/cpipe/sap/egress/agg-rate-or-percent-agg-rate
                    choice agg-rate-or-percent-agg-rate {
                        default "agg-rate";
                        ///nokia-conf/configure/service/cpipe/sap/egress/agg-rate-or-percent-agg-rate/agg-rate
                        case agg-rate {

                            ///nokia-conf/configure/service/cpipe/sap/egress/agg-rate-or-percent-agg-rate/agg-rate/agg-rate
                            container agg-rate {
                                description "Enter the agg-rate context";

                                ///nokia-conf/configure/service/cpipe/sap/egress/agg-rate-or-percent-agg-rate/agg-rate/agg-rate/limit-unused-bandwidth
                                leaf limit-unused-bandwidth {
                                    type boolean;
                                    default "false";
                                    description "Enable aggregate rate overrun protection";
                                }

                                ///nokia-conf/configure/service/cpipe/sap/egress/agg-rate-or-percent-agg-rate/agg-rate/agg-rate/rate
                                leaf rate {
                                    type types-services:agg-rate-rate;
                                    units "kilobps";
                                    description "Enforced aggregate rate for all queues";
                                }

                                ///nokia-conf/configure/service/cpipe/sap/egress/agg-rate-or-percent-agg-rate/agg-rate/agg-rate/cir
                                leaf cir {
                                    type union {
                                        type int32 {
                                            range "0..400000000";
                                        }
                                        type enumeration {
                                            enum max                            { value -1; }
                                        }
                                    }
                                    units "kilobps";
                                    default "0";
                                    description "Administrative CIR";
                                }

                                ///nokia-conf/configure/service/cpipe/sap/egress/agg-rate-or-percent-agg-rate/agg-rate/agg-rate/burst-limit
                                leaf burst-limit {
                                    type union {
                                        type types-qos:bytes {
                                            range "1..14000000";
                                        }
                                        type enumeration {
                                            enum auto                           { value -1; }
                                        }
                                    }
                                    default "auto";
                                    description "Shaping burst size when an aggregate shaper is used";
                                }

                                ///nokia-conf/configure/service/cpipe/sap/egress/agg-rate-or-percent-agg-rate/agg-rate/agg-rate/adaptation-rule
                                leaf adaptation-rule {
                                    type types-qos:adaptation-rule;
                                    default "closest";
                                    description "Adaptation rule to compute the operational PIR value when an aggregate shaper is used";
                                }

                            } // container agg-rate

                        }
                    }
                    ///nokia-conf/configure/service/cpipe/sap/egress/qos
                    container qos {
                        description "Enter the qos context";

                        ///nokia-conf/configure/service/cpipe/sap/egress/qos/sap-egress
                        container sap-egress {
                            description "Enter the sap-egress context";

                            ///nokia-conf/configure/service/cpipe/sap/egress/qos/sap-egress/policy-name
                            leaf policy-name {
                                type leafref {
                                    path "../../../../../../../qos/sap-egress/sap-egress-policy-name";
                                }
                                description "Policy ID to associate with SAP for mirrored service";
                            }

                            ///nokia-conf/configure/service/cpipe/sap/egress/qos/sap-egress/overrides
                            container overrides {
                                description "Enter the overrides context";

                                ///nokia-conf/configure/service/cpipe/sap/egress/qos/sap-egress/overrides/queue
                                list queue {
                                    key "queue-id";
                                    description "Enter the queue list instance";

                                    ///nokia-conf/configure/service/cpipe/sap/egress/qos/sap-egress/overrides/queue/queue-id
                                    leaf queue-id {
                                        type leafref {
                                            path "../../../../../../../../../qos/sap-egress[sap-egress-policy-name=current()/../../../policy-name]/queue/queue-id";
                                        }
                                        description "Policer unique ID";
                                    }

                                    ///nokia-conf/configure/service/cpipe/sap/egress/qos/sap-egress/overrides/queue/avg-frame-overhead
                                    leaf avg-frame-overhead {
                                        type decimal64 {
                                            range "0.00..100.00";
                                            fraction-digits 2;
                                        }
                                        description "Average packet-to-frame encapsulation overhead";
                                    }

                                    ///nokia-conf/configure/service/cpipe/sap/egress/qos/sap-egress/overrides/queue/burst-limit
                                    leaf burst-limit {
                                        type union {
                                            type types-qos:bytes {
                                                range "1..14000000";
                                            }
                                            type enumeration {
                                                enum auto                           { value -1; }
                                            }
                                        }
                                        description "Explicit shaping burst size for the queue";
                                    }

                                    ///nokia-conf/configure/service/cpipe/sap/egress/qos/sap-egress/overrides/queue/cbs
                                    leaf cbs {
                                        type union {
                                            type uint32 {
                                                range "0..1048576";
                                            }
                                            type enumeration {
                                                enum auto                           { value -1; }
                                            }
                                        }
                                        units "kilobytes";
                                        description "CBS";
                                    }

                                    ///nokia-conf/configure/service/cpipe/sap/egress/qos/sap-egress/overrides/queue/mbs
                                    leaf mbs {
                                        type union {
                                            type types-qos:bytes {
                                                range "0..1073741824";
                                            }
                                            type enumeration {
                                                enum auto                           { value -1; }
                                            }
                                        }
                                        units "bytes";
                                        description "MBS";
                                    }

                                    ///nokia-conf/configure/service/cpipe/sap/egress/qos/sap-egress/overrides/queue/monitor-depth
                                    leaf monitor-depth {
                                        status obsolete;
                                        type boolean;
                                        default "false";
                                        description "Monitor queue depth";
                                    }

                                    ///nokia-conf/configure/service/cpipe/sap/egress/qos/sap-egress/overrides/queue/hs-wrr-weight
                                    leaf hs-wrr-weight {
                                        type types-qos:hs-wrr-weight-override;
                                        default "1";
                                        description "WRR weight to parent with the queue into the scheduler";
                                    }

                                    ///nokia-conf/configure/service/cpipe/sap/egress/qos/sap-egress/overrides/queue/hs-class-weight
                                    leaf hs-class-weight {
                                        type types-qos:hs-class-weight-override;
                                        description "Class weight override for the queue";
                                    }

                                    ///nokia-conf/configure/service/cpipe/sap/egress/qos/sap-egress/overrides/queue/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/egress/qos/sap-egress/overrides/queue/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/egress/qos/sap-egress/overrides/queue/queue-override-rate
                                    choice queue-override-rate {
                                        ///nokia-conf/configure/service/cpipe/sap/egress/qos/sap-egress/overrides/queue/queue-override-rate/rate
                                        case rate {

                                            ///nokia-conf/configure/service/cpipe/sap/egress/qos/sap-egress/overrides/queue/queue-override-rate/rate/rate
                                            container rate {
                                                description "Enter the rate context";

                                                ///nokia-conf/configure/service/cpipe/sap/egress/qos/sap-egress/overrides/queue/queue-override-rate/rate/rate/pir
                                                leaf pir {
                                                    type types-services:sap-pir-rate-ovr;
                                                    units "kilobps";
                                                    description "PIR rate";
                                                }

                                                ///nokia-conf/configure/service/cpipe/sap/egress/qos/sap-egress/overrides/queue/queue-override-rate/rate/rate/cir
                                                leaf cir {
                                                    type types-services:sap-cir-rate-ovr;
                                                    units "kilobps";
                                                    description "CIR rate";
                                                }

                                            } // container rate

                                        }
                                        ///nokia-conf/configure/service/cpipe/sap/egress/qos/sap-egress/overrides/queue/queue-override-rate/percent-rate
                                        case percent-rate {

                                            ///nokia-conf/configure/service/cpipe/sap/egress/qos/sap-egress/overrides/queue/queue-override-rate/percent-rate/percent-rate
                                            container percent-rate {
                                                description "Enter the percent-rate context";

                                                ///nokia-conf/configure/service/cpipe/sap/egress/qos/sap-egress/overrides/queue/queue-override-rate/percent-rate/percent-rate/pir
                                                leaf pir {
                                                    type decimal64 {
                                                        range "0.01..100.00";
                                                        fraction-digits 2;
                                                    }
                                                    description "PIR percent rate";
                                                }

                                                ///nokia-conf/configure/service/cpipe/sap/egress/qos/sap-egress/overrides/queue/queue-override-rate/percent-rate/percent-rate/cir
                                                leaf cir {
                                                    type decimal64 {
                                                        range "0.00..100.00";
                                                        fraction-digits 2;
                                                    }
                                                    description "CIR percent rate";
                                                }

                                            } // container percent-rate

                                        }
                                    }
                                    ///nokia-conf/configure/service/cpipe/sap/egress/qos/sap-egress/overrides/queue/adaptation-rule
                                    container adaptation-rule {
                                        description "Enter the adaptation-rule context";

                                        ///nokia-conf/configure/service/cpipe/sap/egress/qos/sap-egress/overrides/queue/adaptation-rule/pir
                                        leaf pir {
                                            type types-qos:adaptation-rule-override;
                                            description "Constraint used when deriving the operational PIR value";
                                        }

                                        ///nokia-conf/configure/service/cpipe/sap/egress/qos/sap-egress/overrides/queue/adaptation-rule/cir
                                        leaf cir {
                                            type types-qos:adaptation-rule-override;
                                            description "Constraint used when deriving the operational CIR value";
                                        }

                                    } // container adaptation-rule

                                    ///nokia-conf/configure/service/cpipe/sap/egress/qos/sap-egress/overrides/queue/drop-tail
                                    container drop-tail {
                                        description "Enter the drop-tail context";

                                        ///nokia-conf/configure/service/cpipe/sap/egress/qos/sap-egress/overrides/queue/drop-tail/low
                                        container low {
                                            description "Enter the low context";

                                            ///nokia-conf/configure/service/cpipe/sap/egress/qos/sap-egress/overrides/queue/drop-tail/low/percent-reduction-from-mbs
                                            leaf percent-reduction-from-mbs {
                                                type types-qos:burst-percent-or-default-override;
                                                description "Percentage reduction from the MBS for a queue drop tail";
                                            }

                                        } // container low

                                    } // container drop-tail

                                    ///nokia-conf/configure/service/cpipe/sap/egress/qos/sap-egress/overrides/queue/parent
                                    container parent {
                                        description "Enter the parent context";

                                        ///nokia-conf/configure/service/cpipe/sap/egress/qos/sap-egress/overrides/queue/parent/weight
                                        leaf weight {
                                            type types-qos:weight-override;
                                            description "PIR parameter that overrides parent for queue group";
                                        }

                                        ///nokia-conf/configure/service/cpipe/sap/egress/qos/sap-egress/overrides/queue/parent/cir-weight
                                        leaf cir-weight {
                                            type types-qos:weight-override;
                                            description "CIR parameter that overrides parent for queue group";
                                        }

                                    } // container parent

                                    ///nokia-conf/configure/service/cpipe/sap/egress/qos/sap-egress/overrides/queue/monitor-queue-depth
                                    container monitor-queue-depth {
                                        presence "Enable the monitor-queue-depth context";
                                        description "Enable the monitor-queue-depth context";

                                        ///nokia-conf/configure/service/cpipe/sap/egress/qos/sap-egress/overrides/queue/monitor-queue-depth/fast-polling
                                        leaf fast-polling {
                                            type boolean;
                                            default "false";
                                            description "Enable fast polling of the queue depth";
                                        }

                                        ///nokia-conf/configure/service/cpipe/sap/egress/qos/sap-egress/overrides/queue/monitor-queue-depth/violation-threshold
                                        leaf violation-threshold {
                                            type decimal64 {
                                                range "0.01..99.99";
                                                fraction-digits 2;
                                            }
                                            description "Threshold for queue depth before violation is raised";
                                        }

                                    } // container monitor-queue-depth

                                    ///nokia-conf/configure/service/cpipe/sap/egress/qos/sap-egress/overrides/queue/hs-wred-queue
                                    container hs-wred-queue {
                                        description "Enter the hs-wred-queue context";

                                        ///nokia-conf/configure/service/cpipe/sap/egress/qos/sap-egress/overrides/queue/hs-wred-queue/policy
                                        leaf policy {
                                            type leafref {
                                                path "../../../../../../../../../../qos/slope-policy/slope-policy-name";
                                            }
                                            description "Slope policy applied to the HSQ queue group queue";
                                        }

                                    } // container hs-wred-queue

                                } // list queue

                                ///nokia-conf/configure/service/cpipe/sap/egress/qos/sap-egress/overrides/policer
                                list policer {
                                    key "policer-id";
                                    description "Enter the policer list instance";

                                    ///nokia-conf/configure/service/cpipe/sap/egress/qos/sap-egress/overrides/policer/policer-id
                                    leaf policer-id {
                                        type leafref {
                                            path "../../../../../../../../../qos/sap-egress[sap-egress-policy-name=current()/../../../policy-name]/policer/policer-id";
                                        }
                                        description "Policer unique ID";
                                    }

                                    ///nokia-conf/configure/service/cpipe/sap/egress/qos/sap-egress/overrides/policer/cbs
                                    leaf cbs {
                                        type types-qos:policer-burst-size-override-max;
                                        description "CBS";
                                    }

                                    ///nokia-conf/configure/service/cpipe/sap/egress/qos/sap-egress/overrides/policer/mbs
                                    leaf mbs {
                                        type types-qos:policer-burst-size-override-max;
                                        description "MBS";
                                    }

                                    ///nokia-conf/configure/service/cpipe/sap/egress/qos/sap-egress/overrides/policer/packet-byte-offset
                                    leaf packet-byte-offset {
                                        type types-qos:egress-per-packet-offset-override;
                                        description "Packet size modification for policing information";
                                    }

                                    ///nokia-conf/configure/service/cpipe/sap/egress/qos/sap-egress/overrides/policer/stat-mode
                                    leaf stat-mode {
                                        type types-qos:egress-policer-stat-mode;
                                        description "Mode of statistics collected by the policer";
                                    }

                                    ///nokia-conf/configure/service/cpipe/sap/egress/qos/sap-egress/overrides/policer/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/egress/qos/sap-egress/overrides/policer/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/egress/qos/sap-egress/overrides/policer/policer-override-rate
                                    choice policer-override-rate {
                                        ///nokia-conf/configure/service/cpipe/sap/egress/qos/sap-egress/overrides/policer/policer-override-rate/rate
                                        case rate {

                                            ///nokia-conf/configure/service/cpipe/sap/egress/qos/sap-egress/overrides/policer/policer-override-rate/rate/rate
                                            container rate {
                                                description "Enter the rate context";

                                                ///nokia-conf/configure/service/cpipe/sap/egress/qos/sap-egress/overrides/policer/policer-override-rate/rate/rate/pir
                                                leaf pir {
                                                    type union {
                                                        type int64 {
                                                            range "1..6400000000";
                                                        }
                                                        type enumeration {
                                                            enum max                            { value -1; }
                                                        }
                                                    }
                                                    units "kilobps";
                                                    description "PIR rate";
                                                }

                                                ///nokia-conf/configure/service/cpipe/sap/egress/qos/sap-egress/overrides/policer/policer-override-rate/rate/rate/cir
                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        ///nokia-conf/configure/service/cpipe/sap/egress/qos/sap-egress/overrides/policer/policer-override-rate/percent-rate
                                        case percent-rate {

                                            ///nokia-conf/configure/service/cpipe/sap/egress/qos/sap-egress/overrides/policer/policer-override-rate/percent-rate/percent-rate
                                            container percent-rate {
                                                description "Enter the percent-rate context";

                                                ///nokia-conf/configure/service/cpipe/sap/egress/qos/sap-egress/overrides/policer/policer-override-rate/percent-rate/percent-rate/pir
                                                leaf pir {
                                                    type decimal64 {
                                                        range "0.01..100.00";
                                                        fraction-digits 2;
                                                    }
                                                    description "PIR percent rate";
                                                }

                                                ///nokia-conf/configure/service/cpipe/sap/egress/qos/sap-egress/overrides/policer/policer-override-rate/percent-rate/percent-rate/cir
                                                leaf cir {
                                                    type decimal64 {
                                                        range "0.00..100.00";
                                                        fraction-digits 2;
                                                    }
                                                    description "CIR percent rate";
                                                }

                                            } // container percent-rate

                                        }
                                    }
                                } // list policer

                            } // container overrides

                        } // container sap-egress

                        ///nokia-conf/configure/service/cpipe/sap/egress/qos/policer-control-policy
                        container policer-control-policy {
                            description "Enter the policer-control-policy context";

                            ///nokia-conf/configure/service/cpipe/sap/egress/qos/policer-control-policy/policy-name
                            leaf policy-name {
                                type leafref {
                                    path "../../../../../../../qos/policer-control-policy/policer-control-policy-name";
                                }
                                description "Policer control policy name";
                            }

                            ///nokia-conf/configure/service/cpipe/sap/egress/qos/policer-control-policy/overrides
                            container overrides {
                                presence "Enable the overrides context";
                                description "Enable the overrides context";

                                ///nokia-conf/configure/service/cpipe/sap/egress/qos/policer-control-policy/overrides/apply-groups
                                leaf-list apply-groups {
                                    type leafref {
                                        path "../../../../../../../../groups/group/name";
                                    }
                                    max-elements 8;
                                    ordered-by user;
                                    description "Apply a configuration group at this level";
                                }

                                ///nokia-conf/configure/service/cpipe/sap/egress/qos/policer-control-policy/overrides/apply-groups-exclude
                                leaf-list apply-groups-exclude {
                                    type leafref {
                                        path "../../../../../../../../groups/group/name";
                                    }
                                    max-elements 8;
                                    ordered-by user;
                                    description "Exclude a configuration group at this level";
                                }

                                ///nokia-conf/configure/service/cpipe/sap/egress/qos/policer-control-policy/overrides/root
                                container root {
                                    description "Enter the root context";

                                    ///nokia-conf/configure/service/cpipe/sap/egress/qos/policer-control-policy/overrides/root/max-rate
                                    leaf max-rate {
                                        type types-services:sap-max-rate-ovr;
                                        description "Maximum frame-based bandwidth limit";
                                    }

                                    ///nokia-conf/configure/service/cpipe/sap/egress/qos/policer-control-policy/overrides/root/priority-mbs-thresholds
                                    container priority-mbs-thresholds {
                                        description "Enter the priority-mbs-thresholds context";

                                        ///nokia-conf/configure/service/cpipe/sap/egress/qos/policer-control-policy/overrides/root/priority-mbs-thresholds/min-thresh-separation
                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        ///nokia-conf/configure/service/cpipe/sap/egress/qos/policer-control-policy/overrides/root/priority-mbs-thresholds/priority
                                        list priority {
                                            key "priority-level";
                                            description "Enter the priority list instance";

                                            ///nokia-conf/configure/service/cpipe/sap/egress/qos/policer-control-policy/overrides/root/priority-mbs-thresholds/priority/priority-level
                                            leaf priority-level {
                                                type types-qos:hierarchy-level;
                                                description "Priority level";
                                            }

                                            ///nokia-conf/configure/service/cpipe/sap/egress/qos/policer-control-policy/overrides/root/priority-mbs-thresholds/priority/mbs-contribution
                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            ///nokia-conf/configure/service/cpipe/sap/egress/qos/policer-control-policy/overrides/root/priority-mbs-thresholds/priority/apply-groups
                                            leaf-list apply-groups {
                                                type leafref {
                                                    path "../../../../../../../../../../../groups/group/name";
                                                }
                                                max-elements 8;
                                                ordered-by user;
                                                description "Apply a configuration group at this level";
                                            }

                                            ///nokia-conf/configure/service/cpipe/sap/egress/qos/policer-control-policy/overrides/root/priority-mbs-thresholds/priority/apply-groups-exclude
                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        ///nokia-conf/configure/service/cpipe/sap/egress/qos/scheduler-policy
                        container scheduler-policy {
                            description "Enter the scheduler-policy context";

                            ///nokia-conf/configure/service/cpipe/sap/egress/qos/scheduler-policy/policy-name
                            leaf policy-name {
                                type leafref {
                                    path "../../../../../../../qos/scheduler-policy/scheduler-policy-name";
                                }
                                description "Scheduler policy name";
                            }

                            ///nokia-conf/configure/service/cpipe/sap/egress/qos/scheduler-policy/overrides
                            container overrides {
                                description "Enter the overrides context";

                                ///nokia-conf/configure/service/cpipe/sap/egress/qos/scheduler-policy/overrides/scheduler
                                list scheduler {
                                    key "scheduler-name";
                                    description "Enter the scheduler list instance";

                                    ///nokia-conf/configure/service/cpipe/sap/egress/qos/scheduler-policy/overrides/scheduler/scheduler-name
                                    leaf scheduler-name {
                                        type types-sros:named-item;
                                        description "Scheduler name";
                                    }

                                    ///nokia-conf/configure/service/cpipe/sap/egress/qos/scheduler-policy/overrides/scheduler/apply-groups
                                    leaf-list apply-groups {
                                        type leafref {
                                            path "../../../../../../../../../groups/group/name";
                                        }
                                        max-elements 8;
                                        ordered-by user;
                                        description "Apply a configuration group at this level";
                                    }

                                    ///nokia-conf/configure/service/cpipe/sap/egress/qos/scheduler-policy/overrides/scheduler/apply-groups-exclude
                                    leaf-list apply-groups-exclude {
                                        type leafref {
                                            path "../../../../../../../../../groups/group/name";
                                        }
                                        max-elements 8;
                                        ordered-by user;
                                        description "Exclude a configuration group at this level";
                                    }

                                    ///nokia-conf/configure/service/cpipe/sap/egress/qos/scheduler-policy/overrides/scheduler/parent
                                    container parent {
                                        description "Enter the parent context";

                                        ///nokia-conf/configure/service/cpipe/sap/egress/qos/scheduler-policy/overrides/scheduler/parent/weight
                                        leaf weight {
                                            type types-qos:weight;
                                            description "Relative weight of the scheduler to feed the queue";
                                        }

                                        ///nokia-conf/configure/service/cpipe/sap/egress/qos/scheduler-policy/overrides/scheduler/parent/cir-weight
                                        leaf cir-weight {
                                            type types-qos:weight;
                                            description "Weight used at the within-CIR port priority level";
                                        }

                                    } // container parent

                                    ///nokia-conf/configure/service/cpipe/sap/egress/qos/scheduler-policy/overrides/scheduler/rate
                                    container rate {
                                        description "Enter the rate context";

                                        ///nokia-conf/configure/service/cpipe/sap/egress/qos/scheduler-policy/overrides/scheduler/rate/pir
                                        leaf pir {
                                            type union {
                                                type int64 {
                                                    range "1..6400000000";
                                                }
                                                type enumeration {
                                                    enum max                            { value -1; }
                                                }
                                            }
                                            units "kilobps";
                                            description "PIR at which the queue is to operate";
                                        }

                                        ///nokia-conf/configure/service/cpipe/sap/egress/qos/scheduler-policy/overrides/scheduler/rate/cir
                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos


                } // container egress

                ///nokia-conf/configure/service/cpipe/sap/lag
                container lag {
                    description "Enter the lag context";

                } // container lag

                ///nokia-conf/configure/service/cpipe/sap/cem
                container cem {
                    description "Enter the cem context";

                    ///nokia-conf/configure/service/cpipe/sap/cem/rtp-header
                    leaf rtp-header {
                        type boolean;
                        default "false";
                        description "Use RTP header for transmitted packets to the PSN";
                    }

                    ///nokia-conf/configure/service/cpipe/sap/cem/packet
                    container packet {
                        description "Enter the packet context";

                        ///nokia-conf/configure/service/cpipe/sap/cem/packet/payload-size
                        leaf payload-size {
                            type uint32 {
                                range "2..1514";
                            }
                            units "bytes";
                            description "Size of payload packets transmitted to PSN by CEM SAP";
                        }

                        ///nokia-conf/configure/service/cpipe/sap/cem/packet/jitter-buffer
                        leaf jitter-buffer {
                            type uint32 {
                                range "1..250";
                            }
                            units "milliseconds";
                            description "Jitter buffer size";
                        }

                    } // container packet

                    ///nokia-conf/configure/service/cpipe/sap/cem/report-alarm
                    container report-alarm {
                        description "Enter the report-alarm context";

                        ///nokia-conf/configure/service/cpipe/sap/cem/report-alarm/stray-packets
                        leaf stray-packets {
                            type boolean;
                            default "true";
                            description "Report alarm for stray packets";
                        }

                        ///nokia-conf/configure/service/cpipe/sap/cem/report-alarm/malformed-packets
                        leaf malformed-packets {
                            type boolean;
                            default "true";
                            description "Report alarm for malformed packets";
                        }

                        ///nokia-conf/configure/service/cpipe/sap/cem/report-alarm/packet-loss
                        leaf packet-loss {
                            type boolean;
                            default "true";
                            description "Report remote peer is currently in packet loss status";
                        }

                        ///nokia-conf/configure/service/cpipe/sap/cem/report-alarm/buffer-overrun
                        leaf buffer-overrun {
                            type boolean;
                            default "true";
                            description "Report alarm for buffer overrun";
                        }

                        ///nokia-conf/configure/service/cpipe/sap/cem/report-alarm/buffer-underrun
                        leaf buffer-underrun {
                            type boolean;
                            default "true";
                            description "Report alarm for buffer underrun";
                        }

                        ///nokia-conf/configure/service/cpipe/sap/cem/report-alarm/remote-packet-loss
                        leaf remote-packet-loss {
                            type boolean;
                            default "false";
                            description "Report remote peer is currently in packet loss status";
                        }

                        ///nokia-conf/configure/service/cpipe/sap/cem/report-alarm/remote-fault
                        leaf remote-fault {
                            type boolean;
                            default "false";
                            description "Report remote TDM interface is currently not in service";
                        }

                        ///nokia-conf/configure/service/cpipe/sap/cem/report-alarm/remote-rdi
                        leaf remote-rdi {
                            type boolean;
                            default "false";
                            description "Report remote TDM interface is currently in RDI status";
                        }

                    } // container report-alarm

                } // container cem

            } // list sap

            ///nokia-conf/configure/service/cpipe/spoke-sdp
            list spoke-sdp {
                key "sdp-bind-id";
                description "Enter the spoke-sdp list instance";

                ///nokia-conf/configure/service/cpipe/spoke-sdp/sdp-bind-id
                leaf sdp-bind-id {
                    type types-services:sdp-bind-id;
                    description "SDP binding ID";
                }

                ///nokia-conf/configure/service/cpipe/spoke-sdp/description
                leaf description {
                    type types-sros:description;
                    description "Text description";
                }

                ///nokia-conf/configure/service/cpipe/spoke-sdp/admin-state
                leaf admin-state {
                    type types-sros:admin-state;
                    default "enable";
                    description "Administrative state of the SDP binding to the service";
                }

                ///nokia-conf/configure/service/cpipe/spoke-sdp/control-word
                leaf control-word {
                    type boolean;
                    default "true";
                    description "Use control word as part of packet encapsulation";
                }

                ///nokia-conf/configure/service/cpipe/spoke-sdp/bandwidth
                leaf bandwidth {
                    type types-services:sdp-bind-bandwidth;
                    units "kilobps";
                    default "0";
                    description "Bandwidth that is reserved for this SDP binding";
                }

                ///nokia-conf/configure/service/cpipe/spoke-sdp/bfd-template
                leaf bfd-template {
                    status obsolete;
                    type leafref {
                        path "../../../../bfd/bfd-template/name";
                    }
                    description "BFD template associated with SDP binding";
                }

                ///nokia-conf/configure/service/cpipe/spoke-sdp/apply-groups
                leaf-list apply-groups {
                    type leafref {
                        path "../../../../groups/group/name";
                    }
                    max-elements 8;
                    ordered-by user;
                    description "Apply a configuration group at this level";
                }

                ///nokia-conf/configure/service/cpipe/spoke-sdp/apply-groups-exclude
                leaf-list apply-groups-exclude {
                    type leafref {
                        path "../../../../groups/group/name";
                    }
                    max-elements 8;
                    ordered-by user;
                    description "Exclude a configuration group at this level";
                }

                ///nokia-conf/configure/service/cpipe/spoke-sdp/ingress
                container ingress {
                    description "Enter the ingress context";

                    ///nokia-conf/configure/service/cpipe/spoke-sdp/ingress/vc-label
                    leaf vc-label {
                        type types-services:ingress-vc-label;
                        sros-ext:auto-restart-to-modify;
                        description "Ingress MPLS VC label to send packets to the far end";
                    }

                    ///nokia-conf/configure/service/cpipe/spoke-sdp/ingress/qos
                    container qos {
                        description "Enter the qos context";

                        ///nokia-conf/configure/service/cpipe/spoke-sdp/ingress/qos/network
                        container network {
                            description "Enter the network context";

                            ///nokia-conf/configure/service/cpipe/spoke-sdp/ingress/qos/network/policy-name
                            leaf policy-name {
                                type leafref {
                                    path "../../../../../../../qos/network/network-policy-name";
                                }
                                description "Network policy ID";
                            }

                            ///nokia-conf/configure/service/cpipe/spoke-sdp/ingress/qos/network/fp-redirect-group
                            container fp-redirect-group {
                                description "Enter the fp-redirect-group context";

                                ///nokia-conf/configure/service/cpipe/spoke-sdp/ingress/qos/network/fp-redirect-group/group-name
                                leaf group-name {
                                    type leafref {
                                        path "../../../../../../../../qos/queue-group-templates/ingress/queue-group/ingress-queue-group-name";
                                    }
                                    description "Name of the forwarding plane queue group template";
                                }

                                ///nokia-conf/configure/service/cpipe/spoke-sdp/ingress/qos/network/fp-redirect-group/instance
                                leaf instance {
                                    type types-services:qos-qgrp-instance-id;
                                    description "Instance of FP ingress queue group for the SDP binding";
                                }

                            } // container fp-redirect-group

                        } // container network

                    } // container qos

                } // container ingress

                ///nokia-conf/configure/service/cpipe/spoke-sdp/egress
                container egress {
                    description "Enter the egress context";

                    ///nokia-conf/configure/service/cpipe/spoke-sdp/egress/vc-label
                    leaf vc-label {
                        type types-services:egress-vc-label;
                        sros-ext:auto-restart-to-modify;
                        description "Egress MPLS VC label to send packets to the far end";
                    }

                    ///nokia-conf/configure/service/cpipe/spoke-sdp/egress/qos
                    container qos {
                        description "Enter the qos context";

                        ///nokia-conf/configure/service/cpipe/spoke-sdp/egress/qos/network
                        container network {
                            description "Enter the network context";

                            ///nokia-conf/configure/service/cpipe/spoke-sdp/egress/qos/network/policy-name
                            leaf policy-name {
                                type leafref {
                                    path "../../../../../../../qos/network/network-policy-name";
                                }
                                description "Network policy ID";
                            }

                            ///nokia-conf/configure/service/cpipe/spoke-sdp/egress/qos/network/port-redirect-group
                            container port-redirect-group {
                                description "Enter the port-redirect-group context";

                                ///nokia-conf/configure/service/cpipe/spoke-sdp/egress/qos/network/port-redirect-group/group-name
                                leaf group-name {
                                    type leafref {
                                        path "../../../../../../../../qos/queue-group-templates/egress/queue-group/egress-queue-group-name";
                                    }
                                    description "Name of the egress port queue group";
                                }

                                ///nokia-conf/configure/service/cpipe/spoke-sdp/egress/qos/network/port-redirect-group/instance
                                leaf instance {
                                    type types-services:qos-qgrp-instance-id;
                                    description "Queue-group instance ID";
                                }

                            } // container port-redirect-group

                        } // container network

                    } // container qos

                } // container egress

                ///nokia-conf/configure/service/cpipe/spoke-sdp/endpoint
                container endpoint {
                    description "Enter the endpoint context";

                    ///nokia-conf/configure/service/cpipe/spoke-sdp/endpoint/name
                    leaf name {
                        type leafref {
                            path "../../../../cpipe[service-name=current()/../../../service-name]/endpoint/name";
                        }
                        sros-ext:auto-restart-to-modify;
                        description "Endpoint name to which SDP bind is attached";
                    }

                    ///nokia-conf/configure/service/cpipe/spoke-sdp/endpoint/precedence
                    leaf precedence {
                        type types-services:sdp-precedence;
                        default "4";
                        description "Precedence when multiple SDP binds are on one endpoint";
                    }

                    ///nokia-conf/configure/service/cpipe/spoke-sdp/endpoint/icb
                    leaf icb {
                        type boolean;
                        sros-ext:auto-restart-to-modify;
                        default "false";
                        description "Bind the SDP as the Inter-Chassis Backup (ICB) type";
                    }

                } // container endpoint

                ///nokia-conf/configure/service/cpipe/spoke-sdp/bfd-liveness
                container bfd-liveness {
                    status obsolete;
                    presence "Enable the bfd-liveness context";
                    description "Enable the bfd-liveness context";

                    ///nokia-conf/configure/service/cpipe/spoke-sdp/bfd-liveness/encap
                    leaf encap {
                        status obsolete;
                        type types-services:bfd-encap;
                        default "ipv4";
                        description "BFD encapsulation used on the SDP binding";
                    }

                } // container bfd-liveness

                ///nokia-conf/configure/service/cpipe/spoke-sdp/bfd
                container bfd {
                    description "Enter the bfd context";

                    ///nokia-conf/configure/service/cpipe/spoke-sdp/bfd/bfd-template
                    leaf bfd-template {
                        type leafref {
                            path "../../../../../bfd/bfd-template/name";
                        }
                        description "BFD template associated with the SDP binding";
                    }

                    ///nokia-conf/configure/service/cpipe/spoke-sdp/bfd/bfd-liveness
                    container bfd-liveness {
                        presence "Enable the bfd-liveness context";
                        description "Enable the bfd-liveness context";

                        ///nokia-conf/configure/service/cpipe/spoke-sdp/bfd/bfd-liveness/encap
                        leaf encap {
                            type types-services:bfd-encap;
                            default "ipv4";
                            description "BFD encapsulation used on the SDP binding";
                        }

                    } // container bfd-liveness

                } // container bfd

            } // list spoke-sdp

        } // list cpipe

    } // grouping conf-svc-cpipe

}
