submodule nokia-state-system {

    yang-version "1.1";

    belongs-to nokia-state { prefix "state"; }

    import ietf-inet-types                { prefix "inet"; }
    import ietf-yang-types                { prefix "yang"; }
    import nokia-sros-yang-extensions     { prefix "sros-ext"; }
    import nokia-types-card               { prefix "types-card"; }
    import nokia-types-lldp               { prefix "types-lldp"; }
    import nokia-types-log                { prefix "types-log"; }
    import nokia-types-operation          { prefix "types-operation"; }
    import nokia-types-qos                { prefix "types-qos"; }
    import nokia-types-sros               { prefix "types-sros"; }
    import nokia-types-system             { prefix "types-system"; }

    include nokia-state-sfm;
    include nokia-state-system-bluetooth;
    include nokia-state-system-bootup;
    include nokia-state-system-cron;
    include nokia-state-system-licensing;
    include nokia-state-system-ptp;
    include nokia-state-system-script-control;
    include nokia-state-system-security;
    include nokia-state-system-telemetry;
    include nokia-state-system-time;

    sros-ext:sros-major-release "rel23";
    organization "Nokia";
    contact
        "Nokia SR OS Support
         Web: <http://www.nokia.com>";
    description
        "Nokia YANG Data model with operational state for system parameters on SR OS based routers.

         Copyright 2016 Nokia. All rights reserved. Reproduction of this document
         is authorized on the condition that the foregoing copyright notice is included.

         This nokia-state-system YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-05";

    grouping state-system {
        ///nokia-state/state/system
        container system {
            description "Enter the system context";

            ///nokia-state/state/system/oper-name
            leaf oper-name {
                type types-sros:named-item-64;
                description "The administrative name that is used by the system.";
            }

            ///nokia-state/state/system/base-mac-address
            leaf base-mac-address {
                type yang:mac-address;
                description
                    "Indicates the base system ethernet MAC address. Special purpose
                     MAC addresses used by the system software are constructed as
                     offsets from this base address.";
            }

            ///nokia-state/state/system/platform
            leaf platform {
                type types-sros:description;
                description
                    "Indicates the model type of the chassis used in
                     this Nokia SROS system.  Chassis types are
                     distinguished by their backplane type.";
            }

            ///nokia-state/state/system/chassis-topology
            leaf chassis-topology {
                type enumeration {
                    enum standalone                     { value 1; }
                    enum extended                       { value 2; }
                }
                description
                    "Indicates the inter-chassis topology mode in which the system
                     is operating.

                     It indicates how multiple chassis are arrange and operate
                     together as a single system.

                     A value of 'standalone' indicates that the system is comprised
                     of a single physical router chassis.

                     A value of 'extended' (for a 7950 XRS based system) indicates
                     that two router chassis are connected together in a
                     'back-to-back' topology with no additional switch fabric
                     chassis. An extended chassis topology is comprised of two
                     XRS-20 chassis and is also known as an XRS-40 system.";
            }

            ///nokia-state/state/system/crypto-module-version
            leaf crypto-module-version {
                type string;
                description "Cryptographic module version.";
            }

            ///nokia-state/state/system/fabric-speed
            leaf fabric-speed {
                type enumeration {
                    enum speed-6g                       { value 1; }
                    enum speed-10g                      { value 2; }
                    enum speed-s4                       { value 3; }
                    enum speed-s5                       { value 4; }
                }
                description "Indicates the system fabric speed.";
            }

            ///nokia-state/state/system/temperature-status
            leaf temperature-status {
                type enumeration {
                    enum ok                             { value 1; }
                    enum over-temp                      { value 2; }
                }
                description
                    "Indicates the over temperature state of the system.

                     ok        - all physical router chassis are below
                                 the temperature threshold.
                     over-temp - at least one physical router chassis is
                                 above the temperature threshold.";
            }

            ///nokia-state/state/system/fp-generation-fp2
            leaf fp-generation-fp2 {
                type boolean;
                description "Whether the system contains at least one FP2 based line card.";
            }

            ///nokia-state/state/system/fp-generation-fp3
            leaf fp-generation-fp3 {
                type boolean;
                description "Whether the system contains at least one FP3 based line card.";
            }

            ///nokia-state/state/system/fp-generation-fp4
            leaf fp-generation-fp4 {
                type boolean;
                description "Whether the system contains at least one FP4 based line card.";
            }

            ///nokia-state/state/system/fp-generation-vfp
            leaf fp-generation-vfp {
                type boolean;
                description "Whether the system contains at least one VFP based line card.";
            }

            ///nokia-state/state/system/fp-generation-fp5
            leaf fp-generation-fp5 {
                type boolean;
                description "Whether the system contains at least one FP5 based line card.";
            }

            ///nokia-state/state/system/system-profile
            leaf system-profile {
                type enumeration {
                    enum none                           { value 0; }
                    enum profile-a                      { value 1; }
                    enum profile-b                      { value 2; }
                }
                description "Configured system profile.";
            }

            ///nokia-state/state/system/active-cpm-slot
            leaf active-cpm-slot {
                type types-card:cpm-card-slot;
                description "The value indicates which CPM is in active state.";
            }

            ///nokia-state/state/system/up-time
            leaf up-time {
                type uint64;
                units "milliseconds";
                description
                    "The time since the network management portion of the system was
                     last re-initialized.";
            }

            ///nokia-state/state/system/current-time
            leaf current-time {
                type yang:date-and-time;
                description "Current system time.";
            }

            ///nokia-state/state/system/boot-good-exec-status
            leaf boot-good-exec-status {
                type types-system:script-state;
                description
                    "The results of executing the CLI script file specified
                     in 'boot-good-exec'.";
            }

            ///nokia-state/state/system/boot-bad-exec-status
            leaf boot-bad-exec-status {
                type types-system:script-state;
                description
                    "The results of executing the CLI script file specified
                     in 'boot-bad-exec'.";
            }

            ///nokia-state/state/system/alarms
            container alarms {
                description "Enter the alarms context";

                ///nokia-state/state/system/alarms/active
                list active {
                    key "raised-time index";
                    description "Enter the active list instance";

                    ///nokia-state/state/system/alarms/active/raised-time
                    leaf raised-time {
                        type yang:date-and-time;
                        description "Date and time when the alarm was raised";
                    }

                    ///nokia-state/state/system/alarms/active/index
                    leaf index {
                        type uint32;
                        description "Monotonically increasing index of entries in the alarm list";
                    }

                    ///nokia-state/state/system/alarms/active/severity
                    leaf severity {
                        type types-log:severity-level;
                        description "ITU perceived severity value";
                    }

                    ///nokia-state/state/system/alarms/active/resource
                    leaf resource {
                        type string {
                            length "0..80";
                        }
                        description "The affected resource in the system (e.g. Fan 1)";
                    }

                    ///nokia-state/state/system/alarms/active/details
                    leaf details {
                        type string {
                            length "0..255";
                        }
                        description "A textual description of the alarm";
                    }

                    ///nokia-state/state/system/alarms/active/alarm-id
                    container alarm-id {
                        description "Enter the alarm-id context";

                        ///nokia-state/state/system/alarms/active/alarm-id/full-id
                        leaf full-id {
                            type string;
                            description "Compound format of the alarm-id";
                        }

                        ///nokia-state/state/system/alarms/active/alarm-id/id-components
                        container id-components {
                            description "Enter the id-components context";

                            ///nokia-state/state/system/alarms/active/alarm-id/id-components/application
                            leaf application {
                                type types-log:application-state;
                                description "Identifier for the SR OS application associated with the alarm type";
                            }

                            ///nokia-state/state/system/alarms/active/alarm-id/id-components/raising-event-id
                            leaf raising-event-id {
                                type types-log:log-event-id;
                                description "Log event id of the raising log event associated with the alarm type";
                            }

                            ///nokia-state/state/system/alarms/active/alarm-id/id-components/alarm-sub-id
                            leaf alarm-sub-id {
                                type uint32;
                                description "Used to distinguish multiple alarm types that are associated with a single event-id";
                            }

                        } // container id-components

                    } // container alarm-id

                } // list active

                ///nokia-state/state/system/alarms/cleared
                list cleared {
                    key "cleared-time index";
                    description "Enter the cleared list instance";

                    ///nokia-state/state/system/alarms/cleared/cleared-time
                    leaf cleared-time {
                        type yang:date-and-time;
                        description "Date and time when the alarm was cleared";
                    }

                    ///nokia-state/state/system/alarms/cleared/index
                    leaf index {
                        type uint32;
                        description "Monotonically increasing index of entries in the alarm list";
                    }

                    ///nokia-state/state/system/alarms/cleared/severity
                    leaf severity {
                        type types-log:severity-level;
                        description "ITU perceived severity value";
                    }

                    ///nokia-state/state/system/alarms/cleared/resource
                    leaf resource {
                        type string {
                            length "0..80";
                        }
                        description "The affected resource in the system (e.g. Fan 1)";
                    }

                    ///nokia-state/state/system/alarms/cleared/subject
                    leaf subject {
                        status obsolete;
                        type string {
                            length "0..32";
                        }
                        description "Affected object for the event (e.g. interface name or port identifier)";
                    }

                    ///nokia-state/state/system/alarms/cleared/details
                    leaf details {
                        type string {
                            length "0..255";
                        }
                        description "A textual description of the alarm";
                    }

                    ///nokia-state/state/system/alarms/cleared/alarm-id
                    container alarm-id {
                        description "Enter the alarm-id context";

                        ///nokia-state/state/system/alarms/cleared/alarm-id/full-id
                        leaf full-id {
                            type string;
                            description "Compound format of the alarm-id";
                        }

                        ///nokia-state/state/system/alarms/cleared/alarm-id/id-components
                        container id-components {
                            description "Enter the id-components context";

                            ///nokia-state/state/system/alarms/cleared/alarm-id/id-components/application
                            leaf application {
                                type types-log:application-state;
                                description "Identifier for the SR OS application associated with the alarm type";
                            }

                            ///nokia-state/state/system/alarms/cleared/alarm-id/id-components/raising-event-id
                            leaf raising-event-id {
                                type types-log:log-event-id;
                                description "Log event id of the raising log event associated with the alarm type";
                            }

                            ///nokia-state/state/system/alarms/cleared/alarm-id/id-components/alarm-sub-id
                            leaf alarm-sub-id {
                                type uint32;
                                description "Used to distinguish multiple alarm types that are associated with a single event-id";
                            }

                        } // container id-components

                    } // container alarm-id

                } // list cleared

            } // container alarms

            ///nokia-state/state/system/alarm-contact-input
            list alarm-contact-input {
                key "input-pin-number";
                description "Enter the alarm-contact-input list instance";

                ///nokia-state/state/system/alarm-contact-input/input-pin-number
                leaf input-pin-number {
                    type int32 {
                        range "1..4";
                    }
                    description "Alarm contact input pin";
                }

                ///nokia-state/state/system/alarm-contact-input/input-status
                leaf input-status {
                    type enumeration {
                        enum no-alarm                       { value 1; }
                        enum alarm                          { value 2; }
                    }
                    description
                        "Current input status of the alarm contact input.

                         Values:
                            alarm    - Input pin is triggered (not at the normal state)
                            no-alarm - Input pin is not triggered (at the normal state)";
                }

                ///nokia-state/state/system/alarm-contact-input/last-status-changed
                leaf last-status-changed {
                    type yang:date-and-time;
                    description "Time that the input pin last changed status.";
                }

            } // list alarm-contact-input

            ///nokia-state/state/system/fp
            container fp {
                description "Enter the fp context";

                ///nokia-state/state/system/fp/options
                container options {
                    description "Enable the options context";

                    ///nokia-state/state/system/fp/options/qos
                    container qos {
                        description "Enter the qos context";

                        ///nokia-state/state/system/fp/options/qos/dscp-transparency
                        container dscp-transparency {
                            description "Enter the dscp-transparency context";

                            ///nokia-state/state/system/fp/options/qos/dscp-transparency/oper-state
                            leaf oper-state {
                                type types-sros:enabled-disabled;
                                description "Indicates the DSCP transparency option operational state.";
                            }

                        } // container dscp-transparency

                        ///nokia-state/state/system/fp/options/qos/fc-4-profile
                        container fc-4-profile {
                            description "Enter the fc-4-profile context";

                            ///nokia-state/state/system/fp/options/qos/fc-4-profile/oper-state
                            leaf oper-state {
                                type types-sros:enabled-disabled;
                                description "Indicates the fc-4-profile option operational state.";
                            }

                        } // container fc-4-profile

                        ///nokia-state/state/system/fp/options/qos/mac-classification-criteria
                        container mac-classification-criteria {
                            description "Enter the mac-classification-criteria context";

                            ///nokia-state/state/system/fp/options/qos/mac-classification-criteria/oper-state
                            leaf oper-state {
                                type types-sros:enabled-disabled;
                                description "Indicates the QOS mac classification criteria operational state.";
                            }

                        } // container mac-classification-criteria

                        ///nokia-state/state/system/fp/options/qos/ipv6-classification-criteria
                        container ipv6-classification-criteria {
                            description "Enter the ipv6-classification-criteria context";

                            ///nokia-state/state/system/fp/options/qos/ipv6-classification-criteria/oper-state
                            leaf oper-state {
                                type types-sros:enabled-disabled;
                                description "Indicates the QOS ipv6 classification criteria operational state.";
                            }

                        } // container ipv6-classification-criteria

                        ///nokia-state/state/system/fp/options/qos/bum-policers
                        container bum-policers {
                            description "Enter the bum-policers context";

                            ///nokia-state/state/system/fp/options/qos/bum-policers/oper-state
                            leaf oper-state {
                                type types-sros:enabled-disabled;
                                description "Indicates the QOS bum policers operational state.";
                            }

                        } // container bum-policers

                        ///nokia-state/state/system/fp/options/qos/shared-policer
                        container shared-policer {
                            description "Enter the shared-policer context";

                            ///nokia-state/state/system/fp/options/qos/shared-policer/oper-state
                            leaf oper-state {
                                type types-sros:enabled-disabled;
                                description "Indicates the QOS shared policer operational state.";
                            }

                        } // container shared-policer

                    } // container qos

                    ///nokia-state/state/system/fp/options/mpls
                    container mpls {
                        description "Enter the mpls context";

                        ///nokia-state/state/system/fp/options/mpls/entropy-label
                        container entropy-label {
                            description "Enter the entropy-label context";

                            ///nokia-state/state/system/fp/options/mpls/entropy-label/oper-state
                            leaf oper-state {
                                type types-sros:enabled-disabled;
                                description "Indicates the entropy label option operational state.";
                            }

                        } // container entropy-label

                        ///nokia-state/state/system/fp/options/mpls/fast-switchover
                        container fast-switchover {
                            status obsolete;
                            description "Enter the fast-switchover context";

                            ///nokia-state/state/system/fp/options/mpls/fast-switchover/oper-state
                            leaf oper-state {
                                status obsolete;
                                type types-sros:enabled-disabled;
                                description "Indicates the MPLS fast switchover option operational state.";
                            }

                        } // container fast-switchover

                    } // container mpls

                    ///nokia-state/state/system/fp/options/service
                    container service {
                        description "Enter the service context";

                        ///nokia-state/state/system/fp/options/service/ces
                        container ces {
                            description "Enter the ces context";

                            ///nokia-state/state/system/fp/options/service/ces/oper-state
                            leaf oper-state {
                                type types-sros:enabled-disabled;
                                description "Indicates the CES service option operational state.";
                            }

                        } // container ces

                        ///nokia-state/state/system/fp/options/service/ring-aps
                        container ring-aps {
                            description "Enter the ring-aps context";

                            ///nokia-state/state/system/fp/options/service/ring-aps/oper-state
                            leaf oper-state {
                                type types-sros:enabled-disabled;
                                description "Indicates the ring-aps option operational state.";
                            }

                        } // container ring-aps

                        ///nokia-state/state/system/fp/options/service/vpls-evpn-mpls
                        container vpls-evpn-mpls {
                            description "Enter the vpls-evpn-mpls context";

                            ///nokia-state/state/system/fp/options/service/vpls-evpn-mpls/oper-state
                            leaf oper-state {
                                type types-sros:enabled-disabled;
                                description "Indicates the VPLS-EVPN-MPLS option operational state.";
                            }

                        } // container vpls-evpn-mpls

                    } // container service

                    ///nokia-state/state/system/fp/options/mac-filter
                    container mac-filter {
                        status obsolete;
                        description "Enter the mac-filter context";

                        ///nokia-state/state/system/fp/options/mac-filter/outer-vlan-priority
                        container outer-vlan-priority {
                            status obsolete;
                            description "Enter the outer-vlan-priority context";

                            ///nokia-state/state/system/fp/options/mac-filter/outer-vlan-priority/oper-state
                            leaf oper-state {
                                status obsolete;
                                type types-sros:enabled-disabled;
                                description
                                    "Indicates the MAC filter outer VLAN priority option operational state.
                                     This leaf was deprecated in release 22.2 on Nokia SROS series";
                            }

                        } // container outer-vlan-priority

                    } // container mac-filter

                    ///nokia-state/state/system/fp/options/router
                    container router {
                        description "Enter the router context";

                        ///nokia-state/state/system/fp/options/router/ecmp
                        container ecmp {
                            status obsolete;
                            description "Enter the ecmp context";

                            ///nokia-state/state/system/fp/options/router/ecmp/oper-state
                            leaf oper-state {
                                status obsolete;
                                type types-sros:enabled-disabled;
                                description "Indicates the router ECMP option operational state.";
                            }

                        } // container ecmp

                    } // container router

                    ///nokia-state/state/system/fp/options/ethernet
                    container ethernet {
                        description "Enter the ethernet context";

                        ///nokia-state/state/system/fp/options/ethernet/dot1x-host-authentication
                        container dot1x-host-authentication {
                            description "Enter the dot1x-host-authentication context";

                            ///nokia-state/state/system/fp/options/ethernet/dot1x-host-authentication/oper-state
                            leaf oper-state {
                                type types-sros:enabled-disabled;
                                description "Indicates the dot1x-host-authentication operational state.";
                            }

                        } // container dot1x-host-authentication

                    } // container ethernet

                    ///nokia-state/state/system/fp/options/ip-filter
                    container ip-filter {
                        description "Enter the ip-filter context";

                        ///nokia-state/state/system/fp/options/ip-filter/pbr-redirect
                        container pbr-redirect {
                            description "Enter the pbr-redirect context";

                            ///nokia-state/state/system/fp/options/ip-filter/pbr-redirect/oper-state
                            leaf oper-state {
                                type types-sros:enabled-disabled;
                                description "Indicates the pbr-redirect operational state.";
                            }

                        } // container pbr-redirect

                        ///nokia-state/state/system/fp/options/ip-filter/stats-collection
                        container stats-collection {
                            description "Enter the stats-collection context";

                            ///nokia-state/state/system/fp/options/ip-filter/stats-collection/oper-state
                            leaf oper-state {
                                type types-sros:enabled-disabled;
                                description "Indicates the stats-collection operational state.";
                            }

                        } // container stats-collection

                    } // container ip-filter

                    ///nokia-state/state/system/fp/options/ipv6-filter
                    container ipv6-filter {
                        description "Enter the ipv6-filter context";

                        ///nokia-state/state/system/fp/options/ipv6-filter/egress
                        container egress {
                            description "Enter the egress context";

                            ///nokia-state/state/system/fp/options/ipv6-filter/egress/oper-state
                            leaf oper-state {
                                type types-sros:enabled-disabled;
                                description "Indicates the egress ipv6-filter operational state.";
                            }

                        } // container egress

                        ///nokia-state/state/system/fp/options/ipv6-filter/dst-ip-lsb
                        container dst-ip-lsb {
                            description "Enter the dst-ip-lsb context";

                            ///nokia-state/state/system/fp/options/ipv6-filter/dst-ip-lsb/oper-state
                            leaf oper-state {
                                type types-sros:enabled-disabled;
                                description "Indicates the dst-ip-lsb operational state.";
                            }

                        } // container dst-ip-lsb

                        ///nokia-state/state/system/fp/options/ipv6-filter/dst-port
                        container dst-port {
                            description "Enter the dst-port context";

                            ///nokia-state/state/system/fp/options/ipv6-filter/dst-port/oper-state
                            leaf oper-state {
                                type types-sros:enabled-disabled;
                                description "Indicates the dst-port operational state.";
                            }

                        } // container dst-port

                        ///nokia-state/state/system/fp/options/ipv6-filter/flow-label
                        container flow-label {
                            description "Enter the flow-label context";

                            ///nokia-state/state/system/fp/options/ipv6-filter/flow-label/oper-state
                            leaf oper-state {
                                type types-sros:enabled-disabled;
                                description "Indicates the flow-label operational state.";
                            }

                        } // container flow-label

                        ///nokia-state/state/system/fp/options/ipv6-filter/next-header
                        container next-header {
                            description "Enter the next-header context";

                            ///nokia-state/state/system/fp/options/ipv6-filter/next-header/oper-state
                            leaf oper-state {
                                type types-sros:enabled-disabled;
                                description "Indicates the next-header operational state.";
                            }

                        } // container next-header

                        ///nokia-state/state/system/fp/options/ipv6-filter/pbr-redirect
                        container pbr-redirect {
                            description "Enter the pbr-redirect context";

                            ///nokia-state/state/system/fp/options/ipv6-filter/pbr-redirect/oper-state
                            leaf oper-state {
                                type types-sros:enabled-disabled;
                                description "Indicates the pbr-redirect operational state.";
                            }

                        } // container pbr-redirect

                        ///nokia-state/state/system/fp/options/ipv6-filter/src-port
                        container src-port {
                            description "Enter the src-port context";

                            ///nokia-state/state/system/fp/options/ipv6-filter/src-port/oper-state
                            leaf oper-state {
                                type types-sros:enabled-disabled;
                                description "Indicates the src-port operational state.";
                            }

                        } // container src-port

                        ///nokia-state/state/system/fp/options/ipv6-filter/stats-collection
                        container stats-collection {
                            description "Enter the stats-collection context";

                            ///nokia-state/state/system/fp/options/ipv6-filter/stats-collection/oper-state
                            leaf oper-state {
                                type types-sros:enabled-disabled;
                                description "Indicates the stats-collection operational state.";
                            }

                        } // container stats-collection

                        ///nokia-state/state/system/fp/options/ipv6-filter/tcp-flags
                        container tcp-flags {
                            description "Enter the tcp-flags context";

                            ///nokia-state/state/system/fp/options/ipv6-filter/tcp-flags/oper-state
                            leaf oper-state {
                                type types-sros:enabled-disabled;
                                description "Indicates the tcp-flags operational state.";
                            }

                        } // container tcp-flags

                    } // container ipv6-filter

                    ///nokia-state/state/system/fp/options/lpm-allocation
                    container lpm-allocation {
                        status obsolete;
                        description "Enter the lpm-allocation context";

                        ///nokia-state/state/system/fp/options/lpm-allocation/scale-option-1
                        container scale-option-1 {
                            status obsolete;
                            description "Enter the scale-option-1 context";

                            ///nokia-state/state/system/fp/options/lpm-allocation/scale-option-1/oper-state
                            leaf oper-state {
                                status obsolete;
                                type types-sros:enabled-disabled;
                                description
                                    "Indicates the scale-option-1 operational state.

                                     This leaf was obsoleted in release 22.2. It was replaced by
                                     system/fp/resource-allocation/lpm/scale-option/oper-state when
                                     key option is 1.";
                            }

                        } // container scale-option-1

                        ///nokia-state/state/system/fp/options/lpm-allocation/scale-option-2
                        container scale-option-2 {
                            status obsolete;
                            description "Enter the scale-option-2 context";

                            ///nokia-state/state/system/fp/options/lpm-allocation/scale-option-2/oper-state
                            leaf oper-state {
                                status obsolete;
                                type types-sros:enabled-disabled;
                                description
                                    "Indicates the scale-option-2 operational state.

                                     This leaf was obsoleted in release 22.2. It was replaced by
                                     system/fp/resource-allocation/lpm/scale-option/oper-state when
                                     key option is 2.";
                            }

                        } // container scale-option-2

                        ///nokia-state/state/system/fp/options/lpm-allocation/scale-option-3
                        container scale-option-3 {
                            status obsolete;
                            description "Enter the scale-option-3 context";

                            ///nokia-state/state/system/fp/options/lpm-allocation/scale-option-3/oper-state
                            leaf oper-state {
                                status obsolete;
                                type types-sros:enabled-disabled;
                                description
                                    "Indicates the scale-option-3 operational state.

                                     This leaf was obsoleted in release 22.2. It was replaced by
                                     system/fp/resource-allocation/lpm/scale-option/oper-state when
                                     key option is 3.";
                            }

                        } // container scale-option-3

                    } // container lpm-allocation

                } // container options

                ///nokia-state/state/system/fp/resource-allocation
                container resource-allocation {
                    description "Enter the resource-allocation context";

                    ///nokia-state/state/system/fp/resource-allocation/oper-g8032-sap
                    leaf oper-g8032-sap {
                        status obsolete;
                        type uint32 {
                            range "0..4096";
                        }
                        description
                            "Operational Max G8032 SAP entries
                             This leaf was deprecated in release 21.10 on Nokia SROS series
                             It has been replaced by /system/fp/resource-alloction/fec/system-wide/oper-paired.";
                    }

                    ///nokia-state/state/system/fp/resource-allocation/egress-encap
                    container egress-encap {
                        description "Enter the egress-encap context";

                        ///nokia-state/state/system/fp/resource-allocation/egress-encap/oper-port-vlan-translation
                        leaf oper-port-vlan-translation {
                            type enumeration {
                                enum 2k                             { value 1; }
                                enum 4k                             { value 2; }
                                enum 8k                             { value 3; }
                                enum 16k                            { value 4; }
                            }
                            description
                                "Indicates the operational number of egress encapsulated port VLAN
                                 translation entries that have been allocated for the given FP.";
                        }

                        ///nokia-state/state/system/fp/resource-allocation/egress-encap/oper-routed
                        leaf oper-routed {
                            type enumeration {
                                enum 4k                             { value 1; }
                                enum 8k                             { value 2; }
                                enum 12k                            { value 3; }
                            }
                            description
                                "Indicates the operational number of egress encapsulated routable
                                 entries that have been allocated for the given FP.";
                        }

                    } // container egress-encap

                    ///nokia-state/state/system/fp/resource-allocation/filter
                    container filter {
                        description "Enter the filter context";

                        ///nokia-state/state/system/fp/resource-allocation/filter/oper-ipv6-number
                        leaf oper-ipv6-number {
                            type uint32 {
                                range "0|2|4|6|8|10";
                            }
                            description "Operational ipv6 filter resource allocated.";
                        }

                        ///nokia-state/state/system/fp/resource-allocation/filter/ingress
                        container ingress {
                            description "Enter the ingress context";

                            ///nokia-state/state/system/fp/resource-allocation/filter/ingress/ip-filter
                            container ip-filter {
                                description "Enable the ip-filter context";

                                ///nokia-state/state/system/fp/resource-allocation/filter/ingress/ip-filter/actions
                                container actions {
                                    description "Enable the actions context";

                                    ///nokia-state/state/system/fp/resource-allocation/filter/ingress/ip-filter/actions/drop
                                    container drop {
                                        description "Enter the drop context";

                                        ///nokia-state/state/system/fp/resource-allocation/filter/ingress/ip-filter/actions/drop/oper-state
                                        leaf oper-state {
                                            type types-sros:enabled-disabled;
                                            description "Indicates the action drop operational state.";
                                        }

                                    } // container drop

                                    ///nokia-state/state/system/fp/resource-allocation/filter/ingress/ip-filter/actions/fc
                                    container fc {
                                        description "Enter the fc context";

                                        ///nokia-state/state/system/fp/resource-allocation/filter/ingress/ip-filter/actions/fc/oper-state
                                        leaf oper-state {
                                            type types-sros:enabled-disabled;
                                            description "Indicates the action fc operational state.";
                                        }

                                    } // container fc

                                    ///nokia-state/state/system/fp/resource-allocation/filter/ingress/ip-filter/actions/log
                                    container log {
                                        description "Enter the log context";

                                        ///nokia-state/state/system/fp/resource-allocation/filter/ingress/ip-filter/actions/log/oper-state
                                        leaf oper-state {
                                            type types-sros:enabled-disabled;
                                            description "Indicates the log action operational state.";
                                        }

                                    } // container log

                                    ///nokia-state/state/system/fp/resource-allocation/filter/ingress/ip-filter/actions/mirror
                                    container mirror {
                                        description "Enter the mirror context";

                                        ///nokia-state/state/system/fp/resource-allocation/filter/ingress/ip-filter/actions/mirror/oper-state
                                        leaf oper-state {
                                            type types-sros:enabled-disabled;
                                            description "Indicates the mirror action operational state.";
                                        }

                                    } // container mirror

                                    ///nokia-state/state/system/fp/resource-allocation/filter/ingress/ip-filter/actions/redirect
                                    container redirect {
                                        description "Enter the redirect context";

                                        ///nokia-state/state/system/fp/resource-allocation/filter/ingress/ip-filter/actions/redirect/oper-state
                                        leaf oper-state {
                                            type types-sros:enabled-disabled;
                                            description "Indicates the action redirect operational state.";
                                        }

                                    } // container redirect

                                    ///nokia-state/state/system/fp/resource-allocation/filter/ingress/ip-filter/actions/stats-collection
                                    container stats-collection {
                                        description "Enter the stats-collection context";

                                        ///nokia-state/state/system/fp/resource-allocation/filter/ingress/ip-filter/actions/stats-collection/oper-state
                                        leaf oper-state {
                                            type types-sros:enabled-disabled;
                                            description "Indicates the filter statistics collection operational state.";
                                        }

                                    } // container stats-collection

                                } // container actions

                                ///nokia-state/state/system/fp/resource-allocation/filter/ingress/ip-filter/match-criteria
                                container match-criteria {
                                    description "Enter the match-criteria context";

                                    ///nokia-state/state/system/fp/resource-allocation/filter/ingress/ip-filter/match-criteria/dscp
                                    container dscp {
                                        description "Enter the dscp context";

                                        ///nokia-state/state/system/fp/resource-allocation/filter/ingress/ip-filter/match-criteria/dscp/oper-state
                                        leaf oper-state {
                                            type types-sros:enabled-disabled;
                                            description "Indicates the dscp operational state.";
                                        }

                                    } // container dscp

                                    ///nokia-state/state/system/fp/resource-allocation/filter/ingress/ip-filter/match-criteria/dst-ip
                                    container dst-ip {
                                        description "Enter the dst-ip context";

                                        ///nokia-state/state/system/fp/resource-allocation/filter/ingress/ip-filter/match-criteria/dst-ip/oper-state
                                        leaf oper-state {
                                            type types-sros:enabled-disabled;
                                            description "Indicates the destination ip address operational state.";
                                        }

                                    } // container dst-ip

                                    ///nokia-state/state/system/fp/resource-allocation/filter/ingress/ip-filter/match-criteria/dst-port
                                    container dst-port {
                                        description "Enter the dst-port context";

                                        ///nokia-state/state/system/fp/resource-allocation/filter/ingress/ip-filter/match-criteria/dst-port/oper-state
                                        leaf oper-state {
                                            type types-sros:enabled-disabled;
                                            description "Indicates the destination port operational state.";
                                        }

                                    } // container dst-port

                                    ///nokia-state/state/system/fp/resource-allocation/filter/ingress/ip-filter/match-criteria/protocol
                                    container protocol {
                                        description "Enter the protocol context";

                                        ///nokia-state/state/system/fp/resource-allocation/filter/ingress/ip-filter/match-criteria/protocol/oper-state
                                        leaf oper-state {
                                            type types-sros:enabled-disabled;
                                            description "Indicates the protocol operational state.";
                                        }

                                    } // container protocol

                                    ///nokia-state/state/system/fp/resource-allocation/filter/ingress/ip-filter/match-criteria/src-ip
                                    container src-ip {
                                        description "Enter the src-ip context";

                                        ///nokia-state/state/system/fp/resource-allocation/filter/ingress/ip-filter/match-criteria/src-ip/oper-state
                                        leaf oper-state {
                                            type types-sros:enabled-disabled;
                                            description "Indicates the source ip address operational state.";
                                        }

                                    } // container src-ip

                                    ///nokia-state/state/system/fp/resource-allocation/filter/ingress/ip-filter/match-criteria/src-port
                                    container src-port {
                                        description "Enter the src-port context";

                                        ///nokia-state/state/system/fp/resource-allocation/filter/ingress/ip-filter/match-criteria/src-port/oper-state
                                        leaf oper-state {
                                            type types-sros:enabled-disabled;
                                            description "Indicates the source port operational state.";
                                        }

                                    } // container src-port

                                    ///nokia-state/state/system/fp/resource-allocation/filter/ingress/ip-filter/match-criteria/tcp-flags
                                    container tcp-flags {
                                        description "Enter the tcp-flags context";

                                        ///nokia-state/state/system/fp/resource-allocation/filter/ingress/ip-filter/match-criteria/tcp-flags/oper-state
                                        leaf oper-state {
                                            type types-sros:enabled-disabled;
                                            description "Indicates the tcp flags operational state.";
                                        }

                                    } // container tcp-flags

                                } // container match-criteria

                            } // container ip-filter

                            ///nokia-state/state/system/fp/resource-allocation/filter/ingress/ipv6-filter
                            container ipv6-filter {
                                description "Enable the ipv6-filter context";

                                ///nokia-state/state/system/fp/resource-allocation/filter/ingress/ipv6-filter/actions
                                container actions {
                                    description "Enter the actions context";

                                    ///nokia-state/state/system/fp/resource-allocation/filter/ingress/ipv6-filter/actions/drop
                                    container drop {
                                        description "Enter the drop context";

                                        ///nokia-state/state/system/fp/resource-allocation/filter/ingress/ipv6-filter/actions/drop/oper-state
                                        leaf oper-state {
                                            type types-sros:enabled-disabled;
                                            description "Indicates the action drop operational state.";
                                        }

                                    } // container drop

                                    ///nokia-state/state/system/fp/resource-allocation/filter/ingress/ipv6-filter/actions/fc
                                    container fc {
                                        description "Enter the fc context";

                                        ///nokia-state/state/system/fp/resource-allocation/filter/ingress/ipv6-filter/actions/fc/oper-state
                                        leaf oper-state {
                                            type types-sros:enabled-disabled;
                                            description "Indicates the action fc operational state.";
                                        }

                                    } // container fc

                                    ///nokia-state/state/system/fp/resource-allocation/filter/ingress/ipv6-filter/actions/log
                                    container log {
                                        description "Enter the log context";

                                        ///nokia-state/state/system/fp/resource-allocation/filter/ingress/ipv6-filter/actions/log/oper-state
                                        leaf oper-state {
                                            type types-sros:enabled-disabled;
                                            description "Indicates the log action operational state.";
                                        }

                                    } // container log

                                    ///nokia-state/state/system/fp/resource-allocation/filter/ingress/ipv6-filter/actions/mirror
                                    container mirror {
                                        description "Enter the mirror context";

                                        ///nokia-state/state/system/fp/resource-allocation/filter/ingress/ipv6-filter/actions/mirror/oper-state
                                        leaf oper-state {
                                            type types-sros:enabled-disabled;
                                            description "Indicates the mirror action operational state.";
                                        }

                                    } // container mirror

                                    ///nokia-state/state/system/fp/resource-allocation/filter/ingress/ipv6-filter/actions/redirect
                                    container redirect {
                                        description "Enter the redirect context";

                                        ///nokia-state/state/system/fp/resource-allocation/filter/ingress/ipv6-filter/actions/redirect/oper-state
                                        leaf oper-state {
                                            type types-sros:enabled-disabled;
                                            description "Indicates the action redirect operational state.";
                                        }

                                    } // container redirect

                                    ///nokia-state/state/system/fp/resource-allocation/filter/ingress/ipv6-filter/actions/stats-collection
                                    container stats-collection {
                                        description "Enter the stats-collection context";

                                        ///nokia-state/state/system/fp/resource-allocation/filter/ingress/ipv6-filter/actions/stats-collection/oper-state
                                        leaf oper-state {
                                            type types-sros:enabled-disabled;
                                            description "Indicates the filter statistics collection operational state.";
                                        }

                                    } // container stats-collection

                                } // container actions

                                ///nokia-state/state/system/fp/resource-allocation/filter/ingress/ipv6-filter/match-criteria
                                container match-criteria {
                                    description "Enable the match-criteria context";

                                    ///nokia-state/state/system/fp/resource-allocation/filter/ingress/ipv6-filter/match-criteria/dscp
                                    container dscp {
                                        description "Enter the dscp context";

                                        ///nokia-state/state/system/fp/resource-allocation/filter/ingress/ipv6-filter/match-criteria/dscp/oper-state
                                        leaf oper-state {
                                            type types-sros:enabled-disabled;
                                            description "Indicates the dscp operational state.";
                                        }

                                    } // container dscp

                                    ///nokia-state/state/system/fp/resource-allocation/filter/ingress/ipv6-filter/match-criteria/dst-ip-lsb
                                    container dst-ip-lsb {
                                        description "Enter the dst-ip-lsb context";

                                        ///nokia-state/state/system/fp/resource-allocation/filter/ingress/ipv6-filter/match-criteria/dst-ip-lsb/oper-state
                                        leaf oper-state {
                                            type types-sros:enabled-disabled;
                                            description "Indicates the destination ip least significant bit operational state.";
                                        }

                                    } // container dst-ip-lsb

                                    ///nokia-state/state/system/fp/resource-allocation/filter/ingress/ipv6-filter/match-criteria/dst-ip-msb
                                    container dst-ip-msb {
                                        description "Enter the dst-ip-msb context";

                                        ///nokia-state/state/system/fp/resource-allocation/filter/ingress/ipv6-filter/match-criteria/dst-ip-msb/oper-state
                                        leaf oper-state {
                                            type types-sros:enabled-disabled;
                                            description "Indicates the destination ip most significant bit operational state.";
                                        }

                                    } // container dst-ip-msb

                                    ///nokia-state/state/system/fp/resource-allocation/filter/ingress/ipv6-filter/match-criteria/dst-port
                                    container dst-port {
                                        description "Enter the dst-port context";

                                        ///nokia-state/state/system/fp/resource-allocation/filter/ingress/ipv6-filter/match-criteria/dst-port/oper-state
                                        leaf oper-state {
                                            type types-sros:enabled-disabled;
                                            description "Indicates the destination port operational state.";
                                        }

                                    } // container dst-port

                                    ///nokia-state/state/system/fp/resource-allocation/filter/ingress/ipv6-filter/match-criteria/flow-label
                                    container flow-label {
                                        description "Enter the flow-label context";

                                        ///nokia-state/state/system/fp/resource-allocation/filter/ingress/ipv6-filter/match-criteria/flow-label/oper-state
                                        leaf oper-state {
                                            type types-sros:enabled-disabled;
                                            description "Indicates the flow-label operational state.";
                                        }

                                    } // container flow-label

                                    ///nokia-state/state/system/fp/resource-allocation/filter/ingress/ipv6-filter/match-criteria/next-header
                                    container next-header {
                                        description "Enter the next-header context";

                                        ///nokia-state/state/system/fp/resource-allocation/filter/ingress/ipv6-filter/match-criteria/next-header/oper-state
                                        leaf oper-state {
                                            type types-sros:enabled-disabled;
                                            description "Indicates the next-header operational state.";
                                        }

                                    } // container next-header

                                    ///nokia-state/state/system/fp/resource-allocation/filter/ingress/ipv6-filter/match-criteria/src-ip-lsb
                                    container src-ip-lsb {
                                        description "Enter the src-ip-lsb context";

                                        ///nokia-state/state/system/fp/resource-allocation/filter/ingress/ipv6-filter/match-criteria/src-ip-lsb/oper-state
                                        leaf oper-state {
                                            type types-sros:enabled-disabled;
                                            description "Indicates the source ip least significant bit operational state.";
                                        }

                                    } // container src-ip-lsb

                                    ///nokia-state/state/system/fp/resource-allocation/filter/ingress/ipv6-filter/match-criteria/src-ip-msb
                                    container src-ip-msb {
                                        description "Enter the src-ip-msb context";

                                        ///nokia-state/state/system/fp/resource-allocation/filter/ingress/ipv6-filter/match-criteria/src-ip-msb/oper-state
                                        leaf oper-state {
                                            type types-sros:enabled-disabled;
                                            description "Indicates the source ip most significant bit operational state.";
                                        }

                                    } // container src-ip-msb

                                    ///nokia-state/state/system/fp/resource-allocation/filter/ingress/ipv6-filter/match-criteria/src-port
                                    container src-port {
                                        description "Enter the src-port context";

                                        ///nokia-state/state/system/fp/resource-allocation/filter/ingress/ipv6-filter/match-criteria/src-port/oper-state
                                        leaf oper-state {
                                            type types-sros:enabled-disabled;
                                            description "Indicates the source port operational state.";
                                        }

                                    } // container src-port

                                    ///nokia-state/state/system/fp/resource-allocation/filter/ingress/ipv6-filter/match-criteria/tcp-flags
                                    container tcp-flags {
                                        description "Enter the tcp-flags context";

                                        ///nokia-state/state/system/fp/resource-allocation/filter/ingress/ipv6-filter/match-criteria/tcp-flags/oper-state
                                        leaf oper-state {
                                            type types-sros:enabled-disabled;
                                            description "Indicates the tcp flags operational state.";
                                        }

                                    } // container tcp-flags

                                } // container match-criteria

                            } // container ipv6-filter

                        } // container ingress

                    } // container filter

                    ///nokia-state/state/system/fp/resource-allocation/pool
                    list pool {
                        key "pool-id";
                        description "Enter the pool list instance";

                        ///nokia-state/state/system/fp/resource-allocation/pool/pool-id
                        leaf pool-id {
                            type uint32 {
                                range "1..2";
                            }
                            description "Pool identifier";
                        }

                        ///nokia-state/state/system/fp/resource-allocation/pool/lag-bundle
                        container lag-bundle {
                            description "Enter the lag-bundle context";

                            ///nokia-state/state/system/fp/resource-allocation/pool/lag-bundle/oper-reserved-member-count
                            leaf oper-reserved-member-count {
                                type uint32;
                                description "Indicates the operational member count reserved for the lag-bundle.";
                            }

                        } // container lag-bundle

                    } // list pool

                    ///nokia-state/state/system/fp/resource-allocation/fec
                    container fec {
                        description "Enter the fec context";

                        ///nokia-state/state/system/fp/resource-allocation/fec/system-wide
                        container system-wide {
                            description "Enter the system-wide context";

                            ///nokia-state/state/system/fp/resource-allocation/fec/system-wide/oper-unpaired
                            leaf oper-unpaired {
                                type uint32;
                                description "Indicates the operational number of system-wide unpaired FEC space.";
                            }

                            ///nokia-state/state/system/fp/resource-allocation/fec/system-wide/oper-paired
                            leaf oper-paired {
                                type uint32 {
                                    range "0..8192";
                                }
                                description "Indicates the operational number of paired FEC space.";
                            }

                        } // container system-wide

                    } // container fec

                    ///nokia-state/state/system/fp/resource-allocation/lpm
                    container lpm {
                        description "Enter the lpm context";

                        ///nokia-state/state/system/fp/resource-allocation/lpm/scale-option
                        list scale-option {
                            key "option";
                            description "Enter the scale-option list instance";

                            ///nokia-state/state/system/fp/resource-allocation/lpm/scale-option/option
                            leaf option {
                                type uint32 {
                                    range "1..4";
                                }
                                description "Unique LPM (FIB) scale option";
                            }

                            ///nokia-state/state/system/fp/resource-allocation/lpm/scale-option/oper-state
                            leaf oper-state {
                                type types-sros:enabled-disabled;
                                description "Indicates the operational state of the LPM scale option.";
                            }

                        } // list scale-option

                    } // container lpm

                    ///nokia-state/state/system/fp/resource-allocation/policer-and-statistics-override
                    container policer-and-statistics-override {
                        description "Enter the policer-and-statistics-override context";

                        ///nokia-state/state/system/fp/resource-allocation/policer-and-statistics-override/oper-state
                        leaf oper-state {
                            type types-sros:oper-state;
                            description "Oper state of policer-and-statistics override.";
                        }

                        ///nokia-state/state/system/fp/resource-allocation/policer-and-statistics-override/application-group
                        container application-group {
                            description "Enter the application-group context";

                            ///nokia-state/state/system/fp/resource-allocation/policer-and-statistics-override/application-group/group
                            list group {
                                key "group-id";
                                description "Enter the group list instance";

                                ///nokia-state/state/system/fp/resource-allocation/policer-and-statistics-override/application-group/group/policer-admin-total
                                leaf policer-admin-total {
                                    type uint32;
                                    description "Indicates the admin value of total number of policers in the application group.";
                                }

                                ///nokia-state/state/system/fp/resource-allocation/policer-and-statistics-override/application-group/group/policer-oper-total
                                leaf policer-oper-total {
                                    type uint32;
                                    description "Indicates the oper value of total number of policers in the application group.";
                                }

                                ///nokia-state/state/system/fp/resource-allocation/policer-and-statistics-override/application-group/group/policer-admin-alloc
                                leaf policer-admin-alloc {
                                    type uint32;
                                    description "Indicates the admin value of allocated number of policers in the application group.";
                                }

                                ///nokia-state/state/system/fp/resource-allocation/policer-and-statistics-override/application-group/group/policer-oper-alloc
                                leaf policer-oper-alloc {
                                    type uint32;
                                    description "Indicates the oper value of allocated number of policers in the application group.";
                                }

                                ///nokia-state/state/system/fp/resource-allocation/policer-and-statistics-override/application-group/group/group-id
                                leaf group-id {
                                    type uint32 {
                                        range "1";
                                    }
                                    description "Application group ID";
                                }

                                ///nokia-state/state/system/fp/resource-allocation/policer-and-statistics-override/application-group/group/policers
                                container policers {
                                    description "Enter the policers context";

                                    ///nokia-state/state/system/fp/resource-allocation/policer-and-statistics-override/application-group/group/policers/application
                                    list application {
                                        key "application-id";
                                        description "Enter the application list instance";

                                        ///nokia-state/state/system/fp/resource-allocation/policer-and-statistics-override/application-group/group/policers/application/application-id
                                        leaf application-id {
                                            type enumeration {
                                                enum per-fc-unicast-broadcast-unknown-multicast { value 1; }
                                                enum per-fc-unicast-multipoint      { value 2; }
                                                enum per-fc                         { value 3; }
                                            }
                                            description "FC policer type";
                                        }

                                        ///nokia-state/state/system/fp/resource-allocation/policer-and-statistics-override/application-group/group/policers/application/oper-scale
                                        leaf oper-scale {
                                            type int32 {
                                                range "-1..32";
                                            }
                                            description "Indicates the scale of the application.";
                                        }

                                    } // list application

                                } // container policers

                            } // list group

                        } // container application-group

                    } // container policer-and-statistics-override


                } // container resource-allocation

            } // container fp

            ///nokia-state/state/system/grpc
            container grpc {
                description "Enter the grpc context";

                ///nokia-state/state/system/grpc/oper-state
                leaf oper-state {
                    type types-sros:oper-state;
                    description "Operational state of gRPC server.";
                }

                ///nokia-state/state/system/grpc/gnoi
                container gnoi {
                    description "Enter the gnoi context";

                    ///nokia-state/state/system/grpc/gnoi/system
                    container system {
                        description "Enter the system context";

                        ///nokia-state/state/system/grpc/gnoi/system/pending-reboot
                        list pending-reboot {
                            key "sub-component";
                            description "Enter the pending-reboot list instance";

                            ///nokia-state/state/system/grpc/gnoi/system/pending-reboot/sub-component
                            leaf sub-component {
                                type string;
                                description "Object of Reboot or Cancel Reboot RPC.";
                            }

                            ///nokia-state/state/system/grpc/gnoi/system/pending-reboot/oper-state
                            leaf oper-state {
                                type types-sros:oper-state;
                                description "Operational state of reboot procedure.";
                            }

                            ///nokia-state/state/system/grpc/gnoi/system/pending-reboot/reboot-delay
                            leaf reboot-delay {
                                type uint32;
                                units "seconds";
                                description "Time left until reboot.";
                            }

                            ///nokia-state/state/system/grpc/gnoi/system/pending-reboot/last-reboot-message
                            leaf last-reboot-message {
                                type string;
                                description "Reason for reboot or for cancelation of any outstanding reboot.";
                            }

                            ///nokia-state/state/system/grpc/gnoi/system/pending-reboot/reboot-count
                            leaf reboot-count {
                                type uint32;
                                description "Number of reboots since active.";
                            }

                        } // list pending-reboot

                    } // container system

                } // container gnoi

                ///nokia-state/state/system/grpc/connection
                list connection {
                    key "address port";
                    description "Enter the connection list instance";

                    ///nokia-state/state/system/grpc/connection/address
                    leaf address {
                        type types-sros:ip-address;
                        description "IP address of gRPC client.";
                    }

                    ///nokia-state/state/system/grpc/connection/port
                    leaf port {
                        type inet:port-number;
                        description "Protocol port number of gRPC client.";
                    }

                    ///nokia-state/state/system/grpc/connection/router-instance
                    leaf router-instance {
                        type types-sros:router-instance;
                        description "The value indicates the routing context of a connection.";
                    }

                    ///nokia-state/state/system/grpc/connection/grpc-tunnel
                    leaf grpc-tunnel {
                        type leafref {
                            path "../../../grpc-tunnel/tunnel/name";
                        }
                        description "The value indicates the gRPC-Tunnel used as transport of a connection.";
                    }

                    ///nokia-state/state/system/grpc/connection/establishment-time
                    leaf establishment-time {
                        type yang:date-and-time;
                        description "The value indicates the time of connection establishment.";
                    }

                    ///nokia-state/state/system/grpc/connection/active-rpc-count
                    leaf active-rpc-count {
                        type yang:gauge64;
                        description "The value indicates the active number of RPC on this connection.";
                    }

                    ///nokia-state/state/system/grpc/connection/total-rpc-count
                    leaf total-rpc-count {
                        type yang:counter64;
                        description
                            "The value indicates the total number of RPC on this connection
                             since establishment time.";
                    }

                    ///nokia-state/state/system/grpc/connection/rx-bytes
                    leaf rx-bytes {
                        type yang:counter64;
                        units "bytes";
                        description "The value indicates the total number of bytes received over this connection.";
                    }

                    ///nokia-state/state/system/grpc/connection/tx-bytes
                    leaf tx-bytes {
                        type yang:counter64;
                        units "bytes";
                        description "The value indicates the total number of bytes sent over this connection.";
                    }

                    ///nokia-state/state/system/grpc/connection/qos
                    leaf qos {
                        type types-qos:dscp-name;
                        description
                            "Operational DSCP value of the connection. Only first Subscribe RPC with qos
                             field specified can alter connection DSCP value. DSCP value is reset to
                             sgt-qos default after last Subscribe RPC on connection is terminated.";
                    }

                    ///nokia-state/state/system/grpc/connection/last-finished-rpc
                    container last-finished-rpc {
                        description "Enter the last-finished-rpc context";

                        ///nokia-state/state/system/grpc/connection/last-finished-rpc/name
                        leaf name {
                            type types-sros:named-item;
                            description "The value indicates the name of a RPC.";
                        }

                        ///nokia-state/state/system/grpc/connection/last-finished-rpc/service-name
                        leaf service-name {
                            type types-sros:named-item;
                            description "The value indicates the name of a RPC service.";
                        }

                        ///nokia-state/state/system/grpc/connection/last-finished-rpc/duration
                        leaf duration {
                            type types-sros:time-duration-64;
                            units "milliseconds";
                            description "The value indicates duration of a RPC in milliseconds.";
                        }

                        ///nokia-state/state/system/grpc/connection/last-finished-rpc/finish-time
                        leaf finish-time {
                            type yang:date-and-time;
                            description "The value indicates the time of a RPC finish.";
                        }

                        ///nokia-state/state/system/grpc/connection/last-finished-rpc/error-rpc-status
                        leaf error-rpc-status {
                            type string {
                                length "1..256";
                            }
                            description "The value indicates the error message in a RPC status.";
                        }

                    } // container last-finished-rpc

                } // list connection

                ///nokia-state/state/system/grpc/rpc
                list rpc {
                    key "rpc-id";
                    description "Enter the rpc list instance";

                    ///nokia-state/state/system/grpc/rpc/rpc-id
                    leaf rpc-id {
                        type uint32;
                        description
                            "The value of this object uniquely identifies a RPC.
                             Id is auto-generated by the system.";
                    }

                    ///nokia-state/state/system/grpc/rpc/name
                    leaf name {
                        type types-sros:named-item;
                        description "The value indicates the name of a RPC.";
                    }

                    ///nokia-state/state/system/grpc/rpc/service-name
                    leaf service-name {
                        type types-sros:named-item;
                        description "The value indicates the name of a RPC service.";
                    }

                    ///nokia-state/state/system/grpc/rpc/establishment-time
                    leaf establishment-time {
                        type yang:date-and-time;
                        description "The value indicates the time of a RPC establishment.";
                    }

                    ///nokia-state/state/system/grpc/rpc/address
                    leaf address {
                        type types-sros:ip-address;
                        description "IP address of gRPC client who sent a RPC.";
                    }

                    ///nokia-state/state/system/grpc/rpc/port
                    leaf port {
                        type inet:port-number;
                        description "Protocol port number of gRPC client who sent a RPC.";
                    }

                    ///nokia-state/state/system/grpc/rpc/grpc-tunnel
                    leaf grpc-tunnel {
                        type leafref {
                            path "../../../grpc-tunnel/tunnel/name";
                        }
                        description "The value indicates the gRPC-Tunnel used as transport of a RPC.";
                    }

                    ///nokia-state/state/system/grpc/rpc/user-name
                    leaf user-name {
                        type types-sros:named-item;
                        description "The name of the user who sent a RPC.";
                    }

                    ///nokia-state/state/system/grpc/rpc/session-id
                    leaf session-id {
                        type uint32;
                        description
                            "The session-id of the user who sent a RPC.
                             Id is auto-generated by the system.";
                    }

                } // list rpc

                ///nokia-state/state/system/grpc/supported-services
                container supported-services {
                    description "Enter the supported-services context";

                    ///nokia-state/state/system/grpc/supported-services/gnmi-version
                    leaf gnmi-version {
                        type string {
                            length "1..10";
                        }
                        description "Indicates the version of gNMI service provided by gRPC server.";
                    }

                    ///nokia-state/state/system/grpc/supported-services/gnoi-cert-mgmt-version
                    leaf gnoi-cert-mgmt-version {
                        type string {
                            length "1..10";
                        }
                        description "Indicates the version of gNOI CertificateManagement service provided by gRPC server.";
                    }

                    ///nokia-state/state/system/grpc/supported-services/gnoi-file-version
                    leaf gnoi-file-version {
                        type string {
                            length "1..10";
                        }
                        description "Indicates the version of gNOI File service provided by gRPC server.";
                    }

                    ///nokia-state/state/system/grpc/supported-services/gnoi-system-version
                    leaf gnoi-system-version {
                        type string {
                            length "1..10";
                        }
                        description "Indicates the version of gNOI System service provided by gRPC server.";
                    }

                    ///nokia-state/state/system/grpc/supported-services/md-cli-version
                    leaf md-cli-version {
                        type string {
                            length "1..10";
                        }
                        description "Indicates the version of MD-CLI service provided by gRPC server.";
                    }

                    ///nokia-state/state/system/grpc/supported-services/rib-api-version
                    leaf rib-api-version {
                        type string {
                            length "1..10";
                        }
                        description "Indicates the version of RibApi service provided by gRPC server.";
                    }

                } // container supported-services

            } // container grpc

            ///nokia-state/state/system/grpc-tunnel
            container grpc-tunnel {
                description "Enter the grpc-tunnel context";

                ///nokia-state/state/system/grpc-tunnel/tunnel
                list tunnel {
                    key "name";
                    description "Enter the tunnel list instance";

                    ///nokia-state/state/system/grpc-tunnel/tunnel/name
                    leaf name {
                        type types-sros:named-item;
                        description "Tunnel name";
                    }

                    ///nokia-state/state/system/grpc-tunnel/tunnel/oper-state
                    leaf oper-state {
                        type types-sros:oper-state;
                        description "Operational state of tunnel.";
                    }

                    ///nokia-state/state/system/grpc-tunnel/tunnel/oper-down-reason
                    leaf oper-down-reason {
                        type string {
                            length "1..256";
                        }
                        description "The reason due to which tunnel is operationally down.";
                    }

                    ///nokia-state/state/system/grpc-tunnel/tunnel/oper-target-name
                    leaf oper-target-name {
                        type string {
                            length "1..422";
                        }
                        description "Operational target string to be sent in tunnel capability message.";
                    }

                    ///nokia-state/state/system/grpc-tunnel/tunnel/statistics
                    container statistics {
                        description "Enter the statistics context";

                        ///nokia-state/state/system/grpc-tunnel/tunnel/statistics/destination
                        list destination {
                            key "address port";
                            description "Enter the destination list instance";

                            ///nokia-state/state/system/grpc-tunnel/tunnel/statistics/destination/address
                            leaf address {
                                type union {
                                    type types-sros:ip-address;
                                    type types-sros:fully-qualified-domain-name;
                                }
                                description "Address of the destination within the destination group";
                            }

                            ///nokia-state/state/system/grpc-tunnel/tunnel/statistics/destination/port
                            leaf port {
                                type types-sros:tcp-udp-port-non-zero;
                                description "TCP port number for the destination";
                            }

                            ///nokia-state/state/system/grpc-tunnel/tunnel/statistics/destination/oper-state
                            leaf oper-state {
                                type types-sros:oper-state;
                                description "Operational state of destination.";
                            }

                            ///nokia-state/state/system/grpc-tunnel/tunnel/statistics/destination/last-oper-down-reason
                            leaf last-oper-down-reason {
                                type string {
                                    length "1..256";
                                }
                                description
                                    "The reason due to which connection to destination
                                     was operationally down.";
                            }

                            ///nokia-state/state/system/grpc-tunnel/tunnel/statistics/destination/oper-router-instance
                            leaf oper-router-instance {
                                type types-sros:router-instance;
                                description "Operational routing context of a connection.";
                            }

                            ///nokia-state/state/system/grpc-tunnel/tunnel/statistics/destination/last-oper-change
                            leaf last-oper-change {
                                type yang:date-and-time;
                                description "The time when the operational state of this destination last changed.";
                            }

                            ///nokia-state/state/system/grpc-tunnel/tunnel/statistics/destination/connection-attempts
                            leaf connection-attempts {
                                type uint64;
                                description "Number of tried connections towards this destination.";
                            }

                        } // list destination

                        ///nokia-state/state/system/grpc-tunnel/tunnel/statistics/session
                        list session {
                            key "tag";
                            description "Enter the session list instance";

                            ///nokia-state/state/system/grpc-tunnel/tunnel/statistics/session/tag
                            leaf tag {
                                type int32;
                                description
                                    "The value of this object uniquely identifies session in a tunnel.
                                     Tag is auto-generated by the gRPC-Tunnel server.";
                            }

                            ///nokia-state/state/system/grpc-tunnel/tunnel/statistics/session/establishment-time
                            leaf establishment-time {
                                type yang:date-and-time;
                                description "The value indicates the time of a session establishment.";
                            }

                            ///nokia-state/state/system/grpc-tunnel/tunnel/statistics/session/target-type
                            leaf target-type {
                                type string {
                                    length "1..64";
                                }
                                description "The value indicates requested target-type of the session.";
                            }

                            ///nokia-state/state/system/grpc-tunnel/tunnel/statistics/session/local-source-port
                            leaf local-source-port {
                                type types-sros:tcp-udp-port-non-zero;
                                description
                                    "The value indicates source protocol TCP port number of the session
                                     connection towards target aplication.";
                            }

                            ///nokia-state/state/system/grpc-tunnel/tunnel/statistics/session/rx-bytes
                            leaf rx-bytes {
                                type yang:counter64;
                                units "bytes";
                                description "The value indicates the total number of bytes received over this session.";
                            }

                            ///nokia-state/state/system/grpc-tunnel/tunnel/statistics/session/tx-bytes
                            leaf tx-bytes {
                                type yang:counter64;
                                units "bytes";
                                description "The value indicates the total number of bytes sent over this session.";
                            }

                        } // list session

                    } // container statistics

                } // list tunnel

            } // container grpc-tunnel

            ///nokia-state/state/system/management-interface
            container management-interface {
                description "Enable the management-interface context";

                ///nokia-state/state/system/management-interface/configuration-oper-mode
                leaf configuration-oper-mode {
                    type enumeration {
                        enum syncing                        { value 0; }
                        enum classic                        { value 1; }
                        enum model-driven                   { value 2; }
                        enum mixed                          { value 3; }
                    }
                    description
                        "The operational state of the management interface
                         configuration mode of the system.";
                }

                ///nokia-state/state/system/management-interface/last-mode-switch
                leaf last-mode-switch {
                    type yang:date-and-time;
                    description "The time the last configuration mode changed for the system.";
                }

                ///nokia-state/state/system/management-interface/last-mode-switch-reason
                leaf last-mode-switch-reason {
                    type enumeration {
                        enum boot                           { value 0; }
                        enum manual                         { value 1; }
                        enum validation                     { value 2; }
                    }
                    description
                        "The reason a mode switch occurred. It could be one of
                         boot, manual, or validation.";
                }

                ///nokia-state/state/system/management-interface/last-mode-switch-duration
                leaf last-mode-switch-duration {
                    type uint32;
                    units "milliseconds";
                    description
                        "The duration, in milliseconds, the last configuration mode
                         change took to activate.";
                }

                ///nokia-state/state/system/management-interface/primary-schema-path
                leaf primary-schema-path {
                    type types-system:schema-path-state-type;
                    description "Location of schema files derived from primary-image.";
                }

                ///nokia-state/state/system/management-interface/secondary-schema-path
                leaf secondary-schema-path {
                    type types-system:schema-path-state-type;
                    description "Location of schema files derived from secondary-image.";
                }

                ///nokia-state/state/system/management-interface/tertiary-schema-path
                leaf tertiary-schema-path {
                    type types-system:schema-path-state-type;
                    description "Location of schema files derived from tertiary-image.";
                }

                ///nokia-state/state/system/management-interface/oper-schema-path
                leaf oper-schema-path {
                    type types-system:schema-path-state-type;
                    description "Operational location of schema files used by the system.";
                }

                ///nokia-state/state/system/management-interface/cli
                container cli {
                    description "Enable the cli context";

                    ///nokia-state/state/system/management-interface/cli/classic-cli
                    container classic-cli {
                        description "Enter the classic-cli context";

                        ///nokia-state/state/system/management-interface/cli/classic-cli/rollback
                        container rollback {
                            description "Enable the rollback context";

                            ///nokia-state/state/system/management-interface/cli/classic-cli/rollback/save
                            container save {
                                description "Enter the save context";

                                ///nokia-state/state/system/management-interface/cli/classic-cli/rollback/save/last-save-result
                                leaf last-save-result {
                                    type types-system:action-result;
                                    description "The result of the last rollback save action.";
                                }

                                ///nokia-state/state/system/management-interface/cli/classic-cli/rollback/save/last-save-completion-time
                                leaf last-save-completion-time {
                                    type yang:date-and-time;
                                    description
                                        "The time when the last rollback save was
                                         completed on the system.";
                                }

                            } // container save

                            ///nokia-state/state/system/management-interface/cli/classic-cli/rollback/revert
                            container revert {
                                description "Enter the revert context";

                                ///nokia-state/state/system/management-interface/cli/classic-cli/rollback/revert/last-revert-index
                                leaf last-revert-index {
                                    type uint32 {
                                        range "0..199";
                                    }
                                    description "The last rollback checkpoint file reverted on the system.";
                                }

                                ///nokia-state/state/system/management-interface/cli/classic-cli/rollback/revert/last-revert-checkpoint-file
                                leaf last-revert-checkpoint-file {
                                    type types-sros:url;
                                    description "The filepath or file-URL of the last reverted rollback file.";
                                }

                                ///nokia-state/state/system/management-interface/cli/classic-cli/rollback/revert/revert-in-progress
                                leaf revert-in-progress {
                                    type boolean;
                                    description "Indicates if a rollback revert is currently in progress.";
                                }

                                ///nokia-state/state/system/management-interface/cli/classic-cli/rollback/revert/last-revert-initiated-user
                                leaf last-revert-initiated-user {
                                    type types-sros:named-item-or-empty;
                                    description "The name of a system user who initiated the last rollback rescue revert.";
                                }

                                ///nokia-state/state/system/management-interface/cli/classic-cli/rollback/revert/last-revert-result
                                leaf last-revert-result {
                                    type types-system:action-result-with-interrupted;
                                    description "The result of the last rollback start action.";
                                }

                                ///nokia-state/state/system/management-interface/cli/classic-cli/rollback/revert/last-revert-initiated-time
                                leaf last-revert-initiated-time {
                                    type yang:date-and-time;
                                    description
                                        "The time when the last rescue rollback file revert
                                         on the system was initiated.";
                                }

                                ///nokia-state/state/system/management-interface/cli/classic-cli/rollback/revert/last-revert-completion-time
                                leaf last-revert-completion-time {
                                    type yang:date-and-time;
                                    description
                                        "The time when the last rescue rollback file revert
                                         was completed on the system.";
                                }

                            } // container revert

                            ///nokia-state/state/system/management-interface/cli/classic-cli/rollback/delete
                            container delete {
                                description "Enter the delete context";

                                ///nokia-state/state/system/management-interface/cli/classic-cli/rollback/delete/last-delete-result
                                leaf last-delete-result {
                                    type types-system:action-result;
                                    description "The result of the last rollback file delete action.";
                                }

                            } // container delete

                            ///nokia-state/state/system/management-interface/cli/classic-cli/rollback/rescue
                            container rescue {
                                description "Enter the rescue context";

                                ///nokia-state/state/system/management-interface/cli/classic-cli/rollback/rescue/rescue-file-saved
                                leaf rescue-file-saved {
                                    type boolean;
                                    description
                                        "Indicates whether a rollback rescue file specified by rescue location
                                         and suffix '.rc' is present.";
                                }

                                ///nokia-state/state/system/management-interface/cli/classic-cli/rollback/rescue/save
                                container save {
                                    description "Enter the save context";

                                    ///nokia-state/state/system/management-interface/cli/classic-cli/rollback/rescue/save/last-save-result
                                    leaf last-save-result {
                                        type types-system:action-result;
                                        description "The result of the last rollback save action.";
                                    }

                                    ///nokia-state/state/system/management-interface/cli/classic-cli/rollback/rescue/save/last-save-completion-time
                                    leaf last-save-completion-time {
                                        type yang:date-and-time;
                                        description
                                            "The time when the last rollback save was
                                             completed on the system.";
                                    }

                                } // container save

                                ///nokia-state/state/system/management-interface/cli/classic-cli/rollback/rescue/revert
                                container revert {
                                    description "Enter the revert context";

                                    ///nokia-state/state/system/management-interface/cli/classic-cli/rollback/rescue/revert/rescue-in-progress
                                    leaf rescue-in-progress {
                                        type boolean;
                                        description "Indicates if a rollback rescue revert is currently in progress.";
                                    }

                                    ///nokia-state/state/system/management-interface/cli/classic-cli/rollback/rescue/revert/last-revert-initiated-user
                                    leaf last-revert-initiated-user {
                                        type types-sros:named-item-or-empty;
                                        description "The name of a system user who initiated the last rollback rescue revert.";
                                    }

                                    ///nokia-state/state/system/management-interface/cli/classic-cli/rollback/rescue/revert/last-revert-result
                                    leaf last-revert-result {
                                        type types-system:action-result-with-interrupted;
                                        description "The result of the last rollback start action.";
                                    }

                                    ///nokia-state/state/system/management-interface/cli/classic-cli/rollback/rescue/revert/last-revert-initiated-time
                                    leaf last-revert-initiated-time {
                                        type yang:date-and-time;
                                        description
                                            "The time when the last rescue rollback file revert
                                             on the system was initiated.";
                                    }

                                    ///nokia-state/state/system/management-interface/cli/classic-cli/rollback/rescue/revert/last-revert-completion-time
                                    leaf last-revert-completion-time {
                                        type yang:date-and-time;
                                        description
                                            "The time when the last rescue rollback file revert
                                             was completed on the system.";
                                    }

                                } // container revert

                                ///nokia-state/state/system/management-interface/cli/classic-cli/rollback/rescue/delete
                                container delete {
                                    description "Enter the delete context";

                                    ///nokia-state/state/system/management-interface/cli/classic-cli/rollback/rescue/delete/last-delete-result
                                    leaf last-delete-result {
                                        type types-system:action-result;
                                        description "The result of the last rollback file delete action.";
                                    }

                                } // container delete

                            } // container rescue

                            ///nokia-state/state/system/management-interface/cli/classic-cli/rollback/rollback-file
                            list rollback-file {
                                key "checkpoint-index";
                                description "Enter the rollback-file list instance";

                                ///nokia-state/state/system/management-interface/cli/classic-cli/rollback/rollback-file/checkpoint-index
                                leaf checkpoint-index {
                                    type uint32 {
                                        range "0..199";
                                    }
                                    description "Specifies the index of the rollback checkpoint file.";
                                }

                                ///nokia-state/state/system/management-interface/cli/classic-cli/rollback/rollback-file/suffix
                                leaf suffix {
                                    type types-sros:named-item;
                                    description "Specifies the suffix of the rollback checkpoint file.";
                                }

                                ///nokia-state/state/system/management-interface/cli/classic-cli/rollback/rollback-file/creation-time
                                leaf creation-time {
                                    type yang:date-and-time;
                                    description "Indicates the timestamp of the creation time.";
                                }

                                ///nokia-state/state/system/management-interface/cli/classic-cli/rollback/rollback-file/release
                                leaf release {
                                    type types-sros:named-item;
                                    description
                                        "Indicates the version number of the software running on the
                                         system when the rollback file is saved.";
                                }

                                ///nokia-state/state/system/management-interface/cli/classic-cli/rollback/rollback-file/user
                                leaf user {
                                    type types-sros:named-item;
                                    description "Indicates the name of a system user who saved this rollback file.";
                                }

                                ///nokia-state/state/system/management-interface/cli/classic-cli/rollback/rollback-file/comment
                                leaf comment {
                                    type types-sros:display-string;
                                    description "Specifies a user provided comment related to a rollback checkpoint file.";
                                }

                            } // list rollback-file

                        } // container rollback

                    } // container classic-cli

                } // container cli

                ///nokia-state/state/system/management-interface/netconf
                container netconf {
                    description "Enter the netconf context";

                    ///nokia-state/state/system/management-interface/netconf/oper-state
                    leaf oper-state {
                        type types-sros:oper-state;
                        description "operational state";
                    }

                    ///nokia-state/state/system/management-interface/netconf/statistics
                    container statistics {
                        description "Enter the statistics context";

                        ///nokia-state/state/system/management-interface/netconf/statistics/requests
                        leaf requests {
                            type yang:counter32;
                            description
                                "total number of NETCONF requests which have been accepted and processed by the NETCONF
                                 server.";
                        }

                        ///nokia-state/state/system/management-interface/netconf/statistics/get-requests
                        leaf get-requests {
                            type yang:counter32;
                            description
                                "total number of get NETCONF requests which have been accepted and processed by the
                                 NETCONF server.";
                        }

                        ///nokia-state/state/system/management-interface/netconf/statistics/get-config-requests
                        leaf get-config-requests {
                            type yang:counter32;
                            description
                                "total number of get-config NETCONF requests which have been accepted and
                                 processed by the NETCONF server.";
                        }

                        ///nokia-state/state/system/management-interface/netconf/statistics/edit-config-requests
                        leaf edit-config-requests {
                            type yang:counter32;
                            description
                                "total number of edit-config NETCONF requests which have been accepted and
                                 processed by the NETCONF server.";
                        }

                        ///nokia-state/state/system/management-interface/netconf/statistics/close-requests
                        leaf close-requests {
                            type yang:counter32;
                            description
                                "total number of close-session NETCONF requests which have been accepted and processed
                                 by the NETCONF server.";
                        }

                        ///nokia-state/state/system/management-interface/netconf/statistics/kill-requests
                        leaf kill-requests {
                            type yang:counter32;
                            description
                                "total number of kill-session NETCONF requests which have been accepted and processed
                                 by the NETCONF server.";
                        }

                        ///nokia-state/state/system/management-interface/netconf/statistics/responses
                        leaf responses {
                            type yang:counter32;
                            description
                                "total number of NETCONF responses which have been generated and sent by the NETCONF
                                 server.";
                        }

                        ///nokia-state/state/system/management-interface/netconf/statistics/error-responses
                        leaf error-responses {
                            type yang:counter32;
                            description
                                "total number of NETCONF error responses which have been generated and sent by the
                                 NETCONF server.";
                        }

                        ///nokia-state/state/system/management-interface/netconf/statistics/copy-config-requests
                        leaf copy-config-requests {
                            type yang:counter32;
                            description
                                "total number of copy-config NETCONF requests which have been accepted and
                                 processed by the NETCONF server.";
                        }

                        ///nokia-state/state/system/management-interface/netconf/statistics/del-config-requests
                        leaf del-config-requests {
                            type yang:counter32;
                            description
                                "total number of delete-config NETCONF requests which have been accepted and
                                 processed by the NETCONF server.";
                        }

                        ///nokia-state/state/system/management-interface/netconf/statistics/validate-requests
                        leaf validate-requests {
                            type yang:counter32;
                            description
                                "total number of validate NETCONF requests which have been accepted and
                                 processed by the NETCONF server.";
                        }

                        ///nokia-state/state/system/management-interface/netconf/statistics/failed-edit-cfg-reqs
                        leaf failed-edit-cfg-reqs {
                            type yang:counter32;
                            description
                                "total number of edit-config NETCONF requests which have failed because of
                                 locks taken by other NETCONF sessions.";
                        }

                        ///nokia-state/state/system/management-interface/netconf/statistics/failed-lock-reqs
                        leaf failed-lock-reqs {
                            type yang:counter32;
                            description
                                "total number of lock NETCONF requests which have failed because of
                                 locks taken by other NETCONF sessions.";
                        }

                        ///nokia-state/state/system/management-interface/netconf/statistics/lock-requests
                        leaf lock-requests {
                            type yang:counter32;
                            description
                                "total number of lock NETCONF requests which have been accepted and
                                 processed by the NETCONF server.";
                        }

                        ///nokia-state/state/system/management-interface/netconf/statistics/unlock-requests
                        leaf unlock-requests {
                            type yang:counter32;
                            description
                                "total number of unlock NETCONF requests which have been accepted
                                 and processed by the NETCONF server.";
                        }

                        ///nokia-state/state/system/management-interface/netconf/statistics/commit-requests
                        leaf commit-requests {
                            type yang:counter32;
                            description
                                "total number of commit NETCONF requests which have been accepted
                                 and processed by the NETCONF server.";
                        }

                        ///nokia-state/state/system/management-interface/netconf/statistics/discard-requests
                        leaf discard-requests {
                            type yang:counter32;
                            description
                                "total number of discard change NETCONF requests which have been accepted
                                 and processed by the NETCONF server.";
                        }

                        ///nokia-state/state/system/management-interface/netconf/statistics/create-subscription-requests
                        leaf create-subscription-requests {
                            type yang:counter32;
                            description
                                "total number of create subscription NETCONF requests which have been accepted
                                 and processed by the NETCONF server.";
                        }

                        ///nokia-state/state/system/management-interface/netconf/statistics/get-schema-requests
                        leaf get-schema-requests {
                            type yang:counter32;
                            description
                                "total number of get-schema NETCONF requests which have been accepted
                                 and processed by the NETCONF server.";
                        }

                        ///nokia-state/state/system/management-interface/netconf/statistics/get-data-requests
                        leaf get-data-requests {
                            type yang:counter32;
                            description
                                "total number of get-data NETCONF requests which have been accepted
                                 and processed by the NETCONF server.";
                        }

                        ///nokia-state/state/system/management-interface/netconf/statistics/action-requests
                        leaf action-requests {
                            type yang:counter32;
                            description
                                "total number of action NETCONF requests which have been accepted
                                 and processed by the NETCONF server.";
                        }

                        ///nokia-state/state/system/management-interface/netconf/statistics/in-bad-hellos
                        leaf in-bad-hellos {
                            type yang:counter32;
                            description "total number of bad NETCONF hello messages which have been received by the NETCONF server.";
                        }

                        ///nokia-state/state/system/management-interface/netconf/statistics/dropped-sessions
                        leaf dropped-sessions {
                            type yang:counter32;
                            description "total number of dropped NETCONF sessions.";
                        }

                        ///nokia-state/state/system/management-interface/netconf/statistics/last-oper-change
                        leaf last-oper-change {
                            type types-sros:date-time;
                            description "time of last change of operational state of NETCONF server.";
                        }

                    } // container statistics

                    ///nokia-state/state/system/management-interface/netconf/notifications
                    container notifications {
                        description "Enter the notifications context";

                        ///nokia-state/state/system/management-interface/netconf/notifications/subscription
                        list subscription {
                            key "session-id";
                            description "Enter the subscription list instance";

                            ///nokia-state/state/system/management-interface/netconf/notifications/subscription/session-id
                            leaf session-id {
                                type uint32;
                                description "The id of the NETCONF session.";
                            }

                            ///nokia-state/state/system/management-interface/netconf/notifications/subscription/stream
                            leaf stream {
                                type string;
                                description "The name of the event stream the session is subscribed to.";
                            }

                            ///nokia-state/state/system/management-interface/netconf/notifications/subscription/connection-ip
                            leaf connection-ip {
                                type types-sros:ip-address;
                                description "Connection ip address.";
                            }

                            ///nokia-state/state/system/management-interface/netconf/notifications/subscription/user
                            leaf user {
                                type types-sros:named-item;
                                description "Name of the user.";
                            }

                        } // list subscription

                    } // container notifications

                } // container netconf

                ///nokia-state/state/system/management-interface/operations
                container operations {
                    description "Enable the operations context";

                    ///nokia-state/state/system/management-interface/operations/oldest-operation-id
                    leaf oldest-operation-id {
                        type types-operation:operation-id;
                        description "Oldest ID assigned to operation currently tracked in the system.";
                    }

                    ///nokia-state/state/system/management-interface/operations/newest-operation-id
                    leaf newest-operation-id {
                        type types-operation:operation-id;
                        description "Most recently assigned operation ID.";
                    }

                    ///nokia-state/state/system/management-interface/operations/operation
                    list operation {
                        key "operation-id";
                        description "Enter the operation list instance";

                        ///nokia-state/state/system/management-interface/operations/operation/operation-id
                        leaf operation-id {
                            type types-operation:operation-id;
                            description "ID assigned to the operation.";
                        }

                        ///nokia-state/state/system/management-interface/operations/operation/asynchronous
                        leaf asynchronous {
                            type types-operation:operation-asynchronous;
                            description "Indicates whether the operation execution happened asynchronously or synchronously.";
                        }

                        ///nokia-state/state/system/management-interface/operations/operation/status
                        leaf status {
                            type types-operation:operation-status;
                            description "Status of operation's execution.";
                        }

                        ///nokia-state/state/system/management-interface/operations/operation/secondary-status
                        leaf secondary-status {
                            type enumeration {
                                enum terminating                    { value 0; }
                            }
                            description "Describes short-lasting operation status transitions.";
                        }

                        ///nokia-state/state/system/management-interface/operations/operation/error-message
                        leaf-list error-message {
                            type types-operation:operation-message;
                            description "Error messages reported during execution of the operation.";
                        }

                        ///nokia-state/state/system/management-interface/operations/operation/warning-message
                        leaf-list warning-message {
                            type types-operation:operation-message;
                            description "Warning messages reported during execution of the operation.";
                        }

                        ///nokia-state/state/system/management-interface/operations/operation/info-message
                        leaf-list info-message {
                            type types-operation:operation-message;
                            description "Info messages reported during execution of the operation.";
                        }

                        ///nokia-state/state/system/management-interface/operations/operation/start-time
                        leaf start-time {
                            type types-operation:operation-timestamp;
                            description "Time when the operation started its execution.";
                        }

                        ///nokia-state/state/system/management-interface/operations/operation/end-time
                        leaf end-time {
                            type types-operation:operation-timestamp;
                            description "Time when the operation ended its execution.";
                        }

                        ///nokia-state/state/system/management-interface/operations/operation/request-path
                        leaf request-path {
                            type types-operation:operation-path;
                            description "Path identifying the operation in xpath format.";
                        }

                        ///nokia-state/state/system/management-interface/operations/operation/results-path
                        leaf results-path {
                            type types-operation:operation-path;
                            description "Path where the operation's results are stored in xpath format.";
                        }

                        ///nokia-state/state/system/management-interface/operations/operation/session-id
                        leaf session-id {
                            type uint32;
                            description "ID of the session that initiated the operation.";
                        }

                        ///nokia-state/state/system/management-interface/operations/operation/user
                        leaf user {
                            type string;
                            description "Name of the user who initiated the operation.";
                        }

                        ///nokia-state/state/system/management-interface/operations/operation/execution-timeout
                        container execution-timeout {
                            description "Enter the execution-timeout context";

                            ///nokia-state/state/system/management-interface/operations/operation/execution-timeout/time
                            leaf time {
                                type yang:date-and-time;
                                description "Time when the operation's execution will timeout and be stopped.";
                            }

                            ///nokia-state/state/system/management-interface/operations/operation/execution-timeout/remaining
                            leaf remaining {
                                type uint32;
                                units "seconds";
                                description "Time remaining until operation's execution timeout.";
                            }

                        } // container execution-timeout

                        ///nokia-state/state/system/management-interface/operations/operation/retention-timeout
                        container retention-timeout {
                            description "Enter the retention-timeout context";

                            ///nokia-state/state/system/management-interface/operations/operation/retention-timeout/time
                            leaf time {
                                type yang:date-and-time;
                                description "Time when the operation's data will be erased from the system.";
                            }

                            ///nokia-state/state/system/management-interface/operations/operation/retention-timeout/remaining
                            leaf remaining {
                                type uint32;
                                units "seconds";
                                description "Time remaining until operation's retention timeout.";
                            }

                        } // container retention-timeout

                    } // list operation

                    ///nokia-state/state/system/management-interface/operations/next-execution-timeout
                    container next-execution-timeout {
                        description "Enter the next-execution-timeout context";

                        ///nokia-state/state/system/management-interface/operations/next-execution-timeout/operation-id
                        leaf operation-id {
                            type types-operation:operation-id;
                            description "ID assigned to the operation to expire execution timer next.";
                        }

                        ///nokia-state/state/system/management-interface/operations/next-execution-timeout/time
                        leaf time {
                            type yang:date-and-time;
                            description "Time when the operation's execution will timeout and be stopped.";
                        }

                        ///nokia-state/state/system/management-interface/operations/next-execution-timeout/remaining
                        leaf remaining {
                            type uint32;
                            units "seconds";
                            description "Time remaining until operation's execution timeout.";
                        }

                    } // container next-execution-timeout

                    ///nokia-state/state/system/management-interface/operations/next-retention-timeout
                    container next-retention-timeout {
                        description "Enter the next-retention-timeout context";

                        ///nokia-state/state/system/management-interface/operations/next-retention-timeout/operation-id
                        leaf operation-id {
                            type types-operation:operation-id;
                            description "ID assigned to the operation to expire retention timer next.";
                        }

                        ///nokia-state/state/system/management-interface/operations/next-retention-timeout/time
                        leaf time {
                            type yang:date-and-time;
                            description "Time when the operation's data will be erased from the system.";
                        }

                        ///nokia-state/state/system/management-interface/operations/next-retention-timeout/remaining
                        leaf remaining {
                            type uint32;
                            units "seconds";
                            description "Time when the operation's data will be erased from the system.";
                        }

                    } // container next-retention-timeout

                } // container operations

                ///nokia-state/state/system/management-interface/remote-management
                container remote-management {
                    description "Enter the remote-management context";

                    ///nokia-state/state/system/management-interface/remote-management/last-registration-status
                    leaf last-registration-status {
                        type types-system:remote-mgmt-registration-status;
                        description "Last result of registration attempt.";
                    }

                    ///nokia-state/state/system/management-interface/remote-management/last-registration-time
                    leaf last-registration-time {
                        type types-sros:date-time;
                        description "Last time the client tried to register.";
                    }

                    ///nokia-state/state/system/management-interface/remote-management/oper-state
                    leaf oper-state {
                        type types-sros:oper-state;
                        description "Administrative state of registration.";
                    }

                    ///nokia-state/state/system/management-interface/remote-management/oper-down-reason
                    leaf oper-down-reason {
                        type enumeration {
                            enum unknown                        { value 0; }
                            enum admin-down                     { value 1; }
                            enum no-manager                     { value 2; }
                        }
                    }

                    ///nokia-state/state/system/management-interface/remote-management/last-hello-time
                    leaf last-hello-time {
                        type types-sros:date-time;
                        description "Last time the remote-management client tried to register.";
                    }

                    ///nokia-state/state/system/management-interface/remote-management/statistics
                    container statistics {
                        description "Enter the statistics context";

                        ///nokia-state/state/system/management-interface/remote-management/statistics/sent-registrations
                        leaf sent-registrations {
                            type yang:counter64;
                            description "The number of registrations sent.";
                        }

                        ///nokia-state/state/system/management-interface/remote-management/statistics/failed-registrations
                        leaf failed-registrations {
                            type yang:counter64;
                            description "The number of registrations failed.";
                        }

                        ///nokia-state/state/system/management-interface/remote-management/statistics/cancelled-registrations
                        leaf cancelled-registrations {
                            type yang:counter64;
                            description "The number of registrations cancelled.";
                        }

                    } // container statistics

                    ///nokia-state/state/system/management-interface/remote-management/manager
                    list manager {
                        key "manager-name";
                        description "Enter the manager list instance";

                        ///nokia-state/state/system/management-interface/remote-management/manager/manager-name
                        leaf manager-name {
                            type types-sros:named-item-64;
                            description "Remote management manager name";
                        }

                        ///nokia-state/state/system/management-interface/remote-management/manager/last-registration-status
                        leaf last-registration-status {
                            type types-system:remote-mgmt-registration-status;
                            description "Last result of registration attempt.";
                        }

                        ///nokia-state/state/system/management-interface/remote-management/manager/last-registration-time
                        leaf last-registration-time {
                            type types-sros:date-time;
                            description "Last time the client tried to register.";
                        }

                        ///nokia-state/state/system/management-interface/remote-management/manager/oper-state
                        leaf oper-state {
                            type types-sros:oper-state;
                            description "Administrative state of registration.";
                        }

                        ///nokia-state/state/system/management-interface/remote-management/manager/oper-down-reason
                        leaf oper-down-reason {
                            type enumeration {
                                enum unknown                        { value 0; }
                                enum admin-down                     { value 1; }
                                enum no-transport-type              { value 2; }
                                enum no-source-address              { value 3; }
                                enum invalid-manager-address        { value 4; }
                                enum registration-failed            { value 5; }
                            }
                        }

                        ///nokia-state/state/system/management-interface/remote-management/manager/oper-client-tls-profile
                        leaf oper-client-tls-profile {
                            type types-sros:named-item-64;
                            description "Operational TLS client profile.";
                        }

                        ///nokia-state/state/system/management-interface/remote-management/manager/oper-transport-type
                        leaf oper-transport-type {
                            type enumeration {
                                enum tls                            { value 1; }
                                enum unsecured                      { value 2; }
                            }
                            description "Operational transport method.";
                        }

                        ///nokia-state/state/system/management-interface/remote-management/manager/oper-connection-timeout
                        leaf oper-connection-timeout {
                            type uint32;
                            units "seconds";
                            description "Operational manager response timeout.";
                        }

                        ///nokia-state/state/system/management-interface/remote-management/manager/oper-router-instance
                        leaf oper-router-instance {
                            type types-sros:router-instance-base-management-vprn-loose;
                            description "router-instance used to connect to the manager";
                        }

                        ///nokia-state/state/system/management-interface/remote-management/manager/oper-device-name
                        leaf oper-device-name {
                            type types-sros:named-item-64;
                            description "Identifier of this device.";
                        }

                        ///nokia-state/state/system/management-interface/remote-management/manager/oper-device-label
                        leaf oper-device-label {
                            type types-sros:named-item-64;
                            description "Label of this device.";
                        }

                        ///nokia-state/state/system/management-interface/remote-management/manager/oper-source-address
                        leaf oper-source-address {
                            type types-sros:ip-address;
                            description "Source IP address used to provide access to management of this device.";
                        }

                        ///nokia-state/state/system/management-interface/remote-management/manager/oper-source-port
                        leaf oper-source-port {
                            type types-sros:tcp-udp-port;
                            description "Source TCP port used to provide access to management of this device.";
                        }

                        ///nokia-state/state/system/management-interface/remote-management/manager/statistics
                        container statistics {
                            description "Enter the statistics context";

                            ///nokia-state/state/system/management-interface/remote-management/manager/statistics/sent-registrations
                            leaf sent-registrations {
                                type yang:counter64;
                                description "The number of registrations sent.";
                            }

                            ///nokia-state/state/system/management-interface/remote-management/manager/statistics/failed-registrations
                            leaf failed-registrations {
                                type yang:counter64;
                                description "The number of registrations failed.";
                            }

                            ///nokia-state/state/system/management-interface/remote-management/manager/statistics/cancelled-registrations
                            leaf cancelled-registrations {
                                type yang:counter64;
                                description "The number of registrations cancelled.";
                            }

                        } // container statistics

                    } // list manager

                } // container remote-management

                ///nokia-state/state/system/management-interface/active-sessions
                list active-sessions {
                    key "session-id";
                    description "Enter the active-sessions list instance";

                    ///nokia-state/state/system/management-interface/active-sessions/session-id
                    leaf session-id {
                        type types-system:user-session-id;
                        description
                            "Represents unique session identifier.
                             The value is auto-generated by the system.";
                    }

                    ///nokia-state/state/system/management-interface/active-sessions/username
                    leaf username {
                        type types-sros:named-item;
                        description "The name of the user who initiated session.";
                    }

                    ///nokia-state/state/system/management-interface/active-sessions/from
                    leaf from {
                        type union {
                            type types-sros:ip-address;
                            type enumeration {
                                enum none                           { value -1; }
                                enum console                        { value 1; }
                                enum cron-ehs                       { value 2; }
                            }
                        }
                        description
                            "Indicates the session origin. Source IP address
                             is returned for non-console sessions.";
                    }

                    ///nokia-state/state/system/management-interface/active-sessions/session-type
                    leaf session-type {
                        type enumeration {
                            enum classic-cli                    { value 1; }
                            enum grpc                           { value 2; }
                            enum md-cli                         { value 3; }
                            enum netconf                        { value 4; }
                            enum snmp                           { value 5; }
                            enum system                         { value 6; }
                        }
                        description "Identifies the management interface used to initiate the session.";
                    }

                    ///nokia-state/state/system/management-interface/active-sessions/session-mode
                    leaf session-mode {
                        type enumeration {
                            enum global                         { value 1; }
                            enum exclusive                      { value 2; }
                            enum private                        { value 3; }
                            enum private-exclusive              { value 4; }
                            enum read-only                      { value 5; }
                        }
                        description
                            "Indicates the candidate configuration mode.

                             Multiple global sessions are allowed to make configuration
                             changes at the same time. If a global session is taken,
                             exclusive mode is unavailable.

                             Exclusive mode blocks any other session from making
                             configuration changes.";
                    }

                    ///nokia-state/state/system/management-interface/active-sessions/idle-time
                    leaf idle-time {
                        type types-sros:time-duration;
                        units "seconds";
                        description
                            "Indicates the session's idle time.

                             For CLI sessions, the idle time is the period of time
                             after the last key press. For NETCONF, it is the period of time
                             since session creation. Idle time is not tracked for gRPC sessions.";
                    }

                    ///nokia-state/state/system/management-interface/active-sessions/scratchpad-count
                    leaf scratchpad-count {
                        type uint32;
                        description "Number of scratchpads in use for session";
                    }

                    ///nokia-state/state/system/management-interface/active-sessions/locked-datastores
                    list locked-datastores {
                        key "region-name datastore-name";
                        description "Enter the locked-datastores list instance";

                        ///nokia-state/state/system/management-interface/active-sessions/locked-datastores/region-name
                        leaf region-name {
                            type types-sros:configuration-region;
                            description "The name of region locked within the command tree.";
                        }

                        ///nokia-state/state/system/management-interface/active-sessions/locked-datastores/datastore-name
                        leaf datastore-name {
                            type types-sros:datastore-name;
                            description "The name of the locked datastore.";
                        }

                    } // list locked-datastores

                } // list active-sessions

                ///nokia-state/state/system/management-interface/snmp
                container snmp {
                    description "Enable the snmp context";

                    ///nokia-state/state/system/management-interface/snmp/engine-boots
                    leaf engine-boots {
                        type uint32;
                        description
                            "The number of times the SNMP engine has re-booted/re-initialized
                             since the SNMP Engine ID was last configured.";
                    }

                    ///nokia-state/state/system/management-interface/snmp/oper-state
                    leaf oper-state {
                        type types-sros:oper-state;
                        description
                            "When oper-state a value of 'in-service', the SNMP daemon
                             will receive SNMP requests from external SNMP managers.
                             When oper-state has a value of 'out-of-service', the SNMP
                             daemon is suspended and will not receive SNMP requests
                             from external SNMP managers.";
                    }

                    ///nokia-state/state/system/management-interface/snmp/statistics
                    container statistics {
                        description "Enter the statistics context";

                        ///nokia-state/state/system/management-interface/snmp/statistics/in-packets
                        leaf in-packets {
                            type yang:zero-based-counter32;
                            description
                                "indicates the total number of messages delivered to the SNMP
                                 entity from the transport service.";
                        }

                        ///nokia-state/state/system/management-interface/snmp/statistics/in-gets
                        leaf in-gets {
                            type yang:zero-based-counter32;
                            description
                                "indicates the total number of SNMP Get-Request PDUs which have
                                 been accepted and processed by the SNMP protocol entity.";
                        }

                        ///nokia-state/state/system/management-interface/snmp/statistics/in-getnexts
                        leaf in-getnexts {
                            type yang:zero-based-counter32;
                            description
                                "indicates the total number of SNMP Get-Next PDUs which have
                                 been accepted and processed by the SNMP protocol entity.";
                        }

                        ///nokia-state/state/system/management-interface/snmp/statistics/in-getbulks
                        leaf in-getbulks {
                            type yang:zero-based-counter32;
                            description
                                "indicates the total number of SNMP Get-Next PDUs which have
                                 been accepted and processed by the SNMP protocol entity.";
                        }

                        ///nokia-state/state/system/management-interface/snmp/statistics/in-sets
                        leaf in-sets {
                            type yang:zero-based-counter32;
                            description
                                "indicates the total number of SNMP Set-Request PDUs which have
                                 been accepted and processed by the SNMP protocol entity.";
                        }

                        ///nokia-state/state/system/management-interface/snmp/statistics/out-packets
                        leaf out-packets {
                            type yang:zero-based-counter32;
                            description
                                "indicates the total number of SNMP Messages which were passed
                                 from the SNMP protocol entity to the transport service.";
                        }

                        ///nokia-state/state/system/management-interface/snmp/statistics/out-get-responses
                        leaf out-get-responses {
                            type yang:zero-based-counter32;
                            description
                                "indicates the total number of SNMP Get-Response PDUs which have
                                 been generated by the SNMP protocol entity.";
                        }

                        ///nokia-state/state/system/management-interface/snmp/statistics/out-traps
                        leaf out-traps {
                            type yang:zero-based-counter32;
                            description
                                "indicates the total number of SNMP Trap PDUs which have been
                                 generated by the SNMP protocol entity.";
                        }

                        ///nokia-state/state/system/management-interface/snmp/statistics/variables-requested
                        leaf variables-requested {
                            type yang:zero-based-counter32;
                            description
                                "indicates the total number of MIB objects which have been
                                 retrieved successfully by the SNMP protocol entity as the result
                                 of receiving valid SNMP Get-Request and Get-Next PDUs.";
                        }

                        ///nokia-state/state/system/management-interface/snmp/statistics/variables-sets
                        leaf variables-sets {
                            type yang:zero-based-counter32;
                            description
                                "indicates the total number of MIB objects which have been altered
                                 successfully by the SNMP protocol entity as the result of receiving
                                 valid SNMP Set-Request PDUs.";
                        }

                        ///nokia-state/state/system/management-interface/snmp/statistics/failed-sets
                        leaf failed-sets {
                            type yang:zero-based-counter32;
                            description
                                "indicates the total number of SNMP set requests which have failed
                                 due to another management interface (such as NETCONF) exclusively
                                 reserving the system resources.";
                        }

                    } // container statistics

                    ///nokia-state/state/system/management-interface/snmp/streaming
                    container streaming {
                        description "Enable the streaming context";

                        ///nokia-state/state/system/management-interface/snmp/streaming/dump-table-requests
                        leaf dump-table-requests {
                            type yang:zero-based-counter32;
                            description
                                "indicates the total number of streaming snmp dump request PDUs
                                 which have been accepted and processed by the Nokia 5620 Service
                                 Aware Manager (SAM) streaming protocol.";
                        }

                        ///nokia-state/state/system/management-interface/snmp/streaming/get-many-requests
                        leaf get-many-requests {
                            type yang:zero-based-counter32;
                            description
                                "indicates the total number of streaming get many request PDUs
                                 which have been accepted and processed by the Nokia 5620 Service
                                 Aware Manager (SAM) streaming protocol entity.";
                        }

                        ///nokia-state/state/system/management-interface/snmp/streaming/responses
                        leaf responses {
                            type yang:zero-based-counter32;
                            description
                                "indicates the total number of streaming response PDUs which
                                 have been generated by the Nokia 5620 Service Aware Manager
                                 (SAM) streaming protocol entity.";
                        }

                    } // container streaming

                } // container snmp

                ///nokia-state/state/system/management-interface/configuration-region
                list configuration-region {
                    key "region-name";
                    description "Enter the configuration-region list instance";

                    ///nokia-state/state/system/management-interface/configuration-region/region-name
                    leaf region-name {
                        type types-sros:configuration-region;
                        description "The name of the datastore.";
                    }

                    ///nokia-state/state/system/management-interface/configuration-region/config-save
                    container config-save {
                        description "Enter the config-save context";

                        ///nokia-state/state/system/management-interface/configuration-region/config-save/last-saved-config
                        leaf last-saved-config {
                            type types-sros:display-string;
                            description
                                "The location and name of the file to which the configuration
                                 was last saved.";
                        }

                        ///nokia-state/state/system/management-interface/configuration-region/config-save/last-saved-time
                        leaf last-saved-time {
                            type yang:date-and-time;
                            description "The date and time when the current configuration was last saved.";
                        }

                    } // container config-save

                    ///nokia-state/state/system/management-interface/configuration-region/datastore
                    list datastore {
                        key "ds-name";
                        description "Enter the datastore list instance";

                        ///nokia-state/state/system/management-interface/configuration-region/datastore/ds-name
                        leaf ds-name {
                            type types-sros:datastore-name;
                            description "The name of the datastore.";
                        }

                        ///nokia-state/state/system/management-interface/configuration-region/datastore/changes-since-last-save
                        leaf changes-since-last-save {
                            type boolean;
                            description "Indicates if the configuration was changed since the last save.";
                        }

                        ///nokia-state/state/system/management-interface/configuration-region/datastore/user-last-modified
                        leaf user-last-modified {
                            type string {
                                length "1..65";
                            }
                            description "The last user who modified the configuration.";
                        }

                        ///nokia-state/state/system/management-interface/configuration-region/datastore/time-last-modified
                        leaf time-last-modified {
                            type yang:date-and-time;
                            description "The date and time when the running configuration was last modified.";
                        }

                        ///nokia-state/state/system/management-interface/configuration-region/datastore/locked
                        leaf locked {
                            type boolean;
                            description
                                "Indicates if lock to the datastore is held by any session.

                                 The datastore is considered as locked if exclusive session is held
                                 by any user or NETCONF lock RPC was used on the datastore.";
                        }

                    } // list datastore

                    ///nokia-state/state/system/management-interface/configuration-region/commit-history
                    container commit-history {
                        description "Enter the commit-history context";

                        ///nokia-state/state/system/management-interface/configuration-region/commit-history/commit-id
                        list commit-id {
                            key "id";
                            description "Enter the commit-id list instance";

                            ///nokia-state/state/system/management-interface/configuration-region/commit-history/commit-id/id
                            leaf id {
                                type uint32 {
                                    range "1..max";
                                }
                                description "Record ID in the commit history";
                            }

                            ///nokia-state/state/system/management-interface/configuration-region/commit-history/commit-id/timestamp
                            leaf timestamp {
                                type yang:date-and-time;
                            }

                            ///nokia-state/state/system/management-interface/configuration-region/commit-history/commit-id/user
                            leaf user {
                                type types-sros:named-item;
                                description "The name of the user who initiated commit.";
                            }

                            ///nokia-state/state/system/management-interface/configuration-region/commit-history/commit-id/type
                            leaf type {
                                type enumeration {
                                    enum md-cli                         { value 0; }
                                    enum netconf                        { value 1; }
                                    enum grpc                           { value 2; }
                                    enum system                         { value 3; }
                                    enum database-initialization        { value 4; }
                                    enum issu                           { value 5; }
                                    enum cron-ehs                       { value 6; }
                                }
                            }

                            ///nokia-state/state/system/management-interface/configuration-region/commit-history/commit-id/from
                            leaf from {
                                type union {
                                    type types-sros:ip-address;
                                    type enumeration {
                                        enum console                        { value 1; }
                                        enum cron-ehs                       { value 2; }
                                    }
                                }
                                description
                                    "Indicates the commit origin. Source IP address
                                     is returned for non-console sessions.";
                            }

                            ///nokia-state/state/system/management-interface/configuration-region/commit-history/commit-id/location
                            leaf location {
                                type types-sros:cflash-and-url;
                            }

                            ///nokia-state/state/system/management-interface/configuration-region/commit-history/commit-id/increment-location
                            leaf increment-location {
                                type types-sros:cflash-and-url;
                            }

                            ///nokia-state/state/system/management-interface/configuration-region/commit-history/commit-id/comment
                            leaf comment {
                                type string {
                                    length "1..2048";
                                }
                            }

                            ///nokia-state/state/system/management-interface/configuration-region/commit-history/commit-id/log
                            leaf log {
                                type string {
                                    length "1..512";
                                }
                            }

                        } // list commit-id

                    } // container commit-history

                } // list configuration-region

            } // container management-interface

            ///nokia-state/state/system/thresholds
            container thresholds {
                description "Enter the thresholds context";

                ///nokia-state/state/system/thresholds/cflash-cap-alarm-percent
                list cflash-cap-alarm-percent {
                    key "cflash-id";
                    description "Enter the cflash-cap-alarm-percent list instance";

                    ///nokia-state/state/system/thresholds/cflash-cap-alarm-percent/cflash-id
                    leaf cflash-id {
                        type types-sros:thresholds-cflash-url;
                        description "cflash device name monitored for capacity";
                    }

                    ///nokia-state/state/system/thresholds/cflash-cap-alarm-percent/rmon-alarm-id
                    leaf rmon-alarm-id {
                        type uint32;
                        description
                            "An index that uniquely identifies an entry in the alarm
                             table.  Each such entry defines a diagnostic sample at a
                             particular interval for an object on the device.";
                    }

                    ///nokia-state/state/system/thresholds/cflash-cap-alarm-percent/alarm-value
                    leaf alarm-value {
                        type int32;
                        description
                            "Specifies the value of the statistic during the last sampling
                             period.";
                    }

                    ///nokia-state/state/system/thresholds/cflash-cap-alarm-percent/variable-oid
                    leaf variable-oid {
                        type string {
                            length "1..255";
                        }
                        description
                            "Specifies the object identifier of the particular variable
                             to be sampled.";
                    }

                    ///nokia-state/state/system/thresholds/cflash-cap-alarm-percent/rising-rmon-event-id
                    leaf rising-rmon-event-id {
                        type uint32;
                        description
                            "Specifies the index of the eventEntry that is used when a
                             rising threshold is crossed.";
                    }

                    ///nokia-state/state/system/thresholds/cflash-cap-alarm-percent/rising-event-last-time-sent
                    leaf rising-event-last-time-sent {
                        type types-sros:time-interval;
                        description
                            "The value of sysUpTime at the time rising event
                             entry last generated an event.  If this entry has
                             not generated any events, this value will be
                             zero.";
                    }

                    ///nokia-state/state/system/thresholds/cflash-cap-alarm-percent/falling-rmon-event-id
                    leaf falling-rmon-event-id {
                        type uint32;
                        description
                            "Specifies the index of the eventEntry that is used when a
                             falling threshold is crossed.";
                    }

                    ///nokia-state/state/system/thresholds/cflash-cap-alarm-percent/falling-event-last-time-sent
                    leaf falling-event-last-time-sent {
                        type types-sros:time-interval;
                        description
                            "The value of sysUpTime at the time falling event
                             entry last generated an event.  If this entry has
                             not generated any events, this value will be
                             zero.";
                    }

                } // list cflash-cap-alarm-percent

                ///nokia-state/state/system/thresholds/cflash-cap-warn-percent
                list cflash-cap-warn-percent {
                    key "cflash-id";
                    description "Enter the cflash-cap-warn-percent list instance";

                    ///nokia-state/state/system/thresholds/cflash-cap-warn-percent/cflash-id
                    leaf cflash-id {
                        type types-sros:thresholds-cflash-url;
                        description "cflash device name monitored for capacity";
                    }

                    ///nokia-state/state/system/thresholds/cflash-cap-warn-percent/rmon-alarm-id
                    leaf rmon-alarm-id {
                        type uint32;
                        description
                            "An index that uniquely identifies an entry in the alarm
                             table.  Each such entry defines a diagnostic sample at a
                             particular interval for an object on the device.";
                    }

                    ///nokia-state/state/system/thresholds/cflash-cap-warn-percent/alarm-value
                    leaf alarm-value {
                        type int32;
                        description
                            "Specifies the value of the statistic during the last sampling
                             period.";
                    }

                    ///nokia-state/state/system/thresholds/cflash-cap-warn-percent/variable-oid
                    leaf variable-oid {
                        type string {
                            length "1..255";
                        }
                        description
                            "Specifies the object identifier of the particular variable
                             to be sampled.";
                    }

                    ///nokia-state/state/system/thresholds/cflash-cap-warn-percent/rising-rmon-event-id
                    leaf rising-rmon-event-id {
                        type uint32;
                        description
                            "Specifies the index of the eventEntry that is used when a
                             rising threshold is crossed.";
                    }

                    ///nokia-state/state/system/thresholds/cflash-cap-warn-percent/rising-event-last-time-sent
                    leaf rising-event-last-time-sent {
                        type types-sros:time-interval;
                        description
                            "The value of sysUpTime at the time rising event
                             entry last generated an event.  If this entry has
                             not generated any events, this value will be
                             zero.";
                    }

                    ///nokia-state/state/system/thresholds/cflash-cap-warn-percent/falling-rmon-event-id
                    leaf falling-rmon-event-id {
                        type uint32;
                        description
                            "Specifies the index of the eventEntry that is used when a
                             falling threshold is crossed.";
                    }

                    ///nokia-state/state/system/thresholds/cflash-cap-warn-percent/falling-event-last-time-sent
                    leaf falling-event-last-time-sent {
                        type types-sros:time-interval;
                        description
                            "The value of sysUpTime at the time falling event
                             entry last generated an event.  If this entry has
                             not generated any events, this value will be
                             zero.";
                    }

                } // list cflash-cap-warn-percent

                ///nokia-state/state/system/thresholds/kb-memory-use-alarm
                container kb-memory-use-alarm {
                    description "Enable the kb-memory-use-alarm context";

                    ///nokia-state/state/system/thresholds/kb-memory-use-alarm/rmon-alarm-id
                    leaf rmon-alarm-id {
                        type uint32;
                        description
                            "An index that uniquely identifies an entry in the alarm
                             table.  Each such entry defines a diagnostic sample at a
                             particular interval for an object on the device.";
                    }

                    ///nokia-state/state/system/thresholds/kb-memory-use-alarm/alarm-value
                    leaf alarm-value {
                        type int32;
                        description
                            "Specifies the value of the statistic during the last sampling
                             period.";
                    }

                    ///nokia-state/state/system/thresholds/kb-memory-use-alarm/variable-oid
                    leaf variable-oid {
                        type string {
                            length "1..255";
                        }
                        description
                            "Specifies the object identifier of the particular variable
                             to be sampled.";
                    }

                    ///nokia-state/state/system/thresholds/kb-memory-use-alarm/rising-rmon-event-id
                    leaf rising-rmon-event-id {
                        type uint32;
                        description
                            "Specifies the index of the eventEntry that is used when a
                             rising threshold is crossed.";
                    }

                    ///nokia-state/state/system/thresholds/kb-memory-use-alarm/rising-event-last-time-sent
                    leaf rising-event-last-time-sent {
                        type types-sros:time-interval;
                        description
                            "The value of sysUpTime at the time rising event
                             entry last generated an event.  If this entry has
                             not generated any events, this value will be
                             zero.";
                    }

                    ///nokia-state/state/system/thresholds/kb-memory-use-alarm/falling-rmon-event-id
                    leaf falling-rmon-event-id {
                        type uint32;
                        description
                            "Specifies the index of the eventEntry that is used when a
                             falling threshold is crossed.";
                    }

                    ///nokia-state/state/system/thresholds/kb-memory-use-alarm/falling-event-last-time-sent
                    leaf falling-event-last-time-sent {
                        type types-sros:time-interval;
                        description
                            "The value of sysUpTime at the time falling event
                             entry last generated an event.  If this entry has
                             not generated any events, this value will be
                             zero.";
                    }

                } // container kb-memory-use-alarm

                ///nokia-state/state/system/thresholds/kb-memory-use-warn
                container kb-memory-use-warn {
                    description "Enable the kb-memory-use-warn context";

                    ///nokia-state/state/system/thresholds/kb-memory-use-warn/rmon-alarm-id
                    leaf rmon-alarm-id {
                        type uint32;
                        description
                            "An index that uniquely identifies an entry in the alarm
                             table.  Each such entry defines a diagnostic sample at a
                             particular interval for an object on the device.";
                    }

                    ///nokia-state/state/system/thresholds/kb-memory-use-warn/alarm-value
                    leaf alarm-value {
                        type int32;
                        description
                            "Specifies the value of the statistic during the last sampling
                             period.";
                    }

                    ///nokia-state/state/system/thresholds/kb-memory-use-warn/variable-oid
                    leaf variable-oid {
                        type string {
                            length "1..255";
                        }
                        description
                            "Specifies the object identifier of the particular variable
                             to be sampled.";
                    }

                    ///nokia-state/state/system/thresholds/kb-memory-use-warn/rising-rmon-event-id
                    leaf rising-rmon-event-id {
                        type uint32;
                        description
                            "Specifies the index of the eventEntry that is used when a
                             rising threshold is crossed.";
                    }

                    ///nokia-state/state/system/thresholds/kb-memory-use-warn/rising-event-last-time-sent
                    leaf rising-event-last-time-sent {
                        type types-sros:time-interval;
                        description
                            "The value of sysUpTime at the time rising event
                             entry last generated an event.  If this entry has
                             not generated any events, this value will be
                             zero.";
                    }

                    ///nokia-state/state/system/thresholds/kb-memory-use-warn/falling-rmon-event-id
                    leaf falling-rmon-event-id {
                        type uint32;
                        description
                            "Specifies the index of the eventEntry that is used when a
                             falling threshold is crossed.";
                    }

                    ///nokia-state/state/system/thresholds/kb-memory-use-warn/falling-event-last-time-sent
                    leaf falling-event-last-time-sent {
                        type types-sros:time-interval;
                        description
                            "The value of sysUpTime at the time falling event
                             entry last generated an event.  If this entry has
                             not generated any events, this value will be
                             zero.";
                    }

                } // container kb-memory-use-warn

                ///nokia-state/state/system/thresholds/rmon
                container rmon {
                    description "Enter the rmon context";

                    ///nokia-state/state/system/thresholds/rmon/alarm
                    list alarm {
                        key "rmon-alarm-id";
                        description "Enter the alarm list instance";

                        ///nokia-state/state/system/thresholds/rmon/alarm/rmon-alarm-id
                        leaf rmon-alarm-id {
                            type uint32 {
                                range "0..65400";
                            }
                            description "Index ID for an entry in the alarm table";
                        }

                        ///nokia-state/state/system/thresholds/rmon/alarm/alarm-value
                        leaf alarm-value {
                            type int32;
                            description
                                "Specifies the value of the statistic during the last sampling
                                 period.";
                        }

                    } // list alarm

                    ///nokia-state/state/system/thresholds/rmon/event
                    list event {
                        key "rmon-event-id";
                        description "Enter the event list instance";

                        ///nokia-state/state/system/thresholds/rmon/event/rmon-event-id
                        leaf rmon-event-id {
                            type uint32 {
                                range "1..65400";
                            }
                            description "Index ID for an entry in the event table";
                        }

                        ///nokia-state/state/system/thresholds/rmon/event/event-last-time-sent
                        leaf event-last-time-sent {
                            type types-sros:time-interval;
                            description
                                "The value of sysUpTime at the time this event
                                 entry last generated an event.  If this entry has
                                 not generated any events, this value will be
                                 zero.";
                        }

                    } // list event

                } // container rmon

            } // container thresholds

            ///nokia-state/state/system/lldp
            container lldp {
                description "Enable the lldp context";

                ///nokia-state/state/system/lldp/chassis-id
                leaf chassis-id {
                    type types-lldp:chassis-id;
                    description "Indicates the chassis component provided by the local system.";
                }

                ///nokia-state/state/system/lldp/chassis-id-subtype
                leaf chassis-id-subtype {
                    type types-lldp:chassis-id-subtype;
                    description "Indicates the chassis identifier subtype associated with the local system.";
                }

                ///nokia-state/state/system/lldp/system-name
                leaf system-name {
                    type string;
                    description "Indicates the system name of the local system.";
                }

                ///nokia-state/state/system/lldp/system-description
                leaf system-description {
                    type string;
                    description "Indicates the system description of the local system.";
                }

                ///nokia-state/state/system/lldp/capabilities-supported
                leaf capabilities-supported {
                    type types-lldp:system-capabilities;
                    description "Indicates which system capabilities are supported on the local system.";
                }

                ///nokia-state/state/system/lldp/capabilities-enabled
                leaf capabilities-enabled {
                    type types-lldp:system-capabilities;
                    description "Indicates which system capabilities are enabled on the local system.";
                }

                ///nokia-state/state/system/lldp/dest-mac
                list dest-mac {
                    key "mac-type";
                    description "Enter the dest-mac list instance";

                    ///nokia-state/state/system/lldp/dest-mac/mac-type
                    leaf mac-type {
                        type types-lldp:mac-addr-type;
                        description "The identifier which uniquely identifies the MAC address type.";
                    }

                    ///nokia-state/state/system/lldp/dest-mac/mac-address
                    leaf mac-address {
                        type yang:mac-address;
                        description
                            "Indicates the destination MAC address associated with
                             this entry.

                             The octet string identifies an individual or a group
                             MAC address that is in use by LLDP as a destination
                             MAC address.

                             The MAC address is encoded in the octet string in
                             canonical format (see IEEE Std 802).";
                    }

                } // list dest-mac

                ///nokia-state/state/system/lldp/mgmt-address
                list mgmt-address {
                    key "mgmt-address-subtype mgmt-address";
                    description "Enter the mgmt-address list instance";

                    ///nokia-state/state/system/lldp/mgmt-address/mgmt-address-subtype
                    leaf mgmt-address-subtype {
                        type types-lldp:address-family-numbers;
                        description
                            "Specifies the type of management address identifier encoding
                             used in mgmt-address.";
                    }

                    ///nokia-state/state/system/lldp/mgmt-address/mgmt-address
                    leaf mgmt-address {
                        type types-lldp:management-address;
                        description
                            "Specifies the string value used to identify the management address
                             component associated with the remote system. The purpose
                             of this address is to contact the management entity.";
                    }

                    ///nokia-state/state/system/lldp/mgmt-address/interface-subtype
                    leaf interface-subtype {
                        type enumeration {
                            enum unknown                        { value 1; }
                            enum if-index                       { value 2; }
                            enum system-port-number             { value 3; }
                        }
                        description
                            "Indicates the interface numbering type provided by the remote
                             system. The corresponding interface number is interface-id.";
                    }

                    ///nokia-state/state/system/lldp/mgmt-address/interface-id
                    leaf interface-id {
                        type int32;
                        description
                            "Indicates the integer value used to identify the interface number
                             regarding the management address component associated with
                             the remote system.";
                    }

                    ///nokia-state/state/system/lldp/mgmt-address/object-identifier
                    leaf object-identifier {
                        type yang:object-identifier-128;
                        description
                            "Indicates the OID value used to identify the type of hardware
                             component or protocol entity associated with the management address
                             advertised by the remote system agent.";
                    }

                } // list mgmt-address

                ///nokia-state/state/system/lldp/statistics
                container statistics {
                    description "Enter the statistics context";

                    ///nokia-state/state/system/lldp/statistics/remote
                    container remote {
                        description "Enter the remote context";

                        ///nokia-state/state/system/lldp/statistics/remote/last-changed
                        leaf last-changed {
                            type yang:date-and-time;
                            description
                                "Indicates the system update time when the remote system information
                                 was last modified.";
                        }

                        ///nokia-state/state/system/lldp/statistics/remote/inserts
                        leaf inserts {
                            type yang:zero-based-counter32;
                            description
                                "Indicates the number of times the complete set of information
                                 advertised by a particular MSAP has been inserted in the list
                                 /port/ethernet/lldp/dest-mac/remote-system.";
                        }

                        ///nokia-state/state/system/lldp/statistics/remote/deletes
                        leaf deletes {
                            type yang:zero-based-counter32;
                            description
                                "Indicates the number of times the complete set of information
                                 advertised by a particular MSAP has been deleted from the list
                                 /port/ethernet/lldp/dest-mac/remote-system.";
                        }

                        ///nokia-state/state/system/lldp/statistics/remote/drops
                        leaf drops {
                            type yang:zero-based-counter32;
                            description
                                "Indicates the number of times the complete set of information
                                 advertised by a particular MSAP could not be entered into the list
                                 /port/ethernet/lldp/dest-mac/remote-system.";
                        }

                        ///nokia-state/state/system/lldp/statistics/remote/ageouts
                        leaf ageouts {
                            type yang:zero-based-counter32;
                            description
                                "Indicates the number of times the complete set of information
                                 advertised by a particular MSAP has been deleted from the list
                                 /port/ethernet/lldp/dest-mac/remote-system because the information
                                 timeliness interval has expired.";
                        }

                    } // container remote

                } // container statistics

            } // container lldp

            ///nokia-state/state/system/l2tp
            container l2tp {
                description "Enable the l2tp context";

                ///nokia-state/state/system/l2tp/max-tunnels
                leaf max-tunnels {
                    type uint32;
                    description "The maximum number of supported tunnels in the system.";
                }

                ///nokia-state/state/system/l2tp/max-sessions
                leaf max-sessions {
                    type uint32;
                    description "The maximum number of supported sessions in the system.";
                }

                ///nokia-state/state/system/l2tp/max-sessions-per-tunnel
                leaf max-sessions-per-tunnel {
                    type uint32;
                    description "The maximum number of supported sessions per tunnel.";
                }

            } // container l2tp

            ///nokia-state/state/system/power-management
            list power-management {
                key "power-zone";
                description "Enter the power-management list instance";

                ///nokia-state/state/system/power-management/power-zone
                leaf power-zone {
                    type uint32 {
                        range "1..2";
                    }
                    description "Power zone";
                }

                ///nokia-state/state/system/power-management/active-conditions
                leaf active-conditions {
                    type bits {
                        bit capacity-exceeded              { position 0; }
                        bit lost-capacity                  { position 1; }
                        bit insufficient-capacity          { position 2; }
                        bit overload                       { position 3; }
                        bit safety-alert                   { position 4; }
                        bit safety-level                   { position 5; }
                    }
                    description
                        "Indicates the active conditions present on a given power zone. When
                         the bit is set, the condition is active. 

                         Conditions include:
                            capacity-exceeded - a device in the power-zone requires power to
                                boot, but there is insufficient capcity to support it
                            lost-capacity - system power capacity is insufficient to
                                satisfy the safety level while maintaining any applicable
                                power reserve
                            insufficient-capacity - the provisioned capacity of the power-zone
                                can not support the requirements of the system and provisioned
                                equipment, while maintaining any applicable power reserve
                            overload - the system power capacity is insufficient to power
                                essential equipment while maintaining any applicable power reserve.
                            safety-alert - the system power capacity has dropped below the
                                safety alert threshold configured by tmnxChassisPwrMgmtSafetyAlert
                            safety-level - the peak power consumption has exceeded the safety
                                level threshold configured by tmnxChassisPwrMgmtSafetyLevel";
                }

                ///nokia-state/state/system/power-management/peak-utilization
                leaf peak-utilization {
                    type uint32;
                    units "watts";
                    description
                        "The maximum power consumed by the system within the current power zone,
                         measured in Watts (W).";
                }

                ///nokia-state/state/system/power-management/reserve-power
                leaf reserve-power {
                    type uint32;
                    units "watts";
                    description "The greatest rated output among equipped power sources, measured in Watts (W)";
                }

                ///nokia-state/state/system/power-management/requirement-remaining-power
                leaf requirement-remaining-power {
                    type int32;
                    units "watts";
                    description
                        "The remaining power available to the system beyond the required and
                         reserved power ratings, measured in Watts (W).";
                }

                ///nokia-state/state/system/power-management/utilization-remaining-power
                leaf utilization-remaining-power {
                    type int32;
                    units "watts";
                    description
                        "The remaining power available to the system beyond the currently-utilized
                         and reserved power ratings, measured in Watts (W).";
                }

                ///nokia-state/state/system/power-management/oper-safety-level
                leaf oper-safety-level {
                    type uint32;
                    units "watts";
                    description "Indicates the operational safety level.";
                }

                ///nokia-state/state/system/power-management/oper-safety-alert
                leaf oper-safety-alert {
                    type uint32;
                    units "watts";
                    description "Indicates the operational safety alert.";
                }

            } // list power-management

            ///nokia-state/state/system/limits
            container limits {
                description "Enter the limits context";

                ///nokia-state/state/system/limits/slots
                leaf slots {
                    type uint32;
                    description
                        "The maximum number of slots that can be made
                         available for plug-in cards if the maximum number of physical
                         router chassis are populated. This includes both CPM and
                         IOM/IMM/XCM slots.";
                }

                ///nokia-state/state/system/limits/operational-slots
                leaf operational-slots {
                    type uint32;
                    description
                        "The number of slots that are available for plug-in
                         cards of all the physical router chassis configured in the
                         system. This includes both CPM and IOM/IMM/XCM slots.";
                }

                ///nokia-state/state/system/limits/ports
                leaf ports {
                    type uint32;
                    description
                        "The total number of faceplate ports and connectors currently
                         installed for all of the physical router chassis in the
                         system. This does not include the Ethernet ports
                         on the CPM cards that are used for management access.";
                }

                ///nokia-state/state/system/limits/physical-ports
                leaf physical-ports {
                    type uint32;
                    description
                        "The total number of faceplate ports and connector-ports
                         currently installed for all the physical router chassis in
                         the system. This does not include the Ethernet ports on
                         the CPM cards that are used for management access.";
                }

                ///nokia-state/state/system/limits/power-supplies
                leaf power-supplies {
                    type uint32;
                    description
                        "The total number of power supplies installed for all
                         the physical router chassis in the system.";
                }

                ///nokia-state/state/system/limits/fan-trays
                leaf fan-trays {
                    type uint32;
                    description
                        "The total number of fan-trays installed for all the
                         physical router chassis in the system.";
                }

                ///nokia-state/state/system/limits/fans
                leaf fans {
                    type uint32;
                    description
                        "The total number of fans installed for all the
                         physical router chassis in the system.";
                }

            } // container limits

            ///nokia-state/state/system/led-states
            container led-states {
                description "Enter the led-states context";

                ///nokia-state/state/system/led-states/critical
                leaf critical {
                    type types-system:led-state;
                    description "The current state of the critical LED in the system.";
                }

                ///nokia-state/state/system/led-states/major
                leaf major {
                    type types-system:led-state;
                    description "The current state of the major LED in the system.";
                }

                ///nokia-state/state/system/led-states/minor
                leaf minor {
                    type types-system:led-state;
                    description "The current state of the minor LED in the system.";
                }

                ///nokia-state/state/system/led-states/alarm
                leaf alarm {
                    type types-system:led-state;
                    description "The current state of the alarm LED in the system.";
                }

            } // container led-states

            ///nokia-state/state/system/connections
            container connections {
                description "Enter the connections context";

                ///nokia-state/state/system/connections/tcp-connection
                list tcp-connection {
                    key "local-ip-address local-port remote-ip-address remote-port router-instance";
                    description "Enter the tcp-connection list instance";

                    ///nokia-state/state/system/connections/tcp-connection/local-ip-address
                    leaf local-ip-address {
                        type types-sros:ip-address;
                        description "IP address of local address.";
                    }

                    ///nokia-state/state/system/connections/tcp-connection/local-port
                    leaf local-port {
                        type inet:port-number;
                        description "Protocol port number of local port.";
                    }

                    ///nokia-state/state/system/connections/tcp-connection/remote-ip-address
                    leaf remote-ip-address {
                        type types-sros:ip-address;
                        description "IP address of remote address.";
                    }

                    ///nokia-state/state/system/connections/tcp-connection/remote-port
                    leaf remote-port {
                        type inet:port-number;
                        description "Protocol port number of remote port.";
                    }

                    ///nokia-state/state/system/connections/tcp-connection/router-instance
                    leaf router-instance {
                        type types-sros:router-instance;
                        description "Specifies the routing context.";
                    }

                    ///nokia-state/state/system/connections/tcp-connection/rx-queue-depth
                    leaf rx-queue-depth {
                        type uint32;
                        description "Bytes in socket receive buffer.";
                    }

                    ///nokia-state/state/system/connections/tcp-connection/tx-queue-depth
                    leaf tx-queue-depth {
                        type uint32;
                        description "Bytes in socket send buffer.";
                    }

                    ///nokia-state/state/system/connections/tcp-connection/tcp-state
                    leaf tcp-state {
                        type enumeration {
                            enum not-available                  { value 0; }
                            enum closed                         { value 1; }
                            enum listen                         { value 2; }
                            enum syn-sent                       { value 3; }
                            enum syn-rcvd                       { value 4; }
                            enum establish                      { value 5; }
                            enum fin-wait-1                     { value 6; }
                            enum fin-wait-2                     { value 7; }
                            enum close-wait                     { value 8; }
                            enum last-ack                       { value 9; }
                            enum closing                        { value 10; }
                            enum time-wait                      { value 11; }
                        }
                        description "TCP connections state.";
                    }

                    ///nokia-state/state/system/connections/tcp-connection/oper-maximum-segment-size
                    leaf oper-maximum-segment-size {
                        type uint32;
                        description "Maximum number of bytes in a single TCP segment.";
                    }

                    ///nokia-state/state/system/connections/tcp-connection/received-maxseg-option
                    leaf received-maxseg-option {
                        type uint32;
                        description
                            "The value received from the peer in the MAXSEG TCP option
                             when the TCP session was started.";
                    }

                } // list tcp-connection

                ///nokia-state/state/system/connections/statistics
                container statistics {
                    description "Enter the statistics context";

                    ///nokia-state/state/system/connections/statistics/tcp
                    container tcp {
                        description "Enter the tcp context";

                        ///nokia-state/state/system/connections/statistics/tcp/ack-for-unsent-data
                        leaf ack-for-unsent-data {
                            type uint32;
                            description "Received acks for unsent data.";
                        }

                        ///nokia-state/state/system/connections/statistics/tcp/ack-only-packets
                        leaf ack-only-packets {
                            type uint32;
                            description "Ack-only packets sent.";
                        }

                        ///nokia-state/state/system/connections/statistics/tcp/ack-only-packets-delayed
                        leaf ack-only-packets-delayed {
                            type uint32;
                            description "Delayed ack packets sent.";
                        }

                        ///nokia-state/state/system/connections/statistics/tcp/acks
                        leaf acks {
                            type uint32;
                            description "Received ack packets.";
                        }

                        ///nokia-state/state/system/connections/statistics/tcp/completely-duplicate-packet
                        leaf completely-duplicate-packet {
                            type uint32;
                            description "Duplicate-only packets received.";
                        }

                        ///nokia-state/state/system/connections/statistics/tcp/connections-accept
                        leaf connections-accept {
                            type uint32;
                            description "Number of connections accepted.";
                        }

                        ///nokia-state/state/system/connections/statistics/tcp/connections-closed
                        leaf connections-closed {
                            type uint32;
                            description "Number of connections closed including dropped connections.";
                        }

                        ///nokia-state/state/system/connections/statistics/tcp/connections-dropped
                        leaf connections-dropped {
                            type uint32;
                            description "Number of connections dropped.";
                        }

                        ///nokia-state/state/system/connections/statistics/tcp/packets-dropped-by-md5
                        leaf packets-dropped-by-md5 {
                            type uint32;
                            description "Number of packets dropped because of MD5.";
                        }

                        ///nokia-state/state/system/connections/statistics/tcp/packets-dropped-by-enhanced-auth
                        leaf packets-dropped-by-enhanced-auth {
                            type uint32;
                            description "Enhanced authentication option packets dropped.";
                        }

                        ///nokia-state/state/system/connections/statistics/tcp/packets-dropped-by-tcp-ao
                        leaf packets-dropped-by-tcp-ao {
                            type uint32;
                            description "Tcp-Ao packets dropped.";
                        }

                        ///nokia-state/state/system/connections/statistics/tcp/connections-dropped-by-full-queue
                        leaf connections-dropped-by-full-queue {
                            type uint32;
                            description "Number of connections dropped because of full queue.";
                        }

                        ///nokia-state/state/system/connections/statistics/tcp/connections-dropped-by-keepalive
                        leaf connections-dropped-by-keepalive {
                            type uint32;
                            description "Number of connections dropped by keepalive.";
                        }

                        ///nokia-state/state/system/connections/statistics/tcp/connections-dropped-by-rexmit-timeout
                        leaf connections-dropped-by-rexmit-timeout {
                            type uint32;
                            description "Number of connections dropped in rxmt timeout.";
                        }

                        ///nokia-state/state/system/connections/statistics/tcp/connections-request
                        leaf connections-request {
                            type uint32;
                            description "Number of connections initiated.";
                        }

                        ///nokia-state/state/system/connections/statistics/tcp/connections-established
                        leaf connections-established {
                            type uint32;
                            description "Number of connection established including accepts.";
                        }

                        ///nokia-state/state/system/connections/statistics/tcp/control-packets
                        leaf control-packets {
                            type uint32;
                            description "Control (SYN|FIN|RST) packets sent.";
                        }

                        ///nokia-state/state/system/connections/statistics/tcp/data-packet
                        leaf data-packet {
                            type uint32;
                            description "Data packets sent.";
                        }

                        ///nokia-state/state/system/connections/statistics/tcp/data-packet-retransmitted
                        leaf data-packet-retransmitted {
                            type uint32;
                            description "Data packets retransmitted.";
                        }

                        ///nokia-state/state/system/connections/statistics/tcp/discarded-because-packet-too-short
                        leaf discarded-because-packet-too-short {
                            type uint32;
                            description "Packets received too short.";
                        }

                        ///nokia-state/state/system/connections/statistics/tcp/discarded-for-bad-checksum
                        leaf discarded-for-bad-checksum {
                            type uint32;
                            description "Packets received with checksum errors.";
                        }

                        ///nokia-state/state/system/connections/statistics/tcp/discarded-for-bad-header-offset-field
                        leaf discarded-for-bad-header-offset-field {
                            type uint32;
                            description "Packets received with bad offset.";
                        }

                        ///nokia-state/state/system/connections/statistics/tcp/duplicate-acks
                        leaf duplicate-acks {
                            type uint32;
                            description "Received duplicate acks.";
                        }

                        ///nokia-state/state/system/connections/statistics/tcp/embryonic-connections-dropped
                        leaf embryonic-connections-dropped {
                            type uint32;
                            description "Embryonic connections dropped.";
                        }

                        ///nokia-state/state/system/connections/statistics/tcp/keepalive-probes-sent
                        leaf keepalive-probes-sent {
                            type uint32;
                            description "Keepalive probes sent.";
                        }

                        ///nokia-state/state/system/connections/statistics/tcp/keepalive-timeouts
                        leaf keepalive-timeouts {
                            type uint32;
                            description "Keepalive timeouts.";
                        }

                        ///nokia-state/state/system/connections/statistics/tcp/out-of-order-packets
                        leaf out-of-order-packets {
                            type uint32;
                            description "Out of order packets received.";
                        }

                        ///nokia-state/state/system/connections/statistics/tcp/packet-of-data-after-window
                        leaf packet-of-data-after-window {
                            type uint32;
                            description "Packets with data after window.";
                        }

                        ///nokia-state/state/system/connections/statistics/tcp/packet-sent
                        leaf packet-sent {
                            type uint32;
                            description "Total packets sent.";
                        }

                        ///nokia-state/state/system/connections/statistics/tcp/packet-with-some-dup-data
                        leaf packet-with-some-dup-data {
                            type uint32;
                            description "Packets with some duplicate data.";
                        }

                        ///nokia-state/state/system/connections/statistics/tcp/packets-received
                        leaf packets-received {
                            type uint32;
                            description "Total packets received.";
                        }

                        ///nokia-state/state/system/connections/statistics/tcp/packets-received-in-sequence
                        leaf packets-received-in-sequence {
                            type uint32;
                            description "Packets received in sequence.";
                        }

                        ///nokia-state/state/system/connections/statistics/tcp/packets-recieved-after-close
                        leaf packets-recieved-after-close {
                            type uint32;
                            description "Packets received after 'close'.";
                        }

                        ///nokia-state/state/system/connections/statistics/tcp/path-mtu-discovery-backoff
                        leaf path-mtu-discovery-backoff {
                            type uint32;
                            description "Number of times the path-mtu-discovery is switched off.";
                        }

                        ///nokia-state/state/system/connections/statistics/tcp/pcb-cache-lookups-failed
                        leaf pcb-cache-lookups-failed {
                            type uint32;
                            description "Number of times pcb cache lookup failed.";
                        }

                        ///nokia-state/state/system/connections/statistics/tcp/persist-timeouts
                        leaf persist-timeouts {
                            type uint32;
                            description "Persist timeouts.";
                        }

                        ///nokia-state/state/system/connections/statistics/tcp/retransmit-timeouts
                        leaf retransmit-timeouts {
                            type uint32;
                            description "Retransmit timeouts.";
                        }

                        ///nokia-state/state/system/connections/statistics/tcp/segments-attempts
                        leaf segments-attempts {
                            type uint32;
                            description "Attempts to get rtt.";
                        }

                        ///nokia-state/state/system/connections/statistics/tcp/segments-updated-rtt
                        leaf segments-updated-rtt {
                            type uint32;
                            description "Successful attempts of rtt update.";
                        }

                        ///nokia-state/state/system/connections/statistics/tcp/urg-only-packet
                        leaf urg-only-packet {
                            type uint32;
                            description "Packets sent with URG only.";
                        }

                        ///nokia-state/state/system/connections/statistics/tcp/window-probe
                        leaf window-probe {
                            type uint32;
                            description "Received windows probe packets.";
                        }

                        ///nokia-state/state/system/connections/statistics/tcp/window-probe-packet
                        leaf window-probe-packet {
                            type uint32;
                            description "Window probes sent.";
                        }

                        ///nokia-state/state/system/connections/statistics/tcp/window-update-packet
                        leaf window-update-packet {
                            type uint32;
                            description "Window update-only packets sent.";
                        }

                        ///nokia-state/state/system/connections/statistics/tcp/window-update-rcv-packet
                        leaf window-update-rcv-packet {
                            type uint32;
                            description "Received window update packets.";
                        }

                    } // container tcp

                } // container statistics

            } // container connections

            ///nokia-state/state/system/cpu
            list cpu {
                key "sample-period";
                description "Enter the cpu list instance";

                ///nokia-state/state/system/cpu/sample-period
                leaf sample-period {
                    type types-sros:time-duration {
                        range "1|60|300";
                    }
                    units "seconds";
                    description "Number of seconds for how long to collect CPU information.";
                }

                ///nokia-state/state/system/cpu/bfd
                container bfd {
                    description "Enter the bfd context";

                    ///nokia-state/state/system/cpu/bfd/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/bfd/time-used
                    leaf time-used {
                        type types-sros:time-duration-64;
                        units "microseconds";
                        description "Number of microseconds used by this group/core since start-up.";
                    }

                    ///nokia-state/state/system/cpu/bfd/cpu-usage
                    leaf cpu-usage {
                        type decimal64 {
                            range "0..100";
                            fraction-digits 2;
                        }
                        units "percent";
                        description "Relative amount of time used by this group/core since start-up.";
                    }

                    ///nokia-state/state/system/cpu/bfd/capacity-usage
                    leaf capacity-usage {
                        type decimal64 {
                            range "0..100";
                            fraction-digits 2;
                        }
                        units "percent";
                        description "Relative amount of time used by the busiest task/core.";
                    }

                } // container bfd

                ///nokia-state/state/system/cpu/bgp
                container bgp {
                    description "Enter the bgp context";

                    ///nokia-state/state/system/cpu/bgp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/bgp/time-used
                    leaf time-used {
                        type types-sros:time-duration-64;
                        units "microseconds";
                        description "Number of microseconds used by this group/core since start-up.";
                    }

                    ///nokia-state/state/system/cpu/bgp/cpu-usage
                    leaf cpu-usage {
                        type decimal64 {
                            range "0..100";
                            fraction-digits 2;
                        }
                        units "percent";
                        description "Relative amount of time used by this group/core since start-up.";
                    }

                    ///nokia-state/state/system/cpu/bgp/capacity-usage
                    leaf capacity-usage {
                        type decimal64 {
                            range "0..100";
                            fraction-digits 2;
                        }
                        units "percent";
                        description "Relative amount of time used by the busiest task/core.";
                    }

                } // container bgp

                ///nokia-state/state/system/cpu/bgp-pe-ce
                container bgp-pe-ce {
                    description "Enter the bgp-pe-ce context";

                    ///nokia-state/state/system/cpu/bgp-pe-ce/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/bgp-pe-ce/time-used
                    leaf time-used {
                        type types-sros:time-duration-64;
                        units "microseconds";
                        description "Number of microseconds used by this group/core since start-up.";
                    }

                    ///nokia-state/state/system/cpu/bgp-pe-ce/cpu-usage
                    leaf cpu-usage {
                        type decimal64 {
                            range "0..100";
                            fraction-digits 2;
                        }
                        units "percent";
                        description "Relative amount of time used by this group/core since start-up.";
                    }

                    ///nokia-state/state/system/cpu/bgp-pe-ce/capacity-usage
                    leaf capacity-usage {
                        type decimal64 {
                            range "0..100";
                            fraction-digits 2;
                        }
                        units "percent";
                        description "Relative amount of time used by the busiest task/core.";
                    }

                } // container bgp-pe-ce

                ///nokia-state/state/system/cpu/bier
                container bier {
                    description "Enter the bier context";

                    ///nokia-state/state/system/cpu/bier/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/bier/time-used
                    leaf time-used {
                        type types-sros:time-duration-64;
                        units "microseconds";
                        description "Number of microseconds used by this group/core since start-up.";
                    }

                    ///nokia-state/state/system/cpu/bier/cpu-usage
                    leaf cpu-usage {
                        type decimal64 {
                            range "0..100";
                            fraction-digits 2;
                        }
                        units "percent";
                        description "Relative amount of time used by this group/core since start-up.";
                    }

                    ///nokia-state/state/system/cpu/bier/capacity-usage
                    leaf capacity-usage {
                        type decimal64 {
                            range "0..100";
                            fraction-digits 2;
                        }
                        units "percent";
                        description "Relative amount of time used by the busiest task/core.";
                    }

                } // container bier

                ///nokia-state/state/system/cpu/calltrace
                container calltrace {
                    description "Enter the calltrace context";

                    ///nokia-state/state/system/cpu/calltrace/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/calltrace/time-used
                    leaf time-used {
                        type types-sros:time-duration-64;
                        units "microseconds";
                        description "Number of microseconds used by this group/core since start-up.";
                    }

                    ///nokia-state/state/system/cpu/calltrace/cpu-usage
                    leaf cpu-usage {
                        type decimal64 {
                            range "0..100";
                            fraction-digits 2;
                        }
                        units "percent";
                        description "Relative amount of time used by this group/core since start-up.";
                    }

                    ///nokia-state/state/system/cpu/calltrace/capacity-usage
                    leaf capacity-usage {
                        type decimal64 {
                            range "0..100";
                            fraction-digits 2;
                        }
                        units "percent";
                        description "Relative amount of time used by the busiest task/core.";
                    }

                } // container calltrace

                ///nokia-state/state/system/cpu/cflowd
                container cflowd {
                    description "Enter the cflowd context";

                    ///nokia-state/state/system/cpu/cflowd/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/cflowd/time-used
                    leaf time-used {
                        type types-sros:time-duration-64;
                        units "microseconds";
                        description "Number of microseconds used by this group/core since start-up.";
                    }

                    ///nokia-state/state/system/cpu/cflowd/cpu-usage
                    leaf cpu-usage {
                        type decimal64 {
                            range "0..100";
                            fraction-digits 2;
                        }
                        units "percent";
                        description "Relative amount of time used by this group/core since start-up.";
                    }

                    ///nokia-state/state/system/cpu/cflowd/capacity-usage
                    leaf capacity-usage {
                        type decimal64 {
                            range "0..100";
                            fraction-digits 2;
                        }
                        units "percent";
                        description "Relative amount of time used by the busiest task/core.";
                    }

                } // container cflowd

                ///nokia-state/state/system/cpu/cards-and-ports
                container cards-and-ports {
                    description "Enter the cards-and-ports context";

                    ///nokia-state/state/system/cpu/cards-and-ports/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/cards-and-ports/time-used
                    leaf time-used {
                        type types-sros:time-duration-64;
                        units "microseconds";
                        description "Number of microseconds used by this group/core since start-up.";
                    }

                    ///nokia-state/state/system/cpu/cards-and-ports/cpu-usage
                    leaf cpu-usage {
                        type decimal64 {
                            range "0..100";
                            fraction-digits 2;
                        }
                        units "percent";
                        description "Relative amount of time used by this group/core since start-up.";
                    }

                    ///nokia-state/state/system/cpu/cards-and-ports/capacity-usage
                    leaf capacity-usage {
                        type decimal64 {
                            range "0..100";
                            fraction-digits 2;
                        }
                        units "percent";
                        description "Relative amount of time used by the busiest task/core.";
                    }

                } // container cards-and-ports

                ///nokia-state/state/system/cpu/dhcp-server
                container dhcp-server {
                    description "Enter the dhcp-server context";

                    ///nokia-state/state/system/cpu/dhcp-server/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/dhcp-server/time-used
                    leaf time-used {
                        type types-sros:time-duration-64;
                        units "microseconds";
                        description "Number of microseconds used by this group/core since start-up.";
                    }

                    ///nokia-state/state/system/cpu/dhcp-server/cpu-usage
                    leaf cpu-usage {
                        type decimal64 {
                            range "0..100";
                            fraction-digits 2;
                        }
                        units "percent";
                        description "Relative amount of time used by this group/core since start-up.";
                    }

                    ///nokia-state/state/system/cpu/dhcp-server/capacity-usage
                    leaf capacity-usage {
                        type decimal64 {
                            range "0..100";
                            fraction-digits 2;
                        }
                        units "percent";
                        description "Relative amount of time used by the busiest task/core.";
                    }

                } // container dhcp-server

                ///nokia-state/state/system/cpu/eth-cfm
                container eth-cfm {
                    description "Enter the eth-cfm context";

                    ///nokia-state/state/system/cpu/eth-cfm/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/eth-cfm/time-used
                    leaf time-used {
                        type types-sros:time-duration-64;
                        units "microseconds";
                        description "Number of microseconds used by this group/core since start-up.";
                    }

                    ///nokia-state/state/system/cpu/eth-cfm/cpu-usage
                    leaf cpu-usage {
                        type decimal64 {
                            range "0..100";
                            fraction-digits 2;
                        }
                        units "percent";
                        description "Relative amount of time used by this group/core since start-up.";
                    }

                    ///nokia-state/state/system/cpu/eth-cfm/capacity-usage
                    leaf capacity-usage {
                        type decimal64 {
                            range "0..100";
                            fraction-digits 2;
                        }
                        units "percent";
                        description "Relative amount of time used by the busiest task/core.";
                    }

                } // container eth-cfm

                ///nokia-state/state/system/cpu/fastpath
                container fastpath {
                    description "Enter the fastpath context";

                    ///nokia-state/state/system/cpu/fastpath/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/fastpath/time-used
                    leaf time-used {
                        type types-sros:time-duration-64;
                        units "microseconds";
                        description "Number of microseconds used by this group/core since start-up.";
                    }

                    ///nokia-state/state/system/cpu/fastpath/cpu-usage
                    leaf cpu-usage {
                        type decimal64 {
                            range "0..100";
                            fraction-digits 2;
                        }
                        units "percent";
                        description "Relative amount of time used by this group/core since start-up.";
                    }

                    ///nokia-state/state/system/cpu/fastpath/capacity-usage
                    leaf capacity-usage {
                        type decimal64 {
                            range "0..100";
                            fraction-digits 2;
                        }
                        units "percent";
                        description "Relative amount of time used by the busiest task/core.";
                    }

                } // container fastpath

                ///nokia-state/state/system/cpu/icc
                container icc {
                    description "Enter the icc context";

                    ///nokia-state/state/system/cpu/icc/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/icc/time-used
                    leaf time-used {
                        type types-sros:time-duration-64;
                        units "microseconds";
                        description "Number of microseconds used by this group/core since start-up.";
                    }

                    ///nokia-state/state/system/cpu/icc/cpu-usage
                    leaf cpu-usage {
                        type decimal64 {
                            range "0..100";
                            fraction-digits 2;
                        }
                        units "percent";
                        description "Relative amount of time used by this group/core since start-up.";
                    }

                    ///nokia-state/state/system/cpu/icc/capacity-usage
                    leaf capacity-usage {
                        type decimal64 {
                            range "0..100";
                            fraction-digits 2;
                        }
                        units "percent";
                        description "Relative amount of time used by the busiest task/core.";
                    }

                } // container icc

                ///nokia-state/state/system/cpu/igmp-mld
                container igmp-mld {
                    description "Enter the igmp-mld context";

                    ///nokia-state/state/system/cpu/igmp-mld/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/igmp-mld/time-used
                    leaf time-used {
                        type types-sros:time-duration-64;
                        units "microseconds";
                        description "Number of microseconds used by this group/core since start-up.";
                    }

                    ///nokia-state/state/system/cpu/igmp-mld/cpu-usage
                    leaf cpu-usage {
                        type decimal64 {
                            range "0..100";
                            fraction-digits 2;
                        }
                        units "percent";
                        description "Relative amount of time used by this group/core since start-up.";
                    }

                    ///nokia-state/state/system/cpu/igmp-mld/capacity-usage
                    leaf capacity-usage {
                        type decimal64 {
                            range "0..100";
                            fraction-digits 2;
                        }
                        units "percent";
                        description "Relative amount of time used by the busiest task/core.";
                    }

                } // container igmp-mld

                ///nokia-state/state/system/cpu/imsi-db-appl
                container imsi-db-appl {
                    description "Enter the imsi-db-appl context";

                    ///nokia-state/state/system/cpu/imsi-db-appl/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/imsi-db-appl/time-used
                    leaf time-used {
                        type types-sros:time-duration-64;
                        units "microseconds";
                        description "Number of microseconds used by this group/core since start-up.";
                    }

                    ///nokia-state/state/system/cpu/imsi-db-appl/cpu-usage
                    leaf cpu-usage {
                        type decimal64 {
                            range "0..100";
                            fraction-digits 2;
                        }
                        units "percent";
                        description "Relative amount of time used by this group/core since start-up.";
                    }

                    ///nokia-state/state/system/cpu/imsi-db-appl/capacity-usage
                    leaf capacity-usage {
                        type decimal64 {
                            range "0..100";
                            fraction-digits 2;
                        }
                        units "percent";
                        description "Relative amount of time used by the busiest task/core.";
                    }

                } // container imsi-db-appl

                ///nokia-state/state/system/cpu/ip-stack
                container ip-stack {
                    description "Enter the ip-stack context";

                    ///nokia-state/state/system/cpu/ip-stack/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/ip-stack/time-used
                    leaf time-used {
                        type types-sros:time-duration-64;
                        units "microseconds";
                        description "Number of microseconds used by this group/core since start-up.";
                    }

                    ///nokia-state/state/system/cpu/ip-stack/cpu-usage
                    leaf cpu-usage {
                        type decimal64 {
                            range "0..100";
                            fraction-digits 2;
                        }
                        units "percent";
                        description "Relative amount of time used by this group/core since start-up.";
                    }

                    ///nokia-state/state/system/cpu/ip-stack/capacity-usage
                    leaf capacity-usage {
                        type decimal64 {
                            range "0..100";
                            fraction-digits 2;
                        }
                        units "percent";
                        description "Relative amount of time used by the busiest task/core.";
                    }

                } // container ip-stack

                ///nokia-state/state/system/cpu/is-is
                container is-is {
                    description "Enter the is-is context";

                    ///nokia-state/state/system/cpu/is-is/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/is-is/time-used
                    leaf time-used {
                        type types-sros:time-duration-64;
                        units "microseconds";
                        description "Number of microseconds used by this group/core since start-up.";
                    }

                    ///nokia-state/state/system/cpu/is-is/cpu-usage
                    leaf cpu-usage {
                        type decimal64 {
                            range "0..100";
                            fraction-digits 2;
                        }
                        units "percent";
                        description "Relative amount of time used by this group/core since start-up.";
                    }

                    ///nokia-state/state/system/cpu/is-is/capacity-usage
                    leaf capacity-usage {
                        type decimal64 {
                            range "0..100";
                            fraction-digits 2;
                        }
                        units "percent";
                        description "Relative amount of time used by the busiest task/core.";
                    }

                } // container is-is

                ///nokia-state/state/system/cpu/isa
                container isa {
                    description "Enter the isa context";

                    ///nokia-state/state/system/cpu/isa/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/isa/time-used
                    leaf time-used {
                        type types-sros:time-duration-64;
                        units "microseconds";
                        description "Number of microseconds used by this group/core since start-up.";
                    }

                    ///nokia-state/state/system/cpu/isa/cpu-usage
                    leaf cpu-usage {
                        type decimal64 {
                            range "0..100";
                            fraction-digits 2;
                        }
                        units "percent";
                        description "Relative amount of time used by this group/core since start-up.";
                    }

                    ///nokia-state/state/system/cpu/isa/capacity-usage
                    leaf capacity-usage {
                        type decimal64 {
                            range "0..100";
                            fraction-digits 2;
                        }
                        units "percent";
                        description "Relative amount of time used by the busiest task/core.";
                    }

                } // container isa

                ///nokia-state/state/system/cpu/ldp
                container ldp {
                    description "Enter the ldp context";

                    ///nokia-state/state/system/cpu/ldp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/ldp/time-used
                    leaf time-used {
                        type types-sros:time-duration-64;
                        units "microseconds";
                        description "Number of microseconds used by this group/core since start-up.";
                    }

                    ///nokia-state/state/system/cpu/ldp/cpu-usage
                    leaf cpu-usage {
                        type decimal64 {
                            range "0..100";
                            fraction-digits 2;
                        }
                        units "percent";
                        description "Relative amount of time used by this group/core since start-up.";
                    }

                    ///nokia-state/state/system/cpu/ldp/capacity-usage
                    leaf capacity-usage {
                        type decimal64 {
                            range "0..100";
                            fraction-digits 2;
                        }
                        units "percent";
                        description "Relative amount of time used by the busiest task/core.";
                    }

                } // container ldp

                ///nokia-state/state/system/cpu/logging
                container logging {
                    description "Enter the logging context";

                    ///nokia-state/state/system/cpu/logging/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/logging/time-used
                    leaf time-used {
                        type types-sros:time-duration-64;
                        units "microseconds";
                        description "Number of microseconds used by this group/core since start-up.";
                    }

                    ///nokia-state/state/system/cpu/logging/cpu-usage
                    leaf cpu-usage {
                        type decimal64 {
                            range "0..100";
                            fraction-digits 2;
                        }
                        units "percent";
                        description "Relative amount of time used by this group/core since start-up.";
                    }

                    ///nokia-state/state/system/cpu/logging/capacity-usage
                    leaf capacity-usage {
                        type decimal64 {
                            range "0..100";
                            fraction-digits 2;
                        }
                        units "percent";
                        description "Relative amount of time used by the busiest task/core.";
                    }

                } // container logging

                ///nokia-state/state/system/cpu/mbuf
                container mbuf {
                    description "Enter the mbuf context";

                    ///nokia-state/state/system/cpu/mbuf/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/mbuf/time-used
                    leaf time-used {
                        type types-sros:time-duration-64;
                        units "microseconds";
                        description "Number of microseconds used by this group/core since start-up.";
                    }

                    ///nokia-state/state/system/cpu/mbuf/cpu-usage
                    leaf cpu-usage {
                        type decimal64 {
                            range "0..100";
                            fraction-digits 2;
                        }
                        units "percent";
                        description "Relative amount of time used by this group/core since start-up.";
                    }

                    ///nokia-state/state/system/cpu/mbuf/capacity-usage
                    leaf capacity-usage {
                        type decimal64 {
                            range "0..100";
                            fraction-digits 2;
                        }
                        units "percent";
                        description "Relative amount of time used by the busiest task/core.";
                    }

                } // container mbuf

                ///nokia-state/state/system/cpu/mcs
                container mcs {
                    description "Enter the mcs context";

                    ///nokia-state/state/system/cpu/mcs/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/mcs/time-used
                    leaf time-used {
                        type types-sros:time-duration-64;
                        units "microseconds";
                        description "Number of microseconds used by this group/core since start-up.";
                    }

                    ///nokia-state/state/system/cpu/mcs/cpu-usage
                    leaf cpu-usage {
                        type decimal64 {
                            range "0..100";
                            fraction-digits 2;
                        }
                        units "percent";
                        description "Relative amount of time used by this group/core since start-up.";
                    }

                    ///nokia-state/state/system/cpu/mcs/capacity-usage
                    leaf capacity-usage {
                        type decimal64 {
                            range "0..100";
                            fraction-digits 2;
                        }
                        units "percent";
                        description "Relative amount of time used by the busiest task/core.";
                    }

                } // container mcs

                ///nokia-state/state/system/cpu/mpls-rsvp
                container mpls-rsvp {
                    description "Enter the mpls-rsvp context";

                    ///nokia-state/state/system/cpu/mpls-rsvp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/mpls-rsvp/time-used
                    leaf time-used {
                        type types-sros:time-duration-64;
                        units "microseconds";
                        description "Number of microseconds used by this group/core since start-up.";
                    }

                    ///nokia-state/state/system/cpu/mpls-rsvp/cpu-usage
                    leaf cpu-usage {
                        type decimal64 {
                            range "0..100";
                            fraction-digits 2;
                        }
                        units "percent";
                        description "Relative amount of time used by this group/core since start-up.";
                    }

                    ///nokia-state/state/system/cpu/mpls-rsvp/capacity-usage
                    leaf capacity-usage {
                        type decimal64 {
                            range "0..100";
                            fraction-digits 2;
                        }
                        units "percent";
                        description "Relative amount of time used by the busiest task/core.";
                    }

                } // container mpls-rsvp

                ///nokia-state/state/system/cpu/mscp
                container mscp {
                    description "Enter the mscp context";

                    ///nokia-state/state/system/cpu/mscp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/mscp/time-used
                    leaf time-used {
                        type types-sros:time-duration-64;
                        units "microseconds";
                        description "Number of microseconds used by this group/core since start-up.";
                    }

                    ///nokia-state/state/system/cpu/mscp/cpu-usage
                    leaf cpu-usage {
                        type decimal64 {
                            range "0..100";
                            fraction-digits 2;
                        }
                        units "percent";
                        description "Relative amount of time used by this group/core since start-up.";
                    }

                    ///nokia-state/state/system/cpu/mscp/capacity-usage
                    leaf capacity-usage {
                        type decimal64 {
                            range "0..100";
                            fraction-digits 2;
                        }
                        units "percent";
                        description "Relative amount of time used by the busiest task/core.";
                    }

                } // container mscp

                ///nokia-state/state/system/cpu/msdp
                container msdp {
                    description "Enter the msdp context";

                    ///nokia-state/state/system/cpu/msdp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/msdp/time-used
                    leaf time-used {
                        type types-sros:time-duration-64;
                        units "microseconds";
                        description "Number of microseconds used by this group/core since start-up.";
                    }

                    ///nokia-state/state/system/cpu/msdp/cpu-usage
                    leaf cpu-usage {
                        type decimal64 {
                            range "0..100";
                            fraction-digits 2;
                        }
                        units "percent";
                        description "Relative amount of time used by this group/core since start-up.";
                    }

                    ///nokia-state/state/system/cpu/msdp/capacity-usage
                    leaf capacity-usage {
                        type decimal64 {
                            range "0..100";
                            fraction-digits 2;
                        }
                        units "percent";
                        description "Relative amount of time used by the busiest task/core.";
                    }

                } // container msdp

                ///nokia-state/state/system/cpu/management
                container management {
                    description "Enter the management context";

                    ///nokia-state/state/system/cpu/management/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/management/time-used
                    leaf time-used {
                        type types-sros:time-duration-64;
                        units "microseconds";
                        description "Number of microseconds used by this group/core since start-up.";
                    }

                    ///nokia-state/state/system/cpu/management/cpu-usage
                    leaf cpu-usage {
                        type decimal64 {
                            range "0..100";
                            fraction-digits 2;
                        }
                        units "percent";
                        description "Relative amount of time used by this group/core since start-up.";
                    }

                    ///nokia-state/state/system/cpu/management/capacity-usage
                    leaf capacity-usage {
                        type decimal64 {
                            range "0..100";
                            fraction-digits 2;
                        }
                        units "percent";
                        description "Relative amount of time used by the busiest task/core.";
                    }

                } // container management

                ///nokia-state/state/system/cpu/oam
                container oam {
                    description "Enter the oam context";

                    ///nokia-state/state/system/cpu/oam/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/oam/time-used
                    leaf time-used {
                        type types-sros:time-duration-64;
                        units "microseconds";
                        description "Number of microseconds used by this group/core since start-up.";
                    }

                    ///nokia-state/state/system/cpu/oam/cpu-usage
                    leaf cpu-usage {
                        type decimal64 {
                            range "0..100";
                            fraction-digits 2;
                        }
                        units "percent";
                        description "Relative amount of time used by this group/core since start-up.";
                    }

                    ///nokia-state/state/system/cpu/oam/capacity-usage
                    leaf capacity-usage {
                        type decimal64 {
                            range "0..100";
                            fraction-digits 2;
                        }
                        units "percent";
                        description "Relative amount of time used by the busiest task/core.";
                    }

                } // container oam

                ///nokia-state/state/system/cpu/ospf
                container ospf {
                    description "Enter the ospf context";

                    ///nokia-state/state/system/cpu/ospf/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/ospf/time-used
                    leaf time-used {
                        type types-sros:time-duration-64;
                        units "microseconds";
                        description "Number of microseconds used by this group/core since start-up.";
                    }

                    ///nokia-state/state/system/cpu/ospf/cpu-usage
                    leaf cpu-usage {
                        type decimal64 {
                            range "0..100";
                            fraction-digits 2;
                        }
                        units "percent";
                        description "Relative amount of time used by this group/core since start-up.";
                    }

                    ///nokia-state/state/system/cpu/ospf/capacity-usage
                    leaf capacity-usage {
                        type decimal64 {
                            range "0..100";
                            fraction-digits 2;
                        }
                        units "percent";
                        description "Relative amount of time used by the busiest task/core.";
                    }

                } // container ospf

                ///nokia-state/state/system/cpu/openflow
                container openflow {
                    description "Enter the openflow context";

                    ///nokia-state/state/system/cpu/openflow/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/openflow/time-used
                    leaf time-used {
                        type types-sros:time-duration-64;
                        units "microseconds";
                        description "Number of microseconds used by this group/core since start-up.";
                    }

                    ///nokia-state/state/system/cpu/openflow/cpu-usage
                    leaf cpu-usage {
                        type decimal64 {
                            range "0..100";
                            fraction-digits 2;
                        }
                        units "percent";
                        description "Relative amount of time used by this group/core since start-up.";
                    }

                    ///nokia-state/state/system/cpu/openflow/capacity-usage
                    leaf capacity-usage {
                        type decimal64 {
                            range "0..100";
                            fraction-digits 2;
                        }
                        units "percent";
                        description "Relative amount of time used by the busiest task/core.";
                    }

                } // container openflow

                ///nokia-state/state/system/cpu/pim-l2mcast
                container pim-l2mcast {
                    description "Enter the pim-l2mcast context";

                    ///nokia-state/state/system/cpu/pim-l2mcast/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/pim-l2mcast/time-used
                    leaf time-used {
                        type types-sros:time-duration-64;
                        units "microseconds";
                        description "Number of microseconds used by this group/core since start-up.";
                    }

                    ///nokia-state/state/system/cpu/pim-l2mcast/cpu-usage
                    leaf cpu-usage {
                        type decimal64 {
                            range "0..100";
                            fraction-digits 2;
                        }
                        units "percent";
                        description "Relative amount of time used by this group/core since start-up.";
                    }

                    ///nokia-state/state/system/cpu/pim-l2mcast/capacity-usage
                    leaf capacity-usage {
                        type decimal64 {
                            range "0..100";
                            fraction-digits 2;
                        }
                        units "percent";
                        description "Relative amount of time used by the busiest task/core.";
                    }

                } // container pim-l2mcast

                ///nokia-state/state/system/cpu/pki
                container pki {
                    description "Enter the pki context";

                    ///nokia-state/state/system/cpu/pki/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/pki/time-used
                    leaf time-used {
                        type types-sros:time-duration-64;
                        units "microseconds";
                        description "Number of microseconds used by this group/core since start-up.";
                    }

                    ///nokia-state/state/system/cpu/pki/cpu-usage
                    leaf cpu-usage {
                        type decimal64 {
                            range "0..100";
                            fraction-digits 2;
                        }
                        units "percent";
                        description "Relative amount of time used by this group/core since start-up.";
                    }

                    ///nokia-state/state/system/cpu/pki/capacity-usage
                    leaf capacity-usage {
                        type decimal64 {
                            range "0..100";
                            fraction-digits 2;
                        }
                        units "percent";
                        description "Relative amount of time used by the busiest task/core.";
                    }

                } // container pki

                ///nokia-state/state/system/cpu/ptp
                container ptp {
                    description "Enter the ptp context";

                    ///nokia-state/state/system/cpu/ptp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/ptp/time-used
                    leaf time-used {
                        type types-sros:time-duration-64;
                        units "microseconds";
                        description "Number of microseconds used by this group/core since start-up.";
                    }

                    ///nokia-state/state/system/cpu/ptp/cpu-usage
                    leaf cpu-usage {
                        type decimal64 {
                            range "0..100";
                            fraction-digits 2;
                        }
                        units "percent";
                        description "Relative amount of time used by this group/core since start-up.";
                    }

                    ///nokia-state/state/system/cpu/ptp/capacity-usage
                    leaf capacity-usage {
                        type decimal64 {
                            range "0..100";
                            fraction-digits 2;
                        }
                        units "percent";
                        description "Relative amount of time used by the busiest task/core.";
                    }

                } // container ptp

                ///nokia-state/state/system/cpu/rip
                container rip {
                    description "Enter the rip context";

                    ///nokia-state/state/system/cpu/rip/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/rip/time-used
                    leaf time-used {
                        type types-sros:time-duration-64;
                        units "microseconds";
                        description "Number of microseconds used by this group/core since start-up.";
                    }

                    ///nokia-state/state/system/cpu/rip/cpu-usage
                    leaf cpu-usage {
                        type decimal64 {
                            range "0..100";
                            fraction-digits 2;
                        }
                        units "percent";
                        description "Relative amount of time used by this group/core since start-up.";
                    }

                    ///nokia-state/state/system/cpu/rip/capacity-usage
                    leaf capacity-usage {
                        type decimal64 {
                            range "0..100";
                            fraction-digits 2;
                        }
                        units "percent";
                        description "Relative amount of time used by the busiest task/core.";
                    }

                } // container rip

                ///nokia-state/state/system/cpu/rtm-policies
                container rtm-policies {
                    description "Enter the rtm-policies context";

                    ///nokia-state/state/system/cpu/rtm-policies/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/rtm-policies/time-used
                    leaf time-used {
                        type types-sros:time-duration-64;
                        units "microseconds";
                        description "Number of microseconds used by this group/core since start-up.";
                    }

                    ///nokia-state/state/system/cpu/rtm-policies/cpu-usage
                    leaf cpu-usage {
                        type decimal64 {
                            range "0..100";
                            fraction-digits 2;
                        }
                        units "percent";
                        description "Relative amount of time used by this group/core since start-up.";
                    }

                    ///nokia-state/state/system/cpu/rtm-policies/capacity-usage
                    leaf capacity-usage {
                        type decimal64 {
                            range "0..100";
                            fraction-digits 2;
                        }
                        units "percent";
                        description "Relative amount of time used by the busiest task/core.";
                    }

                } // container rtm-policies

                ///nokia-state/state/system/cpu/redundancy
                container redundancy {
                    description "Enter the redundancy context";

                    ///nokia-state/state/system/cpu/redundancy/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/redundancy/time-used
                    leaf time-used {
                        type types-sros:time-duration-64;
                        units "microseconds";
                        description "Number of microseconds used by this group/core since start-up.";
                    }

                    ///nokia-state/state/system/cpu/redundancy/cpu-usage
                    leaf cpu-usage {
                        type decimal64 {
                            range "0..100";
                            fraction-digits 2;
                        }
                        units "percent";
                        description "Relative amount of time used by this group/core since start-up.";
                    }

                    ///nokia-state/state/system/cpu/redundancy/capacity-usage
                    leaf capacity-usage {
                        type decimal64 {
                            range "0..100";
                            fraction-digits 2;
                        }
                        units "percent";
                        description "Relative amount of time used by the busiest task/core.";
                    }

                } // container redundancy

                ///nokia-state/state/system/cpu/sim
                container sim {
                    description "Enter the sim context";

                    ///nokia-state/state/system/cpu/sim/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/sim/time-used
                    leaf time-used {
                        type types-sros:time-duration-64;
                        units "microseconds";
                        description "Number of microseconds used by this group/core since start-up.";
                    }

                    ///nokia-state/state/system/cpu/sim/cpu-usage
                    leaf cpu-usage {
                        type decimal64 {
                            range "0..100";
                            fraction-digits 2;
                        }
                        units "percent";
                        description "Relative amount of time used by this group/core since start-up.";
                    }

                    ///nokia-state/state/system/cpu/sim/capacity-usage
                    leaf capacity-usage {
                        type decimal64 {
                            range "0..100";
                            fraction-digits 2;
                        }
                        units "percent";
                        description "Relative amount of time used by the busiest task/core.";
                    }

                } // container sim

                ///nokia-state/state/system/cpu/snmp-daemon
                container snmp-daemon {
                    description "Enter the snmp-daemon context";

                    ///nokia-state/state/system/cpu/snmp-daemon/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/snmp-daemon/time-used
                    leaf time-used {
                        type types-sros:time-duration-64;
                        units "microseconds";
                        description "Number of microseconds used by this group/core since start-up.";
                    }

                    ///nokia-state/state/system/cpu/snmp-daemon/cpu-usage
                    leaf cpu-usage {
                        type decimal64 {
                            range "0..100";
                            fraction-digits 2;
                        }
                        units "percent";
                        description "Relative amount of time used by this group/core since start-up.";
                    }

                    ///nokia-state/state/system/cpu/snmp-daemon/capacity-usage
                    leaf capacity-usage {
                        type decimal64 {
                            range "0..100";
                            fraction-digits 2;
                        }
                        units "percent";
                        description "Relative amount of time used by the busiest task/core.";
                    }

                } // container snmp-daemon

                ///nokia-state/state/system/cpu/security
                container security {
                    description "Enter the security context";

                    ///nokia-state/state/system/cpu/security/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/security/time-used
                    leaf time-used {
                        type types-sros:time-duration-64;
                        units "microseconds";
                        description "Number of microseconds used by this group/core since start-up.";
                    }

                    ///nokia-state/state/system/cpu/security/cpu-usage
                    leaf cpu-usage {
                        type decimal64 {
                            range "0..100";
                            fraction-digits 2;
                        }
                        units "percent";
                        description "Relative amount of time used by this group/core since start-up.";
                    }

                    ///nokia-state/state/system/cpu/security/capacity-usage
                    leaf capacity-usage {
                        type decimal64 {
                            range "0..100";
                            fraction-digits 2;
                        }
                        units "percent";
                        description "Relative amount of time used by the busiest task/core.";
                    }

                } // container security

                ///nokia-state/state/system/cpu/services
                container services {
                    description "Enter the services context";

                    ///nokia-state/state/system/cpu/services/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/services/time-used
                    leaf time-used {
                        type types-sros:time-duration-64;
                        units "microseconds";
                        description "Number of microseconds used by this group/core since start-up.";
                    }

                    ///nokia-state/state/system/cpu/services/cpu-usage
                    leaf cpu-usage {
                        type decimal64 {
                            range "0..100";
                            fraction-digits 2;
                        }
                        units "percent";
                        description "Relative amount of time used by this group/core since start-up.";
                    }

                    ///nokia-state/state/system/cpu/services/capacity-usage
                    leaf capacity-usage {
                        type decimal64 {
                            range "0..100";
                            fraction-digits 2;
                        }
                        units "percent";
                        description "Relative amount of time used by the busiest task/core.";
                    }

                } // container services

                ///nokia-state/state/system/cpu/stats
                container stats {
                    description "Enter the stats context";

                    ///nokia-state/state/system/cpu/stats/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/stats/time-used
                    leaf time-used {
                        type types-sros:time-duration-64;
                        units "microseconds";
                        description "Number of microseconds used by this group/core since start-up.";
                    }

                    ///nokia-state/state/system/cpu/stats/cpu-usage
                    leaf cpu-usage {
                        type decimal64 {
                            range "0..100";
                            fraction-digits 2;
                        }
                        units "percent";
                        description "Relative amount of time used by this group/core since start-up.";
                    }

                    ///nokia-state/state/system/cpu/stats/capacity-usage
                    leaf capacity-usage {
                        type decimal64 {
                            range "0..100";
                            fraction-digits 2;
                        }
                        units "percent";
                        description "Relative amount of time used by the busiest task/core.";
                    }

                } // container stats

                ///nokia-state/state/system/cpu/stats-extended
                container stats-extended {
                    description "Enter the stats-extended context";

                    ///nokia-state/state/system/cpu/stats-extended/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/stats-extended/time-used
                    leaf time-used {
                        type types-sros:time-duration-64;
                        units "microseconds";
                        description "Number of microseconds used by this group/core since start-up.";
                    }

                    ///nokia-state/state/system/cpu/stats-extended/cpu-usage
                    leaf cpu-usage {
                        type decimal64 {
                            range "0..100";
                            fraction-digits 2;
                        }
                        units "percent";
                        description "Relative amount of time used by this group/core since start-up.";
                    }

                    ///nokia-state/state/system/cpu/stats-extended/capacity-usage
                    leaf capacity-usage {
                        type decimal64 {
                            range "0..100";
                            fraction-digits 2;
                        }
                        units "percent";
                        description "Relative amount of time used by the busiest task/core.";
                    }

                } // container stats-extended

                ///nokia-state/state/system/cpu/subscriber-mgmt
                container subscriber-mgmt {
                    description "Enter the subscriber-mgmt context";

                    ///nokia-state/state/system/cpu/subscriber-mgmt/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/subscriber-mgmt/time-used
                    leaf time-used {
                        type types-sros:time-duration-64;
                        units "microseconds";
                        description "Number of microseconds used by this group/core since start-up.";
                    }

                    ///nokia-state/state/system/cpu/subscriber-mgmt/cpu-usage
                    leaf cpu-usage {
                        type decimal64 {
                            range "0..100";
                            fraction-digits 2;
                        }
                        units "percent";
                        description "Relative amount of time used by this group/core since start-up.";
                    }

                    ///nokia-state/state/system/cpu/subscriber-mgmt/capacity-usage
                    leaf capacity-usage {
                        type decimal64 {
                            range "0..100";
                            fraction-digits 2;
                        }
                        units "percent";
                        description "Relative amount of time used by the busiest task/core.";
                    }

                } // container subscriber-mgmt

                ///nokia-state/state/system/cpu/system
                container system {
                    description "Enter the system context";

                    ///nokia-state/state/system/cpu/system/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/system/time-used
                    leaf time-used {
                        type types-sros:time-duration-64;
                        units "microseconds";
                        description "Number of microseconds used by this group/core since start-up.";
                    }

                    ///nokia-state/state/system/cpu/system/cpu-usage
                    leaf cpu-usage {
                        type decimal64 {
                            range "0..100";
                            fraction-digits 2;
                        }
                        units "percent";
                        description "Relative amount of time used by this group/core since start-up.";
                    }

                    ///nokia-state/state/system/cpu/system/capacity-usage
                    leaf capacity-usage {
                        type decimal64 {
                            range "0..100";
                            fraction-digits 2;
                        }
                        units "percent";
                        description "Relative amount of time used by the busiest task/core.";
                    }

                } // container system

                ///nokia-state/state/system/cpu/traffic-eng
                container traffic-eng {
                    description "Enter the traffic-eng context";

                    ///nokia-state/state/system/cpu/traffic-eng/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/traffic-eng/time-used
                    leaf time-used {
                        type types-sros:time-duration-64;
                        units "microseconds";
                        description "Number of microseconds used by this group/core since start-up.";
                    }

                    ///nokia-state/state/system/cpu/traffic-eng/cpu-usage
                    leaf cpu-usage {
                        type decimal64 {
                            range "0..100";
                            fraction-digits 2;
                        }
                        units "percent";
                        description "Relative amount of time used by this group/core since start-up.";
                    }

                    ///nokia-state/state/system/cpu/traffic-eng/capacity-usage
                    leaf capacity-usage {
                        type decimal64 {
                            range "0..100";
                            fraction-digits 2;
                        }
                        units "percent";
                        description "Relative amount of time used by the busiest task/core.";
                    }

                } // container traffic-eng

                ///nokia-state/state/system/cpu/tree-sid
                container tree-sid {
                    description "Enter the tree-sid context";

                    ///nokia-state/state/system/cpu/tree-sid/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/tree-sid/time-used
                    leaf time-used {
                        type types-sros:time-duration-64;
                        units "microseconds";
                        description "Number of microseconds used by this group/core since start-up.";
                    }

                    ///nokia-state/state/system/cpu/tree-sid/cpu-usage
                    leaf cpu-usage {
                        type decimal64 {
                            range "0..100";
                            fraction-digits 2;
                        }
                        units "percent";
                        description "Relative amount of time used by this group/core since start-up.";
                    }

                    ///nokia-state/state/system/cpu/tree-sid/capacity-usage
                    leaf capacity-usage {
                        type decimal64 {
                            range "0..100";
                            fraction-digits 2;
                        }
                        units "percent";
                        description "Relative amount of time used by the busiest task/core.";
                    }

                } // container tree-sid

                ///nokia-state/state/system/cpu/vrrp
                container vrrp {
                    description "Enter the vrrp context";

                    ///nokia-state/state/system/cpu/vrrp/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/vrrp/time-used
                    leaf time-used {
                        type types-sros:time-duration-64;
                        units "microseconds";
                        description "Number of microseconds used by this group/core since start-up.";
                    }

                    ///nokia-state/state/system/cpu/vrrp/cpu-usage
                    leaf cpu-usage {
                        type decimal64 {
                            range "0..100";
                            fraction-digits 2;
                        }
                        units "percent";
                        description "Relative amount of time used by this group/core since start-up.";
                    }

                    ///nokia-state/state/system/cpu/vrrp/capacity-usage
                    leaf capacity-usage {
                        type decimal64 {
                            range "0..100";
                            fraction-digits 2;
                        }
                        units "percent";
                        description "Relative amount of time used by the busiest task/core.";
                    }

                } // container vrrp

                ///nokia-state/state/system/cpu/web-redirect
                container web-redirect {
                    description "Enter the web-redirect context";

                    ///nokia-state/state/system/cpu/web-redirect/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/web-redirect/time-used
                    leaf time-used {
                        type types-sros:time-duration-64;
                        units "microseconds";
                        description "Number of microseconds used by this group/core since start-up.";
                    }

                    ///nokia-state/state/system/cpu/web-redirect/cpu-usage
                    leaf cpu-usage {
                        type decimal64 {
                            range "0..100";
                            fraction-digits 2;
                        }
                        units "percent";
                        description "Relative amount of time used by this group/core since start-up.";
                    }

                    ///nokia-state/state/system/cpu/web-redirect/capacity-usage
                    leaf capacity-usage {
                        type decimal64 {
                            range "0..100";
                            fraction-digits 2;
                        }
                        units "percent";
                        description "Relative amount of time used by the busiest task/core.";
                    }

                } // container web-redirect

                ///nokia-state/state/system/cpu/hqos-algorithm
                container hqos-algorithm {
                    description "Enter the hqos-algorithm context";

                    ///nokia-state/state/system/cpu/hqos-algorithm/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/hqos-algorithm/time-used
                    leaf time-used {
                        type types-sros:time-duration-64;
                        units "microseconds";
                        description "Number of microseconds used by this group/core since start-up.";
                    }

                    ///nokia-state/state/system/cpu/hqos-algorithm/cpu-usage
                    leaf cpu-usage {
                        type decimal64 {
                            range "0..100";
                            fraction-digits 2;
                        }
                        units "percent";
                        description "Relative amount of time used by this group/core since start-up.";
                    }

                    ///nokia-state/state/system/cpu/hqos-algorithm/capacity-usage
                    leaf capacity-usage {
                        type decimal64 {
                            range "0..100";
                            fraction-digits 2;
                        }
                        units "percent";
                        description "Relative amount of time used by the busiest task/core.";
                    }

                } // container hqos-algorithm

                ///nokia-state/state/system/cpu/hqos-statistics
                container hqos-statistics {
                    description "Enter the hqos-statistics context";

                    ///nokia-state/state/system/cpu/hqos-statistics/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/hqos-statistics/time-used
                    leaf time-used {
                        type types-sros:time-duration-64;
                        units "microseconds";
                        description "Number of microseconds used by this group/core since start-up.";
                    }

                    ///nokia-state/state/system/cpu/hqos-statistics/cpu-usage
                    leaf cpu-usage {
                        type decimal64 {
                            range "0..100";
                            fraction-digits 2;
                        }
                        units "percent";
                        description "Relative amount of time used by this group/core since start-up.";
                    }

                    ///nokia-state/state/system/cpu/hqos-statistics/capacity-usage
                    leaf capacity-usage {
                        type decimal64 {
                            range "0..100";
                            fraction-digits 2;
                        }
                        units "percent";
                        description "Relative amount of time used by the busiest task/core.";
                    }

                } // container hqos-statistics

                ///nokia-state/state/system/cpu/iom
                container iom {
                    description "Enter the iom context";

                    ///nokia-state/state/system/cpu/iom/cpu-time
                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    ///nokia-state/state/system/cpu/iom/time-used
                    leaf time-used {
                        type types-sros:time-duration-64;
                        units "microseconds";
                        description "Number of microseconds used by this group/core since start-up.";
                    }

                    ///nokia-state/state/system/cpu/iom/cpu-usage
                    leaf cpu-usage {
                        type decimal64 {
                            range "0..100";
                            fraction-digits 2;
                        }
                        units "percent";
                        description "Relative amount of time used by this group/core since start-up.";
                    }

                    ///nokia-state/state/system/cpu/iom/capacity-usage
                    leaf capacity-usage {
                        type decimal64 {
                            range "0..100";
                            fraction-digits 2;
                        }
                        units "percent";
                        description "Relative amount of time used by the busiest task/core.";
                    }

                } // container iom

                ///nokia-state/state/system/cpu/summary
                container summary {
                    description "Enter the summary context";

                    ///nokia-state/state/system/cpu/summary/total
                    container total {
                        description "Enter the total context";

                        ///nokia-state/state/system/cpu/summary/total/cpu-time
                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        ///nokia-state/state/system/cpu/summary/total/time-used
                        leaf time-used {
                            type types-sros:time-duration-64;
                            units "microseconds";
                            description "Number of microseconds used by this group/core since start-up.";
                        }

                        ///nokia-state/state/system/cpu/summary/total/cpu-usage
                        leaf cpu-usage {
                            type decimal64 {
                                range "0..100";
                                fraction-digits 2;
                            }
                            units "percent";
                            description "Relative amount of time used by this group/core since start-up.";
                        }

                    } // container total

                    ///nokia-state/state/system/cpu/summary/idle
                    container idle {
                        description "Enter the idle context";

                        ///nokia-state/state/system/cpu/summary/idle/cpu-time
                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        ///nokia-state/state/system/cpu/summary/idle/time-used
                        leaf time-used {
                            type types-sros:time-duration-64;
                            units "microseconds";
                            description "Number of microseconds used by this group/core since start-up.";
                        }

                        ///nokia-state/state/system/cpu/summary/idle/cpu-usage
                        leaf cpu-usage {
                            type decimal64 {
                                range "0..100";
                                fraction-digits 2;
                            }
                            units "percent";
                            description "Relative amount of time used by this group/core since start-up.";
                        }

                    } // container idle

                    ///nokia-state/state/system/cpu/summary/usage
                    container usage {
                        description "Enter the usage context";

                        ///nokia-state/state/system/cpu/summary/usage/cpu-time
                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        ///nokia-state/state/system/cpu/summary/usage/time-used
                        leaf time-used {
                            type types-sros:time-duration-64;
                            units "microseconds";
                            description "Number of microseconds used by this group/core since start-up.";
                        }

                        ///nokia-state/state/system/cpu/summary/usage/cpu-usage
                        leaf cpu-usage {
                            type decimal64 {
                                range "0..100";
                                fraction-digits 2;
                            }
                            units "percent";
                            description "Relative amount of time used by this group/core since start-up.";
                        }

                    } // container usage

                    ///nokia-state/state/system/cpu/summary/busiest-core-utilization
                    container busiest-core-utilization {
                        description "Enter the busiest-core-utilization context";

                        ///nokia-state/state/system/cpu/summary/busiest-core-utilization/cpu-time
                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        ///nokia-state/state/system/cpu/summary/busiest-core-utilization/time-used
                        leaf time-used {
                            type types-sros:time-duration-64;
                            units "microseconds";
                            description "Number of microseconds used by this group/core since start-up.";
                        }

                        ///nokia-state/state/system/cpu/summary/busiest-core-utilization/cpu-usage
                        leaf cpu-usage {
                            type decimal64 {
                                range "0..100";
                                fraction-digits 2;
                            }
                            units "percent";
                            description "Relative amount of time used by this group/core since start-up.";
                        }

                    } // container busiest-core-utilization

                } // container summary

            } // list cpu

            ///nokia-state/state/system/memory-pools
            container memory-pools {
                description "Enter the memory-pools context";

                ///nokia-state/state/system/memory-pools/bfd
                container bfd {
                    description "Enter the bfd context";

                    ///nokia-state/state/system/memory-pools/bfd/max-allowed
                    leaf max-allowed {
                        type uint64 {
                            range "1..max";
                        }
                        units "bytes";
                        description "Maximum allowed amount of memory that can be allocated for a group.";
                    }

                    ///nokia-state/state/system/memory-pools/bfd/current-size
                    leaf current-size {
                        type uint64 {
                            range "0..max";
                        }
                        units "bytes";
                        description "Current amount of allocated memory for a group.";
                    }

                    ///nokia-state/state/system/memory-pools/bfd/max-so-far
                    leaf max-so-far {
                        type uint64 {
                            range "0..max";
                        }
                        units "bytes";
                        description "The highest amount of allocated memory for a group.";
                    }

                    ///nokia-state/state/system/memory-pools/bfd/in-use
                    leaf in-use {
                        type uint64 {
                            range "0..max";
                        }
                        units "bytes";
                        description "Amount of memory used by group.";
                    }

                } // container bfd

                ///nokia-state/state/system/memory-pools/bgp
                container bgp {
                    description "Enter the bgp context";

                    ///nokia-state/state/system/memory-pools/bgp/max-allowed
                    leaf max-allowed {
                        type uint64 {
                            range "1..max";
                        }
                        units "bytes";
                        description "Maximum allowed amount of memory that can be allocated for a group.";
                    }

                    ///nokia-state/state/system/memory-pools/bgp/current-size
                    leaf current-size {
                        type uint64 {
                            range "0..max";
                        }
                        units "bytes";
                        description "Current amount of allocated memory for a group.";
                    }

                    ///nokia-state/state/system/memory-pools/bgp/max-so-far
                    leaf max-so-far {
                        type uint64 {
                            range "0..max";
                        }
                        units "bytes";
                        description "The highest amount of allocated memory for a group.";
                    }

                    ///nokia-state/state/system/memory-pools/bgp/in-use
                    leaf in-use {
                        type uint64 {
                            range "0..max";
                        }
                        units "bytes";
                        description "Amount of memory used by group.";
                    }

                } // container bgp

                ///nokia-state/state/system/memory-pools/bgp-pe-ce
                container bgp-pe-ce {
                    description "Enter the bgp-pe-ce context";

                    ///nokia-state/state/system/memory-pools/bgp-pe-ce/max-allowed
                    leaf max-allowed {
                        type uint64 {
                            range "1..max";
                        }
                        units "bytes";
                        description "Maximum allowed amount of memory that can be allocated for a group.";
                    }

                    ///nokia-state/state/system/memory-pools/bgp-pe-ce/current-size
                    leaf current-size {
                        type uint64 {
                            range "0..max";
                        }
                        units "bytes";
                        description "Current amount of allocated memory for a group.";
                    }

                    ///nokia-state/state/system/memory-pools/bgp-pe-ce/max-so-far
                    leaf max-so-far {
                        type uint64 {
                            range "0..max";
                        }
                        units "bytes";
                        description "The highest amount of allocated memory for a group.";
                    }

                    ///nokia-state/state/system/memory-pools/bgp-pe-ce/in-use
                    leaf in-use {
                        type uint64 {
                            range "0..max";
                        }
                        units "bytes";
                        description "Amount of memory used by group.";
                    }

                } // container bgp-pe-ce

                ///nokia-state/state/system/memory-pools/bier
                container bier {
                    description "Enter the bier context";

                    ///nokia-state/state/system/memory-pools/bier/max-allowed
                    leaf max-allowed {
                        type uint64 {
                            range "1..max";
                        }
                        units "bytes";
                        description "Maximum allowed amount of memory that can be allocated for a group.";
                    }

                    ///nokia-state/state/system/memory-pools/bier/current-size
                    leaf current-size {
                        type uint64 {
                            range "0..max";
                        }
                        units "bytes";
                        description "Current amount of allocated memory for a group.";
                    }

                    ///nokia-state/state/system/memory-pools/bier/max-so-far
                    leaf max-so-far {
                        type uint64 {
                            range "0..max";
                        }
                        units "bytes";
                        description "The highest amount of allocated memory for a group.";
                    }

                    ///nokia-state/state/system/memory-pools/bier/in-use
                    leaf in-use {
                        type uint64 {
                            range "0..max";
                        }
                        units "bytes";
                        description "Amount of memory used by group.";
                    }

                } // container bier

                ///nokia-state/state/system/memory-pools/calltrace
                container calltrace {
                    description "Enter the calltrace context";

                    ///nokia-state/state/system/memory-pools/calltrace/max-allowed
                    leaf max-allowed {
                        type uint64 {
                            range "1..max";
                        }
                        units "bytes";
                        description "Maximum allowed amount of memory that can be allocated for a group.";
                    }

                    ///nokia-state/state/system/memory-pools/calltrace/current-size
                    leaf current-size {
                        type uint64 {
                            range "0..max";
                        }
                        units "bytes";
                        description "Current amount of allocated memory for a group.";
                    }

                    ///nokia-state/state/system/memory-pools/calltrace/max-so-far
                    leaf max-so-far {
                        type uint64 {
                            range "0..max";
                        }
                        units "bytes";
                        description "The highest amount of allocated memory for a group.";
                    }

                    ///nokia-state/state/system/memory-pools/calltrace/in-use
                    leaf in-use {
                        type uint64 {
                            range "0..max";
                        }
                        units "bytes";
                        description "Amount of memory used by group.";
                    }

                } // container calltrace

                ///nokia-state/state/system/memory-pools/cflowd
                container cflowd {
                    description "Enter the cflowd context";

                    ///nokia-state/state/system/memory-pools/cflowd/max-allowed
                    leaf max-allowed {
                        type uint64 {
                            range "1..max";
                        }
                        units "bytes";
                        description "Maximum allowed amount of memory that can be allocated for a group.";
                    }

                    ///nokia-state/state/system/memory-pools/cflowd/current-size
                    leaf current-size {
                        type uint64 {
                            range "0..max";
                        }
                        units "bytes";
                        description "Current amount of allocated memory for a group.";
                    }

                    ///nokia-state/state/system/memory-pools/cflowd/max-so-far
                    leaf max-so-far {
                        type uint64 {
                            range "0..max";
                        }
                        units "bytes";
                        description "The highest amount of allocated memory for a group.";
                    }

                    ///nokia-state/state/system/memory-pools/cflowd/in-use
                    leaf in-use {
                        type uint64 {
                            range "0..max";
                        }
                        units "bytes";
                        description "Amount of memory used by group.";
                    }

                } // container cflowd

                ///nokia-state/state/system/memory-pools/cards-and-ports
                container cards-and-ports {
                    description "Enter the cards-and-ports context";

                    ///nokia-state/state/system/memory-pools/cards-and-ports/max-allowed
                    leaf max-allowed {
                        type uint64 {
                            range "1..max";
                        }
                        units "bytes";
                        description "Maximum allowed amount of memory that can be allocated for a group.";
                    }

                    ///nokia-state/state/system/memory-pools/cards-and-ports/current-size
                    leaf current-size {
                        type uint64 {
                            range "0..max";
                        }
                        units "bytes";
                        description "Current amount of allocated memory for a group.";
                    }

                    ///nokia-state/state/system/memory-pools/cards-and-ports/max-so-far
                    leaf max-so-far {
                        type uint64 {
                            range "0..max";
                        }
                        units "bytes";
                        description "The highest amount of allocated memory for a group.";
                    }

                    ///nokia-state/state/system/memory-pools/cards-and-ports/in-use
                    leaf in-use {
                        type uint64 {
                            range "0..max";
                        }
                        units "bytes";
                        description "Amount of memory used by group.";
                    }

                } // container cards-and-ports

                ///nokia-state/state/system/memory-pools/dhcp-server
                container dhcp-server {
                    description "Enter the dhcp-server context";

                    ///nokia-state/state/system/memory-pools/dhcp-server/max-allowed
                    leaf max-allowed {
                        type uint64 {
                            range "1..max";
                        }
                        units "bytes";
                        description "Maximum allowed amount of memory that can be allocated for a group.";
                    }

                    ///nokia-state/state/system/memory-pools/dhcp-server/current-size
                    leaf current-size {
                        type uint64 {
                            range "0..max";
                        }
                        units "bytes";
                        description "Current amount of allocated memory for a group.";
                    }

                    ///nokia-state/state/system/memory-pools/dhcp-server/max-so-far
                    leaf max-so-far {
                        type uint64 {
                            range "0..max";
                        }
                        units "bytes";
                        description "The highest amount of allocated memory for a group.";
                    }

                    ///nokia-state/state/system/memory-pools/dhcp-server/in-use
                    leaf in-use {
                        type uint64 {
                            range "0..max";
                        }
                        units "bytes";
                        description "Amount of memory used by group.";
                    }

                } // container dhcp-server

                ///nokia-state/state/system/memory-pools/eth-cfm
                container eth-cfm {
                    description "Enter the eth-cfm context";

                    ///nokia-state/state/system/memory-pools/eth-cfm/max-allowed
                    leaf max-allowed {
                        type uint64 {
                            range "1..max";
                        }
                        units "bytes";
                        description "Maximum allowed amount of memory that can be allocated for a group.";
                    }

                    ///nokia-state/state/system/memory-pools/eth-cfm/current-size
                    leaf current-size {
                        type uint64 {
                            range "0..max";
                        }
                        units "bytes";
                        description "Current amount of allocated memory for a group.";
                    }

                    ///nokia-state/state/system/memory-pools/eth-cfm/max-so-far
                    leaf max-so-far {
                        type uint64 {
                            range "0..max";
                        }
                        units "bytes";
                        description "The highest amount of allocated memory for a group.";
                    }

                    ///nokia-state/state/system/memory-pools/eth-cfm/in-use
                    leaf in-use {
                        type uint64 {
                            range "0..max";
                        }
                        units "bytes";
                        description "Amount of memory used by group.";
                    }

                } // container eth-cfm

                ///nokia-state/state/system/memory-pools/fastpath
                container fastpath {
                    description "Enter the fastpath context";

                    ///nokia-state/state/system/memory-pools/fastpath/max-allowed
                    leaf max-allowed {
                        type uint64 {
                            range "1..max";
                        }
                        units "bytes";
                        description "Maximum allowed amount of memory that can be allocated for a group.";
                    }

                    ///nokia-state/state/system/memory-pools/fastpath/current-size
                    leaf current-size {
                        type uint64 {
                            range "0..max";
                        }
                        units "bytes";
                        description "Current amount of allocated memory for a group.";
                    }

                    ///nokia-state/state/system/memory-pools/fastpath/max-so-far
                    leaf max-so-far {
                        type uint64 {
                            range "0..max";
                        }
                        units "bytes";
                        description "The highest amount of allocated memory for a group.";
                    }

                    ///nokia-state/state/system/memory-pools/fastpath/in-use
                    leaf in-use {
                        type uint64 {
                            range "0..max";
                        }
                        units "bytes";
                        description "Amount of memory used by group.";
                    }

                } // container fastpath

                ///nokia-state/state/system/memory-pools/hqos-algorithm
                container hqos-algorithm {
                    description "Enter the hqos-algorithm context";

                    ///nokia-state/state/system/memory-pools/hqos-algorithm/max-allowed
                    leaf max-allowed {
                        type uint64 {
                            range "1..max";
                        }
                        units "bytes";
                        description "Maximum allowed amount of memory that can be allocated for a group.";
                    }

                    ///nokia-state/state/system/memory-pools/hqos-algorithm/current-size
                    leaf current-size {
                        type uint64 {
                            range "0..max";
                        }
                        units "bytes";
                        description "Current amount of allocated memory for a group.";
                    }

                    ///nokia-state/state/system/memory-pools/hqos-algorithm/max-so-far
                    leaf max-so-far {
                        type uint64 {
                            range "0..max";
                        }
                        units "bytes";
                        description "The highest amount of allocated memory for a group.";
                    }

                    ///nokia-state/state/system/memory-pools/hqos-algorithm/in-use
                    leaf in-use {
                        type uint64 {
                            range "0..max";
                        }
                        units "bytes";
                        description "Amount of memory used by group.";
                    }

                } // container hqos-algorithm

                ///nokia-state/state/system/memory-pools/hqos-statistics
                container hqos-statistics {
                    description "Enter the hqos-statistics context";

                    ///nokia-state/state/system/memory-pools/hqos-statistics/max-allowed
                    leaf max-allowed {
                        type uint64 {
                            range "1..max";
                        }
                        units "bytes";
                        description "Maximum allowed amount of memory that can be allocated for a group.";
                    }

                    ///nokia-state/state/system/memory-pools/hqos-statistics/current-size
                    leaf current-size {
                        type uint64 {
                            range "0..max";
                        }
                        units "bytes";
                        description "Current amount of allocated memory for a group.";
                    }

                    ///nokia-state/state/system/memory-pools/hqos-statistics/max-so-far
                    leaf max-so-far {
                        type uint64 {
                            range "0..max";
                        }
                        units "bytes";
                        description "The highest amount of allocated memory for a group.";
                    }

                    ///nokia-state/state/system/memory-pools/hqos-statistics/in-use
                    leaf in-use {
                        type uint64 {
                            range "0..max";
                        }
                        units "bytes";
                        description "Amount of memory used by group.";
                    }

                } // container hqos-statistics

                ///nokia-state/state/system/memory-pools/icc
                container icc {
                    description "Enter the icc context";

                    ///nokia-state/state/system/memory-pools/icc/max-allowed
                    leaf max-allowed {
                        type uint64 {
                            range "1..max";
                        }
                        units "bytes";
                        description "Maximum allowed amount of memory that can be allocated for a group.";
                    }

                    ///nokia-state/state/system/memory-pools/icc/current-size
                    leaf current-size {
                        type uint64 {
                            range "0..max";
                        }
                        units "bytes";
                        description "Current amount of allocated memory for a group.";
                    }

                    ///nokia-state/state/system/memory-pools/icc/max-so-far
                    leaf max-so-far {
                        type uint64 {
                            range "0..max";
                        }
                        units "bytes";
                        description "The highest amount of allocated memory for a group.";
                    }

                    ///nokia-state/state/system/memory-pools/icc/in-use
                    leaf in-use {
                        type uint64 {
                            range "0..max";
                        }
                        units "bytes";
                        description "Amount of memory used by group.";
                    }

                } // container icc

                ///nokia-state/state/system/memory-pools/igmp-mld
                container igmp-mld {
                    description "Enter the igmp-mld context";

                    ///nokia-state/state/system/memory-pools/igmp-mld/max-allowed
                    leaf max-allowed {
                        type uint64 {
                            range "1..max";
                        }
                        units "bytes";
                        description "Maximum allowed amount of memory that can be allocated for a group.";
                    }

                    ///nokia-state/state/system/memory-pools/igmp-mld/current-size
                    leaf current-size {
                        type uint64 {
                            range "0..max";
                        }
                        units "bytes";
                        description "Current amount of allocated memory for a group.";
                    }

                    ///nokia-state/state/system/memory-pools/igmp-mld/max-so-far
                    leaf max-so-far {
                        type uint64 {
                            range "0..max";
                        }
                        units "bytes";
                        description "The highest amount of allocated memory for a group.";
                    }

                    ///nokia-state/state/system/memory-pools/igmp-mld/in-use
                    leaf in-use {
                        type uint64 {
                            range "0..max";
                        }
                        units "bytes";
                        description "Amount of memory used by group.";
                    }

                } // container igmp-mld

                ///nokia-state/state/system/memory-pools/imsi-db-appl
                container imsi-db-appl {
                    description "Enter the imsi-db-appl context";

                    ///nokia-state/state/system/memory-pools/imsi-db-appl/max-allowed
                    leaf max-allowed {
                        type uint64 {
                            range "1..max";
                        }
                        units "bytes";
                        description "Maximum allowed amount of memory that can be allocated for a group.";
                    }

                    ///nokia-state/state/system/memory-pools/imsi-db-appl/current-size
                    leaf current-size {
                        type uint64 {
                            range "0..max";
                        }
                        units "bytes";
                        description "Current amount of allocated memory for a group.";
                    }

                    ///nokia-state/state/system/memory-pools/imsi-db-appl/max-so-far
                    leaf max-so-far {
                        type uint64 {
                            range "0..max";
                        }
                        units "bytes";
                        description "The highest amount of allocated memory for a group.";
                    }

                    ///nokia-state/state/system/memory-pools/imsi-db-appl/in-use
                    leaf in-use {
                        type uint64 {
                            range "0..max";
                        }
                        units "bytes";
                        description "Amount of memory used by group.";
                    }

                } // container imsi-db-appl

                ///nokia-state/state/system/memory-pools/ip-stack
                container ip-stack {
                    description "Enter the ip-stack context";

                    ///nokia-state/state/system/memory-pools/ip-stack/max-allowed
                    leaf max-allowed {
                        type uint64 {
                            range "1..max";
                        }
                        units "bytes";
                        description "Maximum allowed amount of memory that can be allocated for a group.";
                    }

                    ///nokia-state/state/system/memory-pools/ip-stack/current-size
                    leaf current-size {
                        type uint64 {
                            range "0..max";
                        }
                        units "bytes";
                        description "Current amount of allocated memory for a group.";
                    }

                    ///nokia-state/state/system/memory-pools/ip-stack/max-so-far
                    leaf max-so-far {
                        type uint64 {
                            range "0..max";
                        }
                        units "bytes";
                        description "The highest amount of allocated memory for a group.";
                    }

                    ///nokia-state/state/system/memory-pools/ip-stack/in-use
                    leaf in-use {
                        type uint64 {
                            range "0..max";
                        }
                        units "bytes";
                        description "Amount of memory used by group.";
                    }

                } // container ip-stack

                ///nokia-state/state/system/memory-pools/is-is
                container is-is {
                    description "Enter the is-is context";

                    ///nokia-state/state/system/memory-pools/is-is/max-allowed
                    leaf max-allowed {
                        type uint64 {
                            range "1..max";
                        }
                        units "bytes";
                        description "Maximum allowed amount of memory that can be allocated for a group.";
                    }

                    ///nokia-state/state/system/memory-pools/is-is/current-size
                    leaf current-size {
                        type uint64 {
                            range "0..max";
                        }
                        units "bytes";
                        description "Current amount of allocated memory for a group.";
                    }

                    ///nokia-state/state/system/memory-pools/is-is/max-so-far
                    leaf max-so-far {
                        type uint64 {
                            range "0..max";
                        }
                        units "bytes";
                        description "The highest amount of allocated memory for a group.";
                    }

                    ///nokia-state/state/system/memory-pools/is-is/in-use
                    leaf in-use {
                        type uint64 {
                            range "0..max";
                        }
                        units "bytes";
                        description "Amount of memory used by group.";
                    }

                } // container is-is

                ///nokia-state/state/system/memory-pools/isa
                container isa {
                    description "Enter the isa context";

                    ///nokia-state/state/system/memory-pools/isa/max-allowed
                    leaf max-allowed {
                        type uint64 {
                            range "1..max";
                        }
                        units "bytes";
                        description "Maximum allowed amount of memory that can be allocated for a group.";
                    }

                    ///nokia-state/state/system/memory-pools/isa/current-size
                    leaf current-size {
                        type uint64 {
                            range "0..max";
                        }
                        units "bytes";
                        description "Current amount of allocated memory for a group.";
                    }

                    ///nokia-state/state/system/memory-pools/isa/max-so-far
                    leaf max-so-far {
                        type uint64 {
                            range "0..max";
                        }
                        units "bytes";
                        description "The highest amount of allocated memory for a group.";
                    }

                    ///nokia-state/state/system/memory-pools/isa/in-use
                    leaf in-use {
                        type uint64 {
                            range "0..max";
                        }
                        units "bytes";
                        description "Amount of memory used by group.";
                    }

                } // container isa

                ///nokia-state/state/system/memory-pools/ldp
                container ldp {
                    description "Enter the ldp context";

                    ///nokia-state/state/system/memory-pools/ldp/max-allowed
                    leaf max-allowed {
                        type uint64 {
                            range "1..max";
                        }
                        units "bytes";
                        description "Maximum allowed amount of memory that can be allocated for a group.";
                    }

                    ///nokia-state/state/system/memory-pools/ldp/current-size
                    leaf current-size {
                        type uint64 {
                            range "0..max";
                        }
                        units "bytes";
                        description "Current amount of allocated memory for a group.";
                    }

                    ///nokia-state/state/system/memory-pools/ldp/max-so-far
                    leaf max-so-far {
                        type uint64 {
                            range "0..max";
                        }
                        units "bytes";
                        description "The highest amount of allocated memory for a group.";
                    }

                    ///nokia-state/state/system/memory-pools/ldp/in-use
                    leaf in-use {
                        type uint64 {
                            range "0..max";
                        }
                        units "bytes";
                        description "Amount of memory used by group.";
                    }

                } // container ldp

                ///nokia-state/state/system/memory-pools/logging
                container logging {
                    description "Enter the logging context";

                    ///nokia-state/state/system/memory-pools/logging/max-allowed
                    leaf max-allowed {
                        type uint64 {
                            range "1..max";
                        }
                        units "bytes";
                        description "Maximum allowed amount of memory that can be allocated for a group.";
                    }

                    ///nokia-state/state/system/memory-pools/logging/current-size
                    leaf current-size {
                        type uint64 {
                            range "0..max";
                        }
                        units "bytes";
                        description "Current amount of allocated memory for a group.";
                    }

                    ///nokia-state/state/system/memory-pools/logging/max-so-far
                    leaf max-so-far {
                        type uint64 {
                            range "0..max";
                        }
                        units "bytes";
                        description "The highest amount of allocated memory for a group.";
                    }

                    ///nokia-state/state/system/memory-pools/logging/in-use
                    leaf in-use {
                        type uint64 {
                            range "0..max";
                        }
                        units "bytes";
                        description "Amount of memory used by group.";
                    }

                } // container logging

                ///nokia-state/state/system/memory-pools/mbuf
                container mbuf {
                    description "Enter the mbuf context";

                    ///nokia-state/state/system/memory-pools/mbuf/max-allowed
                    leaf max-allowed {
                        type uint64 {
                            range "1..max";
                        }
                        units "bytes";
                        description "Maximum allowed amount of memory that can be allocated for a group.";
                    }

                    ///nokia-state/state/system/memory-pools/mbuf/current-size
                    leaf current-size {
                        type uint64 {
                            range "0..max";
                        }
                        units "bytes";
                        description "Current amount of allocated memory for a group.";
                    }

                    ///nokia-state/state/system/memory-pools/mbuf/max-so-far
                    leaf max-so-far {
                        type uint64 {
                            range "0..max";
                        }
                        units "bytes";
                        description "The highest amount of allocated memory for a group.";
                    }

                    ///nokia-state/state/system/memory-pools/mbuf/in-use
                    leaf in-use {
                        type uint64 {
                            range "0..max";
                        }
                        units "bytes";
                        description "Amount of memory used by group.";
                    }

                } // container mbuf

                ///nokia-state/state/system/memory-pools/mcs
                container mcs {
                    description "Enter the mcs context";

                    ///nokia-state/state/system/memory-pools/mcs/max-allowed
                    leaf max-allowed {
                        type uint64 {
                            range "1..max";
                        }
                        units "bytes";
                        description "Maximum allowed amount of memory that can be allocated for a group.";
                    }

                    ///nokia-state/state/system/memory-pools/mcs/current-size
                    leaf current-size {
                        type uint64 {
                            range "0..max";
                        }
                        units "bytes";
                        description "Current amount of allocated memory for a group.";
                    }

                    ///nokia-state/state/system/memory-pools/mcs/max-so-far
                    leaf max-so-far {
                        type uint64 {
                            range "0..max";
                        }
                        units "bytes";
                        description "The highest amount of allocated memory for a group.";
                    }

                    ///nokia-state/state/system/memory-pools/mcs/in-use
                    leaf in-use {
                        type uint64 {
                            range "0..max";
                        }
                        units "bytes";
                        description "Amount of memory used by group.";
                    }

                } // container mcs

                ///nokia-state/state/system/memory-pools/mpls-rsvp
                container mpls-rsvp {
                    description "Enter the mpls-rsvp context";

                    ///nokia-state/state/system/memory-pools/mpls-rsvp/max-allowed
                    leaf max-allowed {
                        type uint64 {
                            range "1..max";
                        }
                        units "bytes";
                        description "Maximum allowed amount of memory that can be allocated for a group.";
                    }

                    ///nokia-state/state/system/memory-pools/mpls-rsvp/current-size
                    leaf current-size {
                        type uint64 {
                            range "0..max";
                        }
                        units "bytes";
                        description "Current amount of allocated memory for a group.";
                    }

                    ///nokia-state/state/system/memory-pools/mpls-rsvp/max-so-far
                    leaf max-so-far {
                        type uint64 {
                            range "0..max";
                        }
                        units "bytes";
                        description "The highest amount of allocated memory for a group.";
                    }

                    ///nokia-state/state/system/memory-pools/mpls-rsvp/in-use
                    leaf in-use {
                        type uint64 {
                            range "0..max";
                        }
                        units "bytes";
                        description "Amount of memory used by group.";
                    }

                } // container mpls-rsvp

                ///nokia-state/state/system/memory-pools/mscp
                container mscp {
                    description "Enter the mscp context";

                    ///nokia-state/state/system/memory-pools/mscp/max-allowed
                    leaf max-allowed {
                        type uint64 {
                            range "1..max";
                        }
                        units "bytes";
                        description "Maximum allowed amount of memory that can be allocated for a group.";
                    }

                    ///nokia-state/state/system/memory-pools/mscp/current-size
                    leaf current-size {
                        type uint64 {
                            range "0..max";
                        }
                        units "bytes";
                        description "Current amount of allocated memory for a group.";
                    }

                    ///nokia-state/state/system/memory-pools/mscp/max-so-far
                    leaf max-so-far {
                        type uint64 {
                            range "0..max";
                        }
                        units "bytes";
                        description "The highest amount of allocated memory for a group.";
                    }

                    ///nokia-state/state/system/memory-pools/mscp/in-use
                    leaf in-use {
                        type uint64 {
                            range "0..max";
                        }
                        units "bytes";
                        description "Amount of memory used by group.";
                    }

                } // container mscp

                ///nokia-state/state/system/memory-pools/msdp
                container msdp {
                    description "Enter the msdp context";

                    ///nokia-state/state/system/memory-pools/msdp/max-allowed
                    leaf max-allowed {
                        type uint64 {
                            range "1..max";
                        }
                        units "bytes";
                        description "Maximum allowed amount of memory that can be allocated for a group.";
                    }

                    ///nokia-state/state/system/memory-pools/msdp/current-size
                    leaf current-size {
                        type uint64 {
                            range "0..max";
                        }
                        units "bytes";
                        description "Current amount of allocated memory for a group.";
                    }

                    ///nokia-state/state/system/memory-pools/msdp/max-so-far
                    leaf max-so-far {
                        type uint64 {
                            range "0..max";
                        }
                        units "bytes";
                        description "The highest amount of allocated memory for a group.";
                    }

                    ///nokia-state/state/system/memory-pools/msdp/in-use
                    leaf in-use {
                        type uint64 {
                            range "0..max";
                        }
                        units "bytes";
                        description "Amount of memory used by group.";
                    }

                } // container msdp

                ///nokia-state/state/system/memory-pools/management
                container management {
                    description "Enter the management context";

                    ///nokia-state/state/system/memory-pools/management/max-allowed
                    leaf max-allowed {
                        type uint64 {
                            range "1..max";
                        }
                        units "bytes";
                        description "Maximum allowed amount of memory that can be allocated for a group.";
                    }

                    ///nokia-state/state/system/memory-pools/management/current-size
                    leaf current-size {
                        type uint64 {
                            range "0..max";
                        }
                        units "bytes";
                        description "Current amount of allocated memory for a group.";
                    }

                    ///nokia-state/state/system/memory-pools/management/max-so-far
                    leaf max-so-far {
                        type uint64 {
                            range "0..max";
                        }
                        units "bytes";
                        description "The highest amount of allocated memory for a group.";
                    }

                    ///nokia-state/state/system/memory-pools/management/in-use
                    leaf in-use {
                        type uint64 {
                            range "0..max";
                        }
                        units "bytes";
                        description "Amount of memory used by group.";
                    }

                } // container management

                ///nokia-state/state/system/memory-pools/oam
                container oam {
                    description "Enter the oam context";

                    ///nokia-state/state/system/memory-pools/oam/max-allowed
                    leaf max-allowed {
                        type uint64 {
                            range "1..max";
                        }
                        units "bytes";
                        description "Maximum allowed amount of memory that can be allocated for a group.";
                    }

                    ///nokia-state/state/system/memory-pools/oam/current-size
                    leaf current-size {
                        type uint64 {
                            range "0..max";
                        }
                        units "bytes";
                        description "Current amount of allocated memory for a group.";
                    }

                    ///nokia-state/state/system/memory-pools/oam/max-so-far
                    leaf max-so-far {
                        type uint64 {
                            range "0..max";
                        }
                        units "bytes";
                        description "The highest amount of allocated memory for a group.";
                    }

                    ///nokia-state/state/system/memory-pools/oam/in-use
                    leaf in-use {
                        type uint64 {
                            range "0..max";
                        }
                        units "bytes";
                        description "Amount of memory used by group.";
                    }

                } // container oam

                ///nokia-state/state/system/memory-pools/ospf
                container ospf {
                    description "Enter the ospf context";

                    ///nokia-state/state/system/memory-pools/ospf/max-allowed
                    leaf max-allowed {
                        type uint64 {
                            range "1..max";
                        }
                        units "bytes";
                        description "Maximum allowed amount of memory that can be allocated for a group.";
                    }

                    ///nokia-state/state/system/memory-pools/ospf/current-size
                    leaf current-size {
                        type uint64 {
                            range "0..max";
                        }
                        units "bytes";
                        description "Current amount of allocated memory for a group.";
                    }

                    ///nokia-state/state/system/memory-pools/ospf/max-so-far
                    leaf max-so-far {
                        type uint64 {
                            range "0..max";
                        }
                        units "bytes";
                        description "The highest amount of allocated memory for a group.";
                    }

                    ///nokia-state/state/system/memory-pools/ospf/in-use
                    leaf in-use {
                        type uint64 {
                            range "0..max";
                        }
                        units "bytes";
                        description "Amount of memory used by group.";
                    }

                } // container ospf

                ///nokia-state/state/system/memory-pools/openflow
                container openflow {
                    description "Enter the openflow context";

                    ///nokia-state/state/system/memory-pools/openflow/max-allowed
                    leaf max-allowed {
                        type uint64 {
                            range "1..max";
                        }
                        units "bytes";
                        description "Maximum allowed amount of memory that can be allocated for a group.";
                    }

                    ///nokia-state/state/system/memory-pools/openflow/current-size
                    leaf current-size {
                        type uint64 {
                            range "0..max";
                        }
                        units "bytes";
                        description "Current amount of allocated memory for a group.";
                    }

                    ///nokia-state/state/system/memory-pools/openflow/max-so-far
                    leaf max-so-far {
                        type uint64 {
                            range "0..max";
                        }
                        units "bytes";
                        description "The highest amount of allocated memory for a group.";
                    }

                    ///nokia-state/state/system/memory-pools/openflow/in-use
                    leaf in-use {
                        type uint64 {
                            range "0..max";
                        }
                        units "bytes";
                        description "Amount of memory used by group.";
                    }

                } // container openflow

                ///nokia-state/state/system/memory-pools/pim-l2mcast
                container pim-l2mcast {
                    description "Enter the pim-l2mcast context";

                    ///nokia-state/state/system/memory-pools/pim-l2mcast/max-allowed
                    leaf max-allowed {
                        type uint64 {
                            range "1..max";
                        }
                        units "bytes";
                        description "Maximum allowed amount of memory that can be allocated for a group.";
                    }

                    ///nokia-state/state/system/memory-pools/pim-l2mcast/current-size
                    leaf current-size {
                        type uint64 {
                            range "0..max";
                        }
                        units "bytes";
                        description "Current amount of allocated memory for a group.";
                    }

                    ///nokia-state/state/system/memory-pools/pim-l2mcast/max-so-far
                    leaf max-so-far {
                        type uint64 {
                            range "0..max";
                        }
                        units "bytes";
                        description "The highest amount of allocated memory for a group.";
                    }

                    ///nokia-state/state/system/memory-pools/pim-l2mcast/in-use
                    leaf in-use {
                        type uint64 {
                            range "0..max";
                        }
                        units "bytes";
                        description "Amount of memory used by group.";
                    }

                } // container pim-l2mcast

                ///nokia-state/state/system/memory-pools/pki
                container pki {
                    description "Enter the pki context";

                    ///nokia-state/state/system/memory-pools/pki/max-allowed
                    leaf max-allowed {
                        type uint64 {
                            range "1..max";
                        }
                        units "bytes";
                        description "Maximum allowed amount of memory that can be allocated for a group.";
                    }

                    ///nokia-state/state/system/memory-pools/pki/current-size
                    leaf current-size {
                        type uint64 {
                            range "0..max";
                        }
                        units "bytes";
                        description "Current amount of allocated memory for a group.";
                    }

                    ///nokia-state/state/system/memory-pools/pki/max-so-far
                    leaf max-so-far {
                        type uint64 {
                            range "0..max";
                        }
                        units "bytes";
                        description "The highest amount of allocated memory for a group.";
                    }

                    ///nokia-state/state/system/memory-pools/pki/in-use
                    leaf in-use {
                        type uint64 {
                            range "0..max";
                        }
                        units "bytes";
                        description "Amount of memory used by group.";
                    }

                } // container pki

                ///nokia-state/state/system/memory-pools/ptp
                container ptp {
                    description "Enter the ptp context";

                    ///nokia-state/state/system/memory-pools/ptp/max-allowed
                    leaf max-allowed {
                        type uint64 {
                            range "1..max";
                        }
                        units "bytes";
                        description "Maximum allowed amount of memory that can be allocated for a group.";
                    }

                    ///nokia-state/state/system/memory-pools/ptp/current-size
                    leaf current-size {
                        type uint64 {
                            range "0..max";
                        }
                        units "bytes";
                        description "Current amount of allocated memory for a group.";
                    }

                    ///nokia-state/state/system/memory-pools/ptp/max-so-far
                    leaf max-so-far {
                        type uint64 {
                            range "0..max";
                        }
                        units "bytes";
                        description "The highest amount of allocated memory for a group.";
                    }

                    ///nokia-state/state/system/memory-pools/ptp/in-use
                    leaf in-use {
                        type uint64 {
                            range "0..max";
                        }
                        units "bytes";
                        description "Amount of memory used by group.";
                    }

                } // container ptp

                ///nokia-state/state/system/memory-pools/rip
                container rip {
                    description "Enter the rip context";

                    ///nokia-state/state/system/memory-pools/rip/max-allowed
                    leaf max-allowed {
                        type uint64 {
                            range "1..max";
                        }
                        units "bytes";
                        description "Maximum allowed amount of memory that can be allocated for a group.";
                    }

                    ///nokia-state/state/system/memory-pools/rip/current-size
                    leaf current-size {
                        type uint64 {
                            range "0..max";
                        }
                        units "bytes";
                        description "Current amount of allocated memory for a group.";
                    }

                    ///nokia-state/state/system/memory-pools/rip/max-so-far
                    leaf max-so-far {
                        type uint64 {
                            range "0..max";
                        }
                        units "bytes";
                        description "The highest amount of allocated memory for a group.";
                    }

                    ///nokia-state/state/system/memory-pools/rip/in-use
                    leaf in-use {
                        type uint64 {
                            range "0..max";
                        }
                        units "bytes";
                        description "Amount of memory used by group.";
                    }

                } // container rip

                ///nokia-state/state/system/memory-pools/rtm-policies
                container rtm-policies {
                    description "Enter the rtm-policies context";

                    ///nokia-state/state/system/memory-pools/rtm-policies/max-allowed
                    leaf max-allowed {
                        type uint64 {
                            range "1..max";
                        }
                        units "bytes";
                        description "Maximum allowed amount of memory that can be allocated for a group.";
                    }

                    ///nokia-state/state/system/memory-pools/rtm-policies/current-size
                    leaf current-size {
                        type uint64 {
                            range "0..max";
                        }
                        units "bytes";
                        description "Current amount of allocated memory for a group.";
                    }

                    ///nokia-state/state/system/memory-pools/rtm-policies/max-so-far
                    leaf max-so-far {
                        type uint64 {
                            range "0..max";
                        }
                        units "bytes";
                        description "The highest amount of allocated memory for a group.";
                    }

                    ///nokia-state/state/system/memory-pools/rtm-policies/in-use
                    leaf in-use {
                        type uint64 {
                            range "0..max";
                        }
                        units "bytes";
                        description "Amount of memory used by group.";
                    }

                } // container rtm-policies

                ///nokia-state/state/system/memory-pools/redundancy
                container redundancy {
                    description "Enter the redundancy context";

                    ///nokia-state/state/system/memory-pools/redundancy/max-allowed
                    leaf max-allowed {
                        type uint64 {
                            range "1..max";
                        }
                        units "bytes";
                        description "Maximum allowed amount of memory that can be allocated for a group.";
                    }

                    ///nokia-state/state/system/memory-pools/redundancy/current-size
                    leaf current-size {
                        type uint64 {
                            range "0..max";
                        }
                        units "bytes";
                        description "Current amount of allocated memory for a group.";
                    }

                    ///nokia-state/state/system/memory-pools/redundancy/max-so-far
                    leaf max-so-far {
                        type uint64 {
                            range "0..max";
                        }
                        units "bytes";
                        description "The highest amount of allocated memory for a group.";
                    }

                    ///nokia-state/state/system/memory-pools/redundancy/in-use
                    leaf in-use {
                        type uint64 {
                            range "0..max";
                        }
                        units "bytes";
                        description "Amount of memory used by group.";
                    }

                } // container redundancy

                ///nokia-state/state/system/memory-pools/sim
                container sim {
                    description "Enter the sim context";

                    ///nokia-state/state/system/memory-pools/sim/max-allowed
                    leaf max-allowed {
                        type uint64 {
                            range "1..max";
                        }
                        units "bytes";
                        description "Maximum allowed amount of memory that can be allocated for a group.";
                    }

                    ///nokia-state/state/system/memory-pools/sim/current-size
                    leaf current-size {
                        type uint64 {
                            range "0..max";
                        }
                        units "bytes";
                        description "Current amount of allocated memory for a group.";
                    }

                    ///nokia-state/state/system/memory-pools/sim/max-so-far
                    leaf max-so-far {
                        type uint64 {
                            range "0..max";
                        }
                        units "bytes";
                        description "The highest amount of allocated memory for a group.";
                    }

                    ///nokia-state/state/system/memory-pools/sim/in-use
                    leaf in-use {
                        type uint64 {
                            range "0..max";
                        }
                        units "bytes";
                        description "Amount of memory used by group.";
                    }

                } // container sim

                ///nokia-state/state/system/memory-pools/snmp-daemon
                container snmp-daemon {
                    description "Enter the snmp-daemon context";

                    ///nokia-state/state/system/memory-pools/snmp-daemon/max-allowed
                    leaf max-allowed {
                        type uint64 {
                            range "1..max";
                        }
                        units "bytes";
                        description "Maximum allowed amount of memory that can be allocated for a group.";
                    }

                    ///nokia-state/state/system/memory-pools/snmp-daemon/current-size
                    leaf current-size {
                        type uint64 {
                            range "0..max";
                        }
                        units "bytes";
                        description "Current amount of allocated memory for a group.";
                    }

                    ///nokia-state/state/system/memory-pools/snmp-daemon/max-so-far
                    leaf max-so-far {
                        type uint64 {
                            range "0..max";
                        }
                        units "bytes";
                        description "The highest amount of allocated memory for a group.";
                    }

                    ///nokia-state/state/system/memory-pools/snmp-daemon/in-use
                    leaf in-use {
                        type uint64 {
                            range "0..max";
                        }
                        units "bytes";
                        description "Amount of memory used by group.";
                    }

                } // container snmp-daemon

                ///nokia-state/state/system/memory-pools/security
                container security {
                    description "Enter the security context";

                    ///nokia-state/state/system/memory-pools/security/max-allowed
                    leaf max-allowed {
                        type uint64 {
                            range "1..max";
                        }
                        units "bytes";
                        description "Maximum allowed amount of memory that can be allocated for a group.";
                    }

                    ///nokia-state/state/system/memory-pools/security/current-size
                    leaf current-size {
                        type uint64 {
                            range "0..max";
                        }
                        units "bytes";
                        description "Current amount of allocated memory for a group.";
                    }

                    ///nokia-state/state/system/memory-pools/security/max-so-far
                    leaf max-so-far {
                        type uint64 {
                            range "0..max";
                        }
                        units "bytes";
                        description "The highest amount of allocated memory for a group.";
                    }

                    ///nokia-state/state/system/memory-pools/security/in-use
                    leaf in-use {
                        type uint64 {
                            range "0..max";
                        }
                        units "bytes";
                        description "Amount of memory used by group.";
                    }

                } // container security

                ///nokia-state/state/system/memory-pools/services
                container services {
                    description "Enter the services context";

                    ///nokia-state/state/system/memory-pools/services/max-allowed
                    leaf max-allowed {
                        type uint64 {
                            range "1..max";
                        }
                        units "bytes";
                        description "Maximum allowed amount of memory that can be allocated for a group.";
                    }

                    ///nokia-state/state/system/memory-pools/services/current-size
                    leaf current-size {
                        type uint64 {
                            range "0..max";
                        }
                        units "bytes";
                        description "Current amount of allocated memory for a group.";
                    }

                    ///nokia-state/state/system/memory-pools/services/max-so-far
                    leaf max-so-far {
                        type uint64 {
                            range "0..max";
                        }
                        units "bytes";
                        description "The highest amount of allocated memory for a group.";
                    }

                    ///nokia-state/state/system/memory-pools/services/in-use
                    leaf in-use {
                        type uint64 {
                            range "0..max";
                        }
                        units "bytes";
                        description "Amount of memory used by group.";
                    }

                } // container services

                ///nokia-state/state/system/memory-pools/stats
                container stats {
                    description "Enter the stats context";

                    ///nokia-state/state/system/memory-pools/stats/max-allowed
                    leaf max-allowed {
                        type uint64 {
                            range "1..max";
                        }
                        units "bytes";
                        description "Maximum allowed amount of memory that can be allocated for a group.";
                    }

                    ///nokia-state/state/system/memory-pools/stats/current-size
                    leaf current-size {
                        type uint64 {
                            range "0..max";
                        }
                        units "bytes";
                        description "Current amount of allocated memory for a group.";
                    }

                    ///nokia-state/state/system/memory-pools/stats/max-so-far
                    leaf max-so-far {
                        type uint64 {
                            range "0..max";
                        }
                        units "bytes";
                        description "The highest amount of allocated memory for a group.";
                    }

                    ///nokia-state/state/system/memory-pools/stats/in-use
                    leaf in-use {
                        type uint64 {
                            range "0..max";
                        }
                        units "bytes";
                        description "Amount of memory used by group.";
                    }

                } // container stats

                ///nokia-state/state/system/memory-pools/subscriber-mgmt
                container subscriber-mgmt {
                    description "Enter the subscriber-mgmt context";

                    ///nokia-state/state/system/memory-pools/subscriber-mgmt/max-allowed
                    leaf max-allowed {
                        type uint64 {
                            range "1..max";
                        }
                        units "bytes";
                        description "Maximum allowed amount of memory that can be allocated for a group.";
                    }

                    ///nokia-state/state/system/memory-pools/subscriber-mgmt/current-size
                    leaf current-size {
                        type uint64 {
                            range "0..max";
                        }
                        units "bytes";
                        description "Current amount of allocated memory for a group.";
                    }

                    ///nokia-state/state/system/memory-pools/subscriber-mgmt/max-so-far
                    leaf max-so-far {
                        type uint64 {
                            range "0..max";
                        }
                        units "bytes";
                        description "The highest amount of allocated memory for a group.";
                    }

                    ///nokia-state/state/system/memory-pools/subscriber-mgmt/in-use
                    leaf in-use {
                        type uint64 {
                            range "0..max";
                        }
                        units "bytes";
                        description "Amount of memory used by group.";
                    }

                } // container subscriber-mgmt

                ///nokia-state/state/system/memory-pools/system
                container system {
                    description "Enter the system context";

                    ///nokia-state/state/system/memory-pools/system/max-allowed
                    leaf max-allowed {
                        type uint64 {
                            range "1..max";
                        }
                        units "bytes";
                        description "Maximum allowed amount of memory that can be allocated for a group.";
                    }

                    ///nokia-state/state/system/memory-pools/system/current-size
                    leaf current-size {
                        type uint64 {
                            range "0..max";
                        }
                        units "bytes";
                        description "Current amount of allocated memory for a group.";
                    }

                    ///nokia-state/state/system/memory-pools/system/max-so-far
                    leaf max-so-far {
                        type uint64 {
                            range "0..max";
                        }
                        units "bytes";
                        description "The highest amount of allocated memory for a group.";
                    }

                    ///nokia-state/state/system/memory-pools/system/in-use
                    leaf in-use {
                        type uint64 {
                            range "0..max";
                        }
                        units "bytes";
                        description "Amount of memory used by group.";
                    }

                } // container system

                ///nokia-state/state/system/memory-pools/traffic-eng
                container traffic-eng {
                    description "Enter the traffic-eng context";

                    ///nokia-state/state/system/memory-pools/traffic-eng/max-allowed
                    leaf max-allowed {
                        type uint64 {
                            range "1..max";
                        }
                        units "bytes";
                        description "Maximum allowed amount of memory that can be allocated for a group.";
                    }

                    ///nokia-state/state/system/memory-pools/traffic-eng/current-size
                    leaf current-size {
                        type uint64 {
                            range "0..max";
                        }
                        units "bytes";
                        description "Current amount of allocated memory for a group.";
                    }

                    ///nokia-state/state/system/memory-pools/traffic-eng/max-so-far
                    leaf max-so-far {
                        type uint64 {
                            range "0..max";
                        }
                        units "bytes";
                        description "The highest amount of allocated memory for a group.";
                    }

                    ///nokia-state/state/system/memory-pools/traffic-eng/in-use
                    leaf in-use {
                        type uint64 {
                            range "0..max";
                        }
                        units "bytes";
                        description "Amount of memory used by group.";
                    }

                } // container traffic-eng

                ///nokia-state/state/system/memory-pools/tree-sid
                container tree-sid {
                    description "Enter the tree-sid context";

                    ///nokia-state/state/system/memory-pools/tree-sid/max-allowed
                    leaf max-allowed {
                        type uint64 {
                            range "1..max";
                        }
                        units "bytes";
                        description "Maximum allowed amount of memory that can be allocated for a group.";
                    }

                    ///nokia-state/state/system/memory-pools/tree-sid/current-size
                    leaf current-size {
                        type uint64 {
                            range "0..max";
                        }
                        units "bytes";
                        description "Current amount of allocated memory for a group.";
                    }

                    ///nokia-state/state/system/memory-pools/tree-sid/max-so-far
                    leaf max-so-far {
                        type uint64 {
                            range "0..max";
                        }
                        units "bytes";
                        description "The highest amount of allocated memory for a group.";
                    }

                    ///nokia-state/state/system/memory-pools/tree-sid/in-use
                    leaf in-use {
                        type uint64 {
                            range "0..max";
                        }
                        units "bytes";
                        description "Amount of memory used by group.";
                    }

                } // container tree-sid

                ///nokia-state/state/system/memory-pools/vrrp
                container vrrp {
                    description "Enter the vrrp context";

                    ///nokia-state/state/system/memory-pools/vrrp/max-allowed
                    leaf max-allowed {
                        type uint64 {
                            range "1..max";
                        }
                        units "bytes";
                        description "Maximum allowed amount of memory that can be allocated for a group.";
                    }

                    ///nokia-state/state/system/memory-pools/vrrp/current-size
                    leaf current-size {
                        type uint64 {
                            range "0..max";
                        }
                        units "bytes";
                        description "Current amount of allocated memory for a group.";
                    }

                    ///nokia-state/state/system/memory-pools/vrrp/max-so-far
                    leaf max-so-far {
                        type uint64 {
                            range "0..max";
                        }
                        units "bytes";
                        description "The highest amount of allocated memory for a group.";
                    }

                    ///nokia-state/state/system/memory-pools/vrrp/in-use
                    leaf in-use {
                        type uint64 {
                            range "0..max";
                        }
                        units "bytes";
                        description "Amount of memory used by group.";
                    }

                } // container vrrp

                ///nokia-state/state/system/memory-pools/web-redirect
                container web-redirect {
                    description "Enter the web-redirect context";

                    ///nokia-state/state/system/memory-pools/web-redirect/max-allowed
                    leaf max-allowed {
                        type uint64 {
                            range "1..max";
                        }
                        units "bytes";
                        description "Maximum allowed amount of memory that can be allocated for a group.";
                    }

                    ///nokia-state/state/system/memory-pools/web-redirect/current-size
                    leaf current-size {
                        type uint64 {
                            range "0..max";
                        }
                        units "bytes";
                        description "Current amount of allocated memory for a group.";
                    }

                    ///nokia-state/state/system/memory-pools/web-redirect/max-so-far
                    leaf max-so-far {
                        type uint64 {
                            range "0..max";
                        }
                        units "bytes";
                        description "The highest amount of allocated memory for a group.";
                    }

                    ///nokia-state/state/system/memory-pools/web-redirect/in-use
                    leaf in-use {
                        type uint64 {
                            range "0..max";
                        }
                        units "bytes";
                        description "Amount of memory used by group.";
                    }

                } // container web-redirect

                ///nokia-state/state/system/memory-pools/iom
                container iom {
                    description "Enter the iom context";

                    ///nokia-state/state/system/memory-pools/iom/max-allowed
                    leaf max-allowed {
                        type uint64 {
                            range "1..max";
                        }
                        units "bytes";
                        description "Maximum allowed amount of memory that can be allocated for a group.";
                    }

                    ///nokia-state/state/system/memory-pools/iom/current-size
                    leaf current-size {
                        type uint64 {
                            range "0..max";
                        }
                        units "bytes";
                        description "Current amount of allocated memory for a group.";
                    }

                    ///nokia-state/state/system/memory-pools/iom/max-so-far
                    leaf max-so-far {
                        type uint64 {
                            range "0..max";
                        }
                        units "bytes";
                        description "The highest amount of allocated memory for a group.";
                    }

                    ///nokia-state/state/system/memory-pools/iom/in-use
                    leaf in-use {
                        type uint64 {
                            range "0..max";
                        }
                        units "bytes";
                        description "Amount of memory used by group.";
                    }

                } // container iom

                ///nokia-state/state/system/memory-pools/summary
                container summary {
                    description "Enter the summary context";

                    ///nokia-state/state/system/memory-pools/summary/current-total-size
                    leaf current-total-size {
                        type uint64 {
                            range "0..max";
                        }
                        units "bytes";
                        description "Amount of memory allocated for all groups.";
                    }

                    ///nokia-state/state/system/memory-pools/summary/total-in-use
                    leaf total-in-use {
                        type uint64 {
                            range "0..max";
                        }
                        units "bytes";
                        description "Amount of memory used by all groups.";
                    }

                    ///nokia-state/state/system/memory-pools/summary/available-memory
                    leaf available-memory {
                        type uint64 {
                            range "0..max";
                        }
                        units "bytes";
                        description "Amount of unused memory.";
                    }

                } // container summary

            } // container memory-pools

            ///nokia-state/state/system/version
            container version {
                description "Enter the version context";

                ///nokia-state/state/system/version/version-number
                leaf version-number {
                    type string;
                    description "Version number.";
                }

                ///nokia-state/state/system/version/version-string
                leaf version-string {
                    type string {
                        length "0..256";
                    }
                    description "Version string.";
                }

            } // container version

            ///nokia-state/state/system/statistics
            container statistics {
                description "Enter the statistics context";

                ///nokia-state/state/system/statistics/ip-tunnel
                container ip-tunnel {
                    description "Enter the ip-tunnel context";

                    ///nokia-state/state/system/statistics/ip-tunnel/number-of-tunnels
                    container number-of-tunnels {
                        description "Enter the number-of-tunnels context";

                        ///nokia-state/state/system/statistics/ip-tunnel/number-of-tunnels/current
                        container current {
                            description "Enter the current context";

                            ///nokia-state/state/system/statistics/ip-tunnel/number-of-tunnels/current/gre
                            leaf gre {
                                type yang:counter64;
                                description "Number of GRE tunnels.";
                            }

                            ///nokia-state/state/system/statistics/ip-tunnel/number-of-tunnels/current/ip
                            leaf ip {
                                type yang:counter64;
                                description "Number of IP tunnels.";
                            }

                            ///nokia-state/state/system/statistics/ip-tunnel/number-of-tunnels/current/l2tpv3
                            leaf l2tpv3 {
                                type yang:counter64;
                                description "Number of L2TPv3 tunnels.";
                            }

                            ///nokia-state/state/system/statistics/ip-tunnel/number-of-tunnels/current/start-time
                            leaf start-time {
                                type yang:date-and-time;
                                description "The time when the sampling interval started.";
                            }

                        } // container current

                    } // container number-of-tunnels

                    ///nokia-state/state/system/statistics/ip-tunnel/throughput
                    container throughput {
                        description "Enter the throughput context";

                        ///nokia-state/state/system/statistics/ip-tunnel/throughput/gre
                        container gre {
                            description "Enter the gre context";

                            ///nokia-state/state/system/statistics/ip-tunnel/throughput/gre/current
                            container current {
                                description "Enter the current context";

                                ///nokia-state/state/system/statistics/ip-tunnel/throughput/gre/current/start-time
                                leaf start-time {
                                    type yang:date-and-time;
                                    description "The time when the sampling interval started.";
                                }

                                ///nokia-state/state/system/statistics/ip-tunnel/throughput/gre/current/sampling-duration
                                leaf sampling-duration {
                                    type types-sros:time-duration;
                                    description "The duration of the corresponding sampling interval.";
                                }

                                ///nokia-state/state/system/statistics/ip-tunnel/throughput/gre/current/packets
                                container packets {
                                    description "Enter the packets context";

                                    ///nokia-state/state/system/statistics/ip-tunnel/throughput/gre/current/packets/encapsulated
                                    leaf encapsulated {
                                        type yang:counter64;
                                        units "packets per second";
                                        description "Encapsulated GRE tunnel throughput.";
                                    }

                                    ///nokia-state/state/system/statistics/ip-tunnel/throughput/gre/current/packets/decapsulated
                                    leaf decapsulated {
                                        type yang:counter64;
                                        units "packets per second";
                                        description "Decapsulated GRE tunnel throughput.";
                                    }

                                    ///nokia-state/state/system/statistics/ip-tunnel/throughput/gre/current/packets/total
                                    leaf total {
                                        type yang:counter64;
                                        units "packets per second";
                                        description "Encapsulated and decapsulated GRE tunnel throughput.";
                                    }

                                } // container packets

                                ///nokia-state/state/system/statistics/ip-tunnel/throughput/gre/current/bytes
                                container bytes {
                                    description "Enter the bytes context";

                                    ///nokia-state/state/system/statistics/ip-tunnel/throughput/gre/current/bytes/encapsulated
                                    leaf encapsulated {
                                        type yang:counter64;
                                        units "megabps";
                                        description "Encapsulated GRE tunnel throughput.";
                                    }

                                    ///nokia-state/state/system/statistics/ip-tunnel/throughput/gre/current/bytes/decapsulated
                                    leaf decapsulated {
                                        type yang:counter64;
                                        units "megabps";
                                        description "Decapsulated GRE tunnel throughput.";
                                    }

                                    ///nokia-state/state/system/statistics/ip-tunnel/throughput/gre/current/bytes/total
                                    leaf total {
                                        type yang:counter64;
                                        units "megabps";
                                        description "Encapsulated and decapsulated GRE tunnel throughput.";
                                    }

                                } // container bytes

                            } // container current

                            ///nokia-state/state/system/statistics/ip-tunnel/throughput/gre/historical
                            list historical {
                                key "index";
                                description "Enter the historical list instance";

                                ///nokia-state/state/system/statistics/ip-tunnel/throughput/gre/historical/index
                                leaf index {
                                    type uint32 {
                                        range "2..max";
                                    }
                                    description
                                        "The index of the finished sampling interval period for this statistic.
                                         It starts with '2' and is ordered by start time of intervals so that
                                         smaller index indicate more recent intervals.";
                                }

                                ///nokia-state/state/system/statistics/ip-tunnel/throughput/gre/historical/start-time
                                leaf start-time {
                                    type yang:date-and-time;
                                    description "The time when the sampling interval started.";
                                }

                                ///nokia-state/state/system/statistics/ip-tunnel/throughput/gre/historical/sampling-duration
                                leaf sampling-duration {
                                    type types-sros:time-duration;
                                    description "The duration of the corresponding sampling interval.";
                                }

                                ///nokia-state/state/system/statistics/ip-tunnel/throughput/gre/historical/packets
                                container packets {
                                    description "Enter the packets context";

                                    ///nokia-state/state/system/statistics/ip-tunnel/throughput/gre/historical/packets/encapsulated
                                    leaf encapsulated {
                                        type yang:counter64;
                                        units "packets per second";
                                        description "Encapsulated GRE tunnel throughput.";
                                    }

                                    ///nokia-state/state/system/statistics/ip-tunnel/throughput/gre/historical/packets/decapsulated
                                    leaf decapsulated {
                                        type yang:counter64;
                                        units "packets per second";
                                        description "Decapsulated GRE tunnel throughput.";
                                    }

                                    ///nokia-state/state/system/statistics/ip-tunnel/throughput/gre/historical/packets/total
                                    leaf total {
                                        type yang:counter64;
                                        units "packets per second";
                                        description "Encapsulated and decapsulated GRE tunnel throughput.";
                                    }

                                } // container packets

                                ///nokia-state/state/system/statistics/ip-tunnel/throughput/gre/historical/bytes
                                container bytes {
                                    description "Enter the bytes context";

                                    ///nokia-state/state/system/statistics/ip-tunnel/throughput/gre/historical/bytes/encapsulated
                                    leaf encapsulated {
                                        type yang:counter64;
                                        units "megabps";
                                        description "Encapsulated GRE tunnel throughput.";
                                    }

                                    ///nokia-state/state/system/statistics/ip-tunnel/throughput/gre/historical/bytes/decapsulated
                                    leaf decapsulated {
                                        type yang:counter64;
                                        units "megabps";
                                        description "Decapsulated GRE tunnel throughput.";
                                    }

                                    ///nokia-state/state/system/statistics/ip-tunnel/throughput/gre/historical/bytes/total
                                    leaf total {
                                        type yang:counter64;
                                        units "megabps";
                                        description "Encapsulated and decapsulated GRE tunnel throughput.";
                                    }

                                } // container bytes

                            } // list historical

                        } // container gre

                        ///nokia-state/state/system/statistics/ip-tunnel/throughput/ip
                        container ip {
                            description "Enter the ip context";

                            ///nokia-state/state/system/statistics/ip-tunnel/throughput/ip/current
                            container current {
                                description "Enter the current context";

                                ///nokia-state/state/system/statistics/ip-tunnel/throughput/ip/current/start-time
                                leaf start-time {
                                    type yang:date-and-time;
                                    description "The time when the sampling interval started.";
                                }

                                ///nokia-state/state/system/statistics/ip-tunnel/throughput/ip/current/sampling-duration
                                leaf sampling-duration {
                                    type types-sros:time-duration;
                                    description "The duration of the corresponding sampling interval.";
                                }

                                ///nokia-state/state/system/statistics/ip-tunnel/throughput/ip/current/packets
                                container packets {
                                    description "Enter the packets context";

                                    ///nokia-state/state/system/statistics/ip-tunnel/throughput/ip/current/packets/encapsulated
                                    leaf encapsulated {
                                        type yang:counter64;
                                        units "packets per second";
                                        description "Encapsulated IP tunnel throughput.";
                                    }

                                    ///nokia-state/state/system/statistics/ip-tunnel/throughput/ip/current/packets/decapsulated
                                    leaf decapsulated {
                                        type yang:counter64;
                                        units "packets per second";
                                        description "Decapsulated IP tunnel throughput.";
                                    }

                                    ///nokia-state/state/system/statistics/ip-tunnel/throughput/ip/current/packets/total
                                    leaf total {
                                        type yang:counter64;
                                        units "packets per second";
                                        description "Encapsulated and decapsulated IP tunnel throughput.";
                                    }

                                } // container packets

                                ///nokia-state/state/system/statistics/ip-tunnel/throughput/ip/current/bytes
                                container bytes {
                                    description "Enter the bytes context";

                                    ///nokia-state/state/system/statistics/ip-tunnel/throughput/ip/current/bytes/encapsulated
                                    leaf encapsulated {
                                        type yang:counter64;
                                        units "megabps";
                                        description "Encapsulated IP tunnel throughput.";
                                    }

                                    ///nokia-state/state/system/statistics/ip-tunnel/throughput/ip/current/bytes/decapsulated
                                    leaf decapsulated {
                                        type yang:counter64;
                                        units "megabps";
                                        description "Decapsulated IP tunnel throughput.";
                                    }

                                    ///nokia-state/state/system/statistics/ip-tunnel/throughput/ip/current/bytes/total
                                    leaf total {
                                        type yang:counter64;
                                        units "megabps";
                                        description "Encapsulated and decapsulated IP tunnel throughput.";
                                    }

                                } // container bytes

                            } // container current

                            ///nokia-state/state/system/statistics/ip-tunnel/throughput/ip/historical
                            list historical {
                                key "index";
                                description "Enter the historical list instance";

                                ///nokia-state/state/system/statistics/ip-tunnel/throughput/ip/historical/index
                                leaf index {
                                    type uint32 {
                                        range "2..max";
                                    }
                                    description
                                        "The index of the finished sampling interval period for this statistic.
                                         It starts with '2' and is ordered by start time of intervals so that
                                         smaller index indicate more recent intervals.";
                                }

                                ///nokia-state/state/system/statistics/ip-tunnel/throughput/ip/historical/start-time
                                leaf start-time {
                                    type yang:date-and-time;
                                    description "The time when the sampling interval started.";
                                }

                                ///nokia-state/state/system/statistics/ip-tunnel/throughput/ip/historical/sampling-duration
                                leaf sampling-duration {
                                    type types-sros:time-duration;
                                    description "The duration of the corresponding sampling interval.";
                                }

                                ///nokia-state/state/system/statistics/ip-tunnel/throughput/ip/historical/packets
                                container packets {
                                    description "Enter the packets context";

                                    ///nokia-state/state/system/statistics/ip-tunnel/throughput/ip/historical/packets/encapsulated
                                    leaf encapsulated {
                                        type yang:counter64;
                                        units "packets per second";
                                        description "Encapsulated IP tunnel throughput.";
                                    }

                                    ///nokia-state/state/system/statistics/ip-tunnel/throughput/ip/historical/packets/decapsulated
                                    leaf decapsulated {
                                        type yang:counter64;
                                        units "packets per second";
                                        description "Decapsulated IP tunnel throughput.";
                                    }

                                    ///nokia-state/state/system/statistics/ip-tunnel/throughput/ip/historical/packets/total
                                    leaf total {
                                        type yang:counter64;
                                        units "packets per second";
                                        description "Encapsulated and decapsulated IP tunnel throughput.";
                                    }

                                } // container packets

                                ///nokia-state/state/system/statistics/ip-tunnel/throughput/ip/historical/bytes
                                container bytes {
                                    description "Enter the bytes context";

                                    ///nokia-state/state/system/statistics/ip-tunnel/throughput/ip/historical/bytes/encapsulated
                                    leaf encapsulated {
                                        type yang:counter64;
                                        units "megabps";
                                        description "Encapsulated IP tunnel throughput.";
                                    }

                                    ///nokia-state/state/system/statistics/ip-tunnel/throughput/ip/historical/bytes/decapsulated
                                    leaf decapsulated {
                                        type yang:counter64;
                                        units "megabps";
                                        description "Decapsulated IP tunnel throughput.";
                                    }

                                    ///nokia-state/state/system/statistics/ip-tunnel/throughput/ip/historical/bytes/total
                                    leaf total {
                                        type yang:counter64;
                                        units "megabps";
                                        description "Encapsulated and decapsulated IP tunnel throughput.";
                                    }

                                } // container bytes

                            } // list historical

                        } // container ip

                        ///nokia-state/state/system/statistics/ip-tunnel/throughput/l2tpv3
                        container l2tpv3 {
                            description "Enter the l2tpv3 context";

                            ///nokia-state/state/system/statistics/ip-tunnel/throughput/l2tpv3/current
                            container current {
                                description "Enter the current context";

                                ///nokia-state/state/system/statistics/ip-tunnel/throughput/l2tpv3/current/start-time
                                leaf start-time {
                                    type yang:date-and-time;
                                    description "The time when the sampling interval started.";
                                }

                                ///nokia-state/state/system/statistics/ip-tunnel/throughput/l2tpv3/current/sampling-duration
                                leaf sampling-duration {
                                    type types-sros:time-duration;
                                    description "The duration of the corresponding sampling interval.";
                                }

                                ///nokia-state/state/system/statistics/ip-tunnel/throughput/l2tpv3/current/packets
                                container packets {
                                    description "Enter the packets context";

                                    ///nokia-state/state/system/statistics/ip-tunnel/throughput/l2tpv3/current/packets/encapsulated
                                    leaf encapsulated {
                                        type yang:counter64;
                                        units "packets per second";
                                        description "Encapsulated L2TPv3 tunnel throughput.";
                                    }

                                    ///nokia-state/state/system/statistics/ip-tunnel/throughput/l2tpv3/current/packets/decapsulated
                                    leaf decapsulated {
                                        type yang:counter64;
                                        units "packets per second";
                                        description "Decapsulated L2TPv3 tunnel throughput.";
                                    }

                                    ///nokia-state/state/system/statistics/ip-tunnel/throughput/l2tpv3/current/packets/total
                                    leaf total {
                                        type yang:counter64;
                                        units "packets per second";
                                        description "Encapsulated and decapsulated L2TPv3 tunnel throughput.";
                                    }

                                } // container packets

                                ///nokia-state/state/system/statistics/ip-tunnel/throughput/l2tpv3/current/bytes
                                container bytes {
                                    description "Enter the bytes context";

                                    ///nokia-state/state/system/statistics/ip-tunnel/throughput/l2tpv3/current/bytes/encapsulated
                                    leaf encapsulated {
                                        type yang:counter64;
                                        units "megabps";
                                        description "Encapsulated L2TPv3 tunnel throughput.";
                                    }

                                    ///nokia-state/state/system/statistics/ip-tunnel/throughput/l2tpv3/current/bytes/decapsulated
                                    leaf decapsulated {
                                        type yang:counter64;
                                        units "megabps";
                                        description "Decapsulated L2TPv3 tunnel throughput.";
                                    }

                                    ///nokia-state/state/system/statistics/ip-tunnel/throughput/l2tpv3/current/bytes/total
                                    leaf total {
                                        type yang:counter64;
                                        units "megabps";
                                        description "Encapsulated and decapsulated L2TPv3 tunnel throughput.";
                                    }

                                } // container bytes

                            } // container current

                            ///nokia-state/state/system/statistics/ip-tunnel/throughput/l2tpv3/historical
                            list historical {
                                key "index";
                                description "Enter the historical list instance";

                                ///nokia-state/state/system/statistics/ip-tunnel/throughput/l2tpv3/historical/index
                                leaf index {
                                    type uint32 {
                                        range "2..max";
                                    }
                                    description
                                        "The index of the finished sampling interval period for this statistic.
                                         It starts with '2' and is ordered by start time of intervals so that
                                         smaller index indicate more recent intervals.";
                                }

                                ///nokia-state/state/system/statistics/ip-tunnel/throughput/l2tpv3/historical/start-time
                                leaf start-time {
                                    type yang:date-and-time;
                                    description "The time when the sampling interval started.";
                                }

                                ///nokia-state/state/system/statistics/ip-tunnel/throughput/l2tpv3/historical/sampling-duration
                                leaf sampling-duration {
                                    type types-sros:time-duration;
                                    description "The duration of the corresponding sampling interval.";
                                }

                                ///nokia-state/state/system/statistics/ip-tunnel/throughput/l2tpv3/historical/packets
                                container packets {
                                    description "Enter the packets context";

                                    ///nokia-state/state/system/statistics/ip-tunnel/throughput/l2tpv3/historical/packets/encapsulated
                                    leaf encapsulated {
                                        type yang:counter64;
                                        units "packets per second";
                                        description "Encapsulated L2TPv3 tunnel throughput.";
                                    }

                                    ///nokia-state/state/system/statistics/ip-tunnel/throughput/l2tpv3/historical/packets/decapsulated
                                    leaf decapsulated {
                                        type yang:counter64;
                                        units "packets per second";
                                        description "Decapsulated L2TPv3 tunnel throughput.";
                                    }

                                    ///nokia-state/state/system/statistics/ip-tunnel/throughput/l2tpv3/historical/packets/total
                                    leaf total {
                                        type yang:counter64;
                                        units "packets per second";
                                        description "Encapsulated and decapsulated L2TPv3 tunnel throughput.";
                                    }

                                } // container packets

                                ///nokia-state/state/system/statistics/ip-tunnel/throughput/l2tpv3/historical/bytes
                                container bytes {
                                    description "Enter the bytes context";

                                    ///nokia-state/state/system/statistics/ip-tunnel/throughput/l2tpv3/historical/bytes/encapsulated
                                    leaf encapsulated {
                                        type yang:counter64;
                                        units "megabps";
                                        description "Encapsulated L2TPv3 tunnel throughput.";
                                    }

                                    ///nokia-state/state/system/statistics/ip-tunnel/throughput/l2tpv3/historical/bytes/decapsulated
                                    leaf decapsulated {
                                        type yang:counter64;
                                        units "megabps";
                                        description "Decapsulated L2TPv3 tunnel throughput.";
                                    }

                                    ///nokia-state/state/system/statistics/ip-tunnel/throughput/l2tpv3/historical/bytes/total
                                    leaf total {
                                        type yang:counter64;
                                        units "megabps";
                                        description "Encapsulated and decapsulated L2TPv3 tunnel throughput.";
                                    }

                                } // container bytes

                            } // list historical

                        } // container l2tpv3

                    } // container throughput

                } // container ip-tunnel

                ///nokia-state/state/system/statistics/ipsec
                container ipsec {
                    description "Enter the ipsec context";

                    ///nokia-state/state/system/statistics/ipsec/number-of-tunnels
                    container number-of-tunnels {
                        description "Enter the number-of-tunnels context";

                        ///nokia-state/state/system/statistics/ipsec/number-of-tunnels/current
                        container current {
                            description "Enter the current context";

                            ///nokia-state/state/system/statistics/ipsec/number-of-tunnels/current/static-lan-to-lan
                            leaf static-lan-to-lan {
                                type yang:counter64;
                                description "Number of IPsec static LAN-to-LAN (SL2L) tunnels.";
                            }

                            ///nokia-state/state/system/statistics/ipsec/number-of-tunnels/current/dynamic-lan-to-lan
                            leaf dynamic-lan-to-lan {
                                type yang:counter64;
                                description "Number of IPsec dynamic LAN-to-LAN (DL2L) tunnels.";
                            }

                            ///nokia-state/state/system/statistics/ipsec/number-of-tunnels/current/remote-access
                            leaf remote-access {
                                type yang:counter64;
                                description "Number of IPsec remote access (RA) tunnels.";
                            }

                            ///nokia-state/state/system/statistics/ipsec/number-of-tunnels/current/total
                            leaf total {
                                type yang:counter64;
                                description "Total number of IPsec tunnels.";
                            }

                            ///nokia-state/state/system/statistics/ipsec/number-of-tunnels/current/start-time
                            leaf start-time {
                                type yang:date-and-time;
                                description "The time when the sampling interval started.";
                            }

                        } // container current

                        ///nokia-state/state/system/statistics/ipsec/number-of-tunnels/historical
                        list historical {
                            key "index";
                            description "Enter the historical list instance";

                            ///nokia-state/state/system/statistics/ipsec/number-of-tunnels/historical/index
                            leaf index {
                                type uint32 {
                                    range "2..max";
                                }
                                description
                                    "The index of the finished sampling interval period for this statistic.
                                     It starts with '2' and is ordered by start time of intervals so that
                                     smaller index indicate more recent intervals.";
                            }

                            ///nokia-state/state/system/statistics/ipsec/number-of-tunnels/historical/static-lan-to-lan
                            leaf static-lan-to-lan {
                                type yang:counter64;
                                description "Number of IPsec static LAN-to-LAN (SL2L) tunnels.";
                            }

                            ///nokia-state/state/system/statistics/ipsec/number-of-tunnels/historical/dynamic-lan-to-lan
                            leaf dynamic-lan-to-lan {
                                type yang:counter64;
                                description "Number of IPsec dynamic LAN-to-LAN (DL2L) tunnels.";
                            }

                            ///nokia-state/state/system/statistics/ipsec/number-of-tunnels/historical/remote-access
                            leaf remote-access {
                                type yang:counter64;
                                description "Number of IPsec remote access (RA) tunnels.";
                            }

                            ///nokia-state/state/system/statistics/ipsec/number-of-tunnels/historical/total
                            leaf total {
                                type yang:counter64;
                                description "Total number of IPsec tunnels.";
                            }

                            ///nokia-state/state/system/statistics/ipsec/number-of-tunnels/historical/start-time
                            leaf start-time {
                                type yang:date-and-time;
                                description "The time when the sampling interval started.";
                            }

                        } // list historical

                    } // container number-of-tunnels

                    ///nokia-state/state/system/statistics/ipsec/throughput
                    container throughput {
                        description "Enter the throughput context";

                        ///nokia-state/state/system/statistics/ipsec/throughput/current
                        container current {
                            description "Enter the current context";

                            ///nokia-state/state/system/statistics/ipsec/throughput/current/start-time
                            leaf start-time {
                                type yang:date-and-time;
                                description "The time when the sampling interval started.";
                            }

                            ///nokia-state/state/system/statistics/ipsec/throughput/current/sampling-duration
                            leaf sampling-duration {
                                type types-sros:time-duration;
                                description "The duration of the corresponding sampling interval.";
                            }

                            ///nokia-state/state/system/statistics/ipsec/throughput/current/packets
                            container packets {
                                description "Enter the packets context";

                                ///nokia-state/state/system/statistics/ipsec/throughput/current/packets/encrypted
                                leaf encrypted {
                                    type yang:counter64;
                                    units "packets per second";
                                    description "Encrypted IPsec traffic throughput.";
                                }

                                ///nokia-state/state/system/statistics/ipsec/throughput/current/packets/decrypted
                                leaf decrypted {
                                    type yang:counter64;
                                    units "packets per second";
                                    description "Decrypted IPsec traffic throughput.";
                                }

                                ///nokia-state/state/system/statistics/ipsec/throughput/current/packets/total
                                leaf total {
                                    type yang:counter64;
                                    units "packets per second";
                                    description "Encrypted and decrypted IPsec traffic throughput.";
                                }

                            } // container packets

                            ///nokia-state/state/system/statistics/ipsec/throughput/current/bytes
                            container bytes {
                                description "Enter the bytes context";

                                ///nokia-state/state/system/statistics/ipsec/throughput/current/bytes/encrypted
                                leaf encrypted {
                                    type yang:counter64;
                                    units "megabps";
                                    description "Encrypted IPsec traffic throughput.";
                                }

                                ///nokia-state/state/system/statistics/ipsec/throughput/current/bytes/decrypted
                                leaf decrypted {
                                    type yang:counter64;
                                    units "megabps";
                                    description "Decrypted IPsec traffic throughput.";
                                }

                                ///nokia-state/state/system/statistics/ipsec/throughput/current/bytes/total
                                leaf total {
                                    type yang:counter64;
                                    units "megabps";
                                    description "Encrypted and decrypted IPsec traffic throughput.";
                                }

                            } // container bytes

                        } // container current

                        ///nokia-state/state/system/statistics/ipsec/throughput/historical
                        list historical {
                            key "index";
                            description "Enter the historical list instance";

                            ///nokia-state/state/system/statistics/ipsec/throughput/historical/index
                            leaf index {
                                type uint32 {
                                    range "2..max";
                                }
                                description
                                    "The index of the finished sampling interval period for this statistic.
                                     It starts with '2' and is ordered by start time of intervals so that
                                     smaller index indicate more recent intervals.";
                            }

                            ///nokia-state/state/system/statistics/ipsec/throughput/historical/start-time
                            leaf start-time {
                                type yang:date-and-time;
                                description "The time when the sampling interval started.";
                            }

                            ///nokia-state/state/system/statistics/ipsec/throughput/historical/sampling-duration
                            leaf sampling-duration {
                                type types-sros:time-duration;
                                description "The duration of the corresponding sampling interval.";
                            }

                            ///nokia-state/state/system/statistics/ipsec/throughput/historical/packets
                            container packets {
                                description "Enter the packets context";

                                ///nokia-state/state/system/statistics/ipsec/throughput/historical/packets/encrypted
                                leaf encrypted {
                                    type yang:counter64;
                                    units "packets per second";
                                    description "Encrypted IPsec traffic throughput.";
                                }

                                ///nokia-state/state/system/statistics/ipsec/throughput/historical/packets/decrypted
                                leaf decrypted {
                                    type yang:counter64;
                                    units "packets per second";
                                    description "Decrypted IPsec traffic throughput.";
                                }

                                ///nokia-state/state/system/statistics/ipsec/throughput/historical/packets/total
                                leaf total {
                                    type yang:counter64;
                                    units "packets per second";
                                    description "Encrypted and decrypted IPsec traffic throughput.";
                                }

                            } // container packets

                            ///nokia-state/state/system/statistics/ipsec/throughput/historical/bytes
                            container bytes {
                                description "Enter the bytes context";

                                ///nokia-state/state/system/statistics/ipsec/throughput/historical/bytes/encrypted
                                leaf encrypted {
                                    type yang:counter64;
                                    units "megabps";
                                    description "Encrypted IPsec traffic throughput.";
                                }

                                ///nokia-state/state/system/statistics/ipsec/throughput/historical/bytes/decrypted
                                leaf decrypted {
                                    type yang:counter64;
                                    units "megabps";
                                    description "Decrypted IPsec traffic throughput.";
                                }

                                ///nokia-state/state/system/statistics/ipsec/throughput/historical/bytes/total
                                leaf total {
                                    type yang:counter64;
                                    units "megabps";
                                    description "Encrypted and decrypted IPsec traffic throughput.";
                                }

                            } // container bytes

                        } // list historical

                    } // container throughput

                    ///nokia-state/state/system/statistics/ipsec/tunnel-setup-rate
                    container tunnel-setup-rate {
                        description "Enter the tunnel-setup-rate context";

                        ///nokia-state/state/system/statistics/ipsec/tunnel-setup-rate/current
                        container current {
                            description "Enter the current context";

                            ///nokia-state/state/system/statistics/ipsec/tunnel-setup-rate/current/static-lan-to-lan
                            leaf static-lan-to-lan {
                                type decimal64 {
                                    fraction-digits 2;
                                }
                                units "tunnels per second";
                                description "Static LAN-to-LAN (SL2L) tunnel setup rate.";
                            }

                            ///nokia-state/state/system/statistics/ipsec/tunnel-setup-rate/current/total
                            leaf total {
                                type decimal64 {
                                    fraction-digits 2;
                                }
                                units "tunnels per second";
                                description "Total IPsec tunnel setup rate.";
                            }

                            ///nokia-state/state/system/statistics/ipsec/tunnel-setup-rate/current/dynamic-lan-to-lan
                            leaf dynamic-lan-to-lan {
                                type decimal64 {
                                    fraction-digits 2;
                                }
                                units "tunnels per second";
                                description "Dynamic LAN-to-LAN (DL2L) tunnel setup rate.";
                            }

                            ///nokia-state/state/system/statistics/ipsec/tunnel-setup-rate/current/remote-access
                            leaf remote-access {
                                type decimal64 {
                                    fraction-digits 2;
                                }
                                units "tunnels per second";
                                description "Remote access (RA) tunnel setup rate.";
                            }

                            ///nokia-state/state/system/statistics/ipsec/tunnel-setup-rate/current/start-time
                            leaf start-time {
                                type yang:date-and-time;
                                description "The time when the sampling interval started.";
                            }

                            ///nokia-state/state/system/statistics/ipsec/tunnel-setup-rate/current/sampling-duration
                            leaf sampling-duration {
                                type types-sros:time-duration;
                                description "The duration of the corresponding sampling interval.";
                            }

                        } // container current

                        ///nokia-state/state/system/statistics/ipsec/tunnel-setup-rate/historical
                        list historical {
                            key "index";
                            description "Enter the historical list instance";

                            ///nokia-state/state/system/statistics/ipsec/tunnel-setup-rate/historical/index
                            leaf index {
                                type uint32 {
                                    range "2..max";
                                }
                                description
                                    "The index of the finished sampling interval period for this statistic.
                                     It starts with '2' and is ordered by start time of intervals so that
                                     smaller index indicate more recent intervals.";
                            }

                            ///nokia-state/state/system/statistics/ipsec/tunnel-setup-rate/historical/static-lan-to-lan
                            leaf static-lan-to-lan {
                                type decimal64 {
                                    fraction-digits 2;
                                }
                                units "tunnels per second";
                                description "Static LAN-to-LAN (SL2L) tunnel setup rate.";
                            }

                            ///nokia-state/state/system/statistics/ipsec/tunnel-setup-rate/historical/total
                            leaf total {
                                type decimal64 {
                                    fraction-digits 2;
                                }
                                units "tunnels per second";
                                description "Total IPsec tunnel setup rate.";
                            }

                            ///nokia-state/state/system/statistics/ipsec/tunnel-setup-rate/historical/dynamic-lan-to-lan
                            leaf dynamic-lan-to-lan {
                                type decimal64 {
                                    fraction-digits 2;
                                }
                                units "tunnels per second";
                                description "Dynamic LAN-to-LAN (DL2L) tunnel setup rate.";
                            }

                            ///nokia-state/state/system/statistics/ipsec/tunnel-setup-rate/historical/remote-access
                            leaf remote-access {
                                type decimal64 {
                                    fraction-digits 2;
                                }
                                units "tunnels per second";
                                description "Remote access (RA) tunnel setup rate.";
                            }

                            ///nokia-state/state/system/statistics/ipsec/tunnel-setup-rate/historical/start-time
                            leaf start-time {
                                type yang:date-and-time;
                                description "The time when the sampling interval started.";
                            }

                            ///nokia-state/state/system/statistics/ipsec/tunnel-setup-rate/historical/sampling-duration
                            leaf sampling-duration {
                                type types-sros:time-duration;
                                description "The duration of the corresponding sampling interval.";
                            }

                        } // list historical

                    } // container tunnel-setup-rate

                    ///nokia-state/state/system/statistics/ipsec/ike-exchange-failure-rate
                    container ike-exchange-failure-rate {
                        description "Enter the ike-exchange-failure-rate context";

                        ///nokia-state/state/system/statistics/ipsec/ike-exchange-failure-rate/current
                        container current {
                            description "Enter the current context";

                            ///nokia-state/state/system/statistics/ipsec/ike-exchange-failure-rate/current/start-time
                            leaf start-time {
                                type yang:date-and-time;
                                description "The time when the sampling interval started.";
                            }

                            ///nokia-state/state/system/statistics/ipsec/ike-exchange-failure-rate/current/sampling-duration
                            leaf sampling-duration {
                                type types-sros:time-duration;
                                description "The duration of the corresponding sampling interval.";
                            }

                            ///nokia-state/state/system/statistics/ipsec/ike-exchange-failure-rate/current/auth-failure
                            container auth-failure {
                                description "Enter the auth-failure context";

                                ///nokia-state/state/system/statistics/ipsec/ike-exchange-failure-rate/current/auth-failure/count
                                leaf count {
                                    type decimal64 {
                                        fraction-digits 2;
                                    }
                                    units "failures per second";
                                    description "IKE exchange failure rate - authentication.";
                                }

                                ///nokia-state/state/system/statistics/ipsec/ike-exchange-failure-rate/current/auth-failure/first-failure
                                leaf first-failure {
                                    type yang:date-and-time;
                                    description
                                        "The time when the first IKE exchange failure happened
                                         in the corresponding sampling interval.";
                                }

                                ///nokia-state/state/system/statistics/ipsec/ike-exchange-failure-rate/current/auth-failure/first-failure-description
                                leaf first-failure-description {
                                    type types-sros:long-description;
                                    description "The description of the place where the first IKE exchange failure happened.";
                                }

                                ///nokia-state/state/system/statistics/ipsec/ike-exchange-failure-rate/current/auth-failure/last-failure
                                leaf last-failure {
                                    type yang:date-and-time;
                                    description
                                        "The time when the last IKE exchange failure happened
                                         in the corresponding sampling interval.";
                                }

                                ///nokia-state/state/system/statistics/ipsec/ike-exchange-failure-rate/current/auth-failure/last-failure-description
                                leaf last-failure-description {
                                    type types-sros:long-description;
                                    description "The description of the place where the last IKE exchange failure happened.";
                                }

                            } // container auth-failure

                            ///nokia-state/state/system/statistics/ipsec/ike-exchange-failure-rate/current/non-proposal-chosen
                            container non-proposal-chosen {
                                description "Enter the non-proposal-chosen context";

                                ///nokia-state/state/system/statistics/ipsec/ike-exchange-failure-rate/current/non-proposal-chosen/count
                                leaf count {
                                    type decimal64 {
                                        fraction-digits 2;
                                    }
                                    units "failures per second";
                                    description "IKE exchange failure rate - non-proposal chosen.";
                                }

                                ///nokia-state/state/system/statistics/ipsec/ike-exchange-failure-rate/current/non-proposal-chosen/first-failure
                                leaf first-failure {
                                    type yang:date-and-time;
                                    description
                                        "The time when the first IKE exchange failure happened
                                         in the corresponding sampling interval.";
                                }

                                ///nokia-state/state/system/statistics/ipsec/ike-exchange-failure-rate/current/non-proposal-chosen/first-failure-description
                                leaf first-failure-description {
                                    type types-sros:long-description;
                                    description "The description of the place where the first IKE exchange failure happened.";
                                }

                                ///nokia-state/state/system/statistics/ipsec/ike-exchange-failure-rate/current/non-proposal-chosen/last-failure
                                leaf last-failure {
                                    type yang:date-and-time;
                                    description
                                        "The time when the last IKE exchange failure happened
                                         in the corresponding sampling interval.";
                                }

                                ///nokia-state/state/system/statistics/ipsec/ike-exchange-failure-rate/current/non-proposal-chosen/last-failure-description
                                leaf last-failure-description {
                                    type types-sros:long-description;
                                    description "The description of the place where the last IKE exchange failure happened.";
                                }

                            } // container non-proposal-chosen

                            ///nokia-state/state/system/statistics/ipsec/ike-exchange-failure-rate/current/internal-address-assignment
                            container internal-address-assignment {
                                description "Enter the internal-address-assignment context";

                                ///nokia-state/state/system/statistics/ipsec/ike-exchange-failure-rate/current/internal-address-assignment/count
                                leaf count {
                                    type decimal64 {
                                        fraction-digits 2;
                                    }
                                    units "failures per second";
                                    description "IKE exchange failure rate - address assignment.";
                                }

                                ///nokia-state/state/system/statistics/ipsec/ike-exchange-failure-rate/current/internal-address-assignment/first-failure
                                leaf first-failure {
                                    type yang:date-and-time;
                                    description
                                        "The time when the first IKE exchange failure happened
                                         in the corresponding sampling interval.";
                                }

                                ///nokia-state/state/system/statistics/ipsec/ike-exchange-failure-rate/current/internal-address-assignment/first-failure-description
                                leaf first-failure-description {
                                    type types-sros:long-description;
                                    description "The description of the place where the first IKE exchange failure happened.";
                                }

                                ///nokia-state/state/system/statistics/ipsec/ike-exchange-failure-rate/current/internal-address-assignment/last-failure
                                leaf last-failure {
                                    type yang:date-and-time;
                                    description
                                        "The time when the last IKE exchange failure happened
                                         in the corresponding sampling interval.";
                                }

                                ///nokia-state/state/system/statistics/ipsec/ike-exchange-failure-rate/current/internal-address-assignment/last-failure-description
                                leaf last-failure-description {
                                    type types-sros:long-description;
                                    description "The description of the place where the last IKE exchange failure happened.";
                                }

                            } // container internal-address-assignment

                            ///nokia-state/state/system/statistics/ipsec/ike-exchange-failure-rate/current/invalid-ts
                            container invalid-ts {
                                description "Enter the invalid-ts context";

                                ///nokia-state/state/system/statistics/ipsec/ike-exchange-failure-rate/current/invalid-ts/count
                                leaf count {
                                    type decimal64 {
                                        fraction-digits 2;
                                    }
                                    units "failures per second";
                                    description "IKE exchange failure rate - invalid traffic selector.";
                                }

                                ///nokia-state/state/system/statistics/ipsec/ike-exchange-failure-rate/current/invalid-ts/first-failure
                                leaf first-failure {
                                    type yang:date-and-time;
                                    description
                                        "The time when the first IKE exchange failure happened
                                         in the corresponding sampling interval.";
                                }

                                ///nokia-state/state/system/statistics/ipsec/ike-exchange-failure-rate/current/invalid-ts/first-failure-description
                                leaf first-failure-description {
                                    type types-sros:long-description;
                                    description "The description of the place where the first IKE exchange failure happened.";
                                }

                                ///nokia-state/state/system/statistics/ipsec/ike-exchange-failure-rate/current/invalid-ts/last-failure
                                leaf last-failure {
                                    type yang:date-and-time;
                                    description
                                        "The time when the last IKE exchange failure happened
                                         in the corresponding sampling interval.";
                                }

                                ///nokia-state/state/system/statistics/ipsec/ike-exchange-failure-rate/current/invalid-ts/last-failure-description
                                leaf last-failure-description {
                                    type types-sros:long-description;
                                    description "The description of the place where the last IKE exchange failure happened.";
                                }

                            } // container invalid-ts

                            ///nokia-state/state/system/statistics/ipsec/ike-exchange-failure-rate/current/invalid-ke
                            container invalid-ke {
                                description "Enter the invalid-ke context";

                                ///nokia-state/state/system/statistics/ipsec/ike-exchange-failure-rate/current/invalid-ke/count
                                leaf count {
                                    type decimal64 {
                                        fraction-digits 2;
                                    }
                                    units "failures per second";
                                    description "IKE exchange failure rate - invalid key exchange.";
                                }

                                ///nokia-state/state/system/statistics/ipsec/ike-exchange-failure-rate/current/invalid-ke/first-failure
                                leaf first-failure {
                                    type yang:date-and-time;
                                    description
                                        "The time when the first IKE exchange failure happened
                                         in the corresponding sampling interval.";
                                }

                                ///nokia-state/state/system/statistics/ipsec/ike-exchange-failure-rate/current/invalid-ke/first-failure-description
                                leaf first-failure-description {
                                    type types-sros:long-description;
                                    description "The description of the place where the first IKE exchange failure happened.";
                                }

                                ///nokia-state/state/system/statistics/ipsec/ike-exchange-failure-rate/current/invalid-ke/last-failure
                                leaf last-failure {
                                    type yang:date-and-time;
                                    description
                                        "The time when the last IKE exchange failure happened
                                         in the corresponding sampling interval.";
                                }

                                ///nokia-state/state/system/statistics/ipsec/ike-exchange-failure-rate/current/invalid-ke/last-failure-description
                                leaf last-failure-description {
                                    type types-sros:long-description;
                                    description "The description of the place where the last IKE exchange failure happened.";
                                }

                            } // container invalid-ke

                            ///nokia-state/state/system/statistics/ipsec/ike-exchange-failure-rate/current/dpd-timeout
                            container dpd-timeout {
                                description "Enter the dpd-timeout context";

                                ///nokia-state/state/system/statistics/ipsec/ike-exchange-failure-rate/current/dpd-timeout/count
                                leaf count {
                                    type decimal64 {
                                        fraction-digits 2;
                                    }
                                    units "failures per second";
                                    description "IKE exchange failure rate - DPD timeout.";
                                }

                                ///nokia-state/state/system/statistics/ipsec/ike-exchange-failure-rate/current/dpd-timeout/first-failure
                                leaf first-failure {
                                    type yang:date-and-time;
                                    description
                                        "The time when the first IKE exchange failure happened
                                         in the corresponding sampling interval.";
                                }

                                ///nokia-state/state/system/statistics/ipsec/ike-exchange-failure-rate/current/dpd-timeout/first-failure-description
                                leaf first-failure-description {
                                    type types-sros:long-description;
                                    description "The description of the place where the first IKE exchange failure happened.";
                                }

                                ///nokia-state/state/system/statistics/ipsec/ike-exchange-failure-rate/current/dpd-timeout/last-failure
                                leaf last-failure {
                                    type yang:date-and-time;
                                    description
                                        "The time when the last IKE exchange failure happened
                                         in the corresponding sampling interval.";
                                }

                                ///nokia-state/state/system/statistics/ipsec/ike-exchange-failure-rate/current/dpd-timeout/last-failure-description
                                leaf last-failure-description {
                                    type types-sros:long-description;
                                    description "The description of the place where the last IKE exchange failure happened.";
                                }

                            } // container dpd-timeout

                            ///nokia-state/state/system/statistics/ipsec/ike-exchange-failure-rate/current/other
                            container other {
                                description "Enter the other context";

                                ///nokia-state/state/system/statistics/ipsec/ike-exchange-failure-rate/current/other/count
                                leaf count {
                                    type decimal64 {
                                        fraction-digits 2;
                                    }
                                    units "failures per second";
                                    description "IKE exchange failure rate - other failure reasons.";
                                }

                                ///nokia-state/state/system/statistics/ipsec/ike-exchange-failure-rate/current/other/first-failure
                                leaf first-failure {
                                    type yang:date-and-time;
                                    description
                                        "The time when the first IKE exchange failure happened
                                         in the corresponding sampling interval.";
                                }

                                ///nokia-state/state/system/statistics/ipsec/ike-exchange-failure-rate/current/other/first-failure-description
                                leaf first-failure-description {
                                    type types-sros:long-description;
                                    description "The description of the place where the first IKE exchange failure happened.";
                                }

                                ///nokia-state/state/system/statistics/ipsec/ike-exchange-failure-rate/current/other/last-failure
                                leaf last-failure {
                                    type yang:date-and-time;
                                    description
                                        "The time when the last IKE exchange failure happened
                                         in the corresponding sampling interval.";
                                }

                                ///nokia-state/state/system/statistics/ipsec/ike-exchange-failure-rate/current/other/last-failure-description
                                leaf last-failure-description {
                                    type types-sros:long-description;
                                    description "The description of the place where the last IKE exchange failure happened.";
                                }

                            } // container other

                        } // container current

                        ///nokia-state/state/system/statistics/ipsec/ike-exchange-failure-rate/historical
                        list historical {
                            key "index";
                            description "Enter the historical list instance";

                            ///nokia-state/state/system/statistics/ipsec/ike-exchange-failure-rate/historical/index
                            leaf index {
                                type uint32 {
                                    range "2..max";
                                }
                                description
                                    "The index of the finished sampling interval period for this statistic.
                                     It starts with '2' and is ordered by start time of intervals so that
                                     smaller index indicate more recent intervals.";
                            }

                            ///nokia-state/state/system/statistics/ipsec/ike-exchange-failure-rate/historical/start-time
                            leaf start-time {
                                type yang:date-and-time;
                                description "The time when the sampling interval started.";
                            }

                            ///nokia-state/state/system/statistics/ipsec/ike-exchange-failure-rate/historical/sampling-duration
                            leaf sampling-duration {
                                type types-sros:time-duration;
                                description "The duration of the corresponding sampling interval.";
                            }

                            ///nokia-state/state/system/statistics/ipsec/ike-exchange-failure-rate/historical/auth-failure
                            container auth-failure {
                                description "Enter the auth-failure context";

                                ///nokia-state/state/system/statistics/ipsec/ike-exchange-failure-rate/historical/auth-failure/count
                                leaf count {
                                    type decimal64 {
                                        fraction-digits 2;
                                    }
                                    units "failures per second";
                                    description "IKE exchange failure rate - authentication.";
                                }

                                ///nokia-state/state/system/statistics/ipsec/ike-exchange-failure-rate/historical/auth-failure/first-failure
                                leaf first-failure {
                                    type yang:date-and-time;
                                    description
                                        "The time when the first IKE exchange failure happened
                                         in the corresponding sampling interval.";
                                }

                                ///nokia-state/state/system/statistics/ipsec/ike-exchange-failure-rate/historical/auth-failure/first-failure-description
                                leaf first-failure-description {
                                    type types-sros:long-description;
                                    description "The description of the place where the first IKE exchange failure happened.";
                                }

                                ///nokia-state/state/system/statistics/ipsec/ike-exchange-failure-rate/historical/auth-failure/last-failure
                                leaf last-failure {
                                    type yang:date-and-time;
                                    description
                                        "The time when the last IKE exchange failure happened
                                         in the corresponding sampling interval.";
                                }

                                ///nokia-state/state/system/statistics/ipsec/ike-exchange-failure-rate/historical/auth-failure/last-failure-description
                                leaf last-failure-description {
                                    type types-sros:long-description;
                                    description "The description of the place where the last IKE exchange failure happened.";
                                }

                            } // container auth-failure

                            ///nokia-state/state/system/statistics/ipsec/ike-exchange-failure-rate/historical/non-proposal-chosen
                            container non-proposal-chosen {
                                description "Enter the non-proposal-chosen context";

                                ///nokia-state/state/system/statistics/ipsec/ike-exchange-failure-rate/historical/non-proposal-chosen/count
                                leaf count {
                                    type decimal64 {
                                        fraction-digits 2;
                                    }
                                    units "failures per second";
                                    description "IKE exchange failure rate - non-proposal chosen.";
                                }

                                ///nokia-state/state/system/statistics/ipsec/ike-exchange-failure-rate/historical/non-proposal-chosen/first-failure
                                leaf first-failure {
                                    type yang:date-and-time;
                                    description
                                        "The time when the first IKE exchange failure happened
                                         in the corresponding sampling interval.";
                                }

                                ///nokia-state/state/system/statistics/ipsec/ike-exchange-failure-rate/historical/non-proposal-chosen/first-failure-description
                                leaf first-failure-description {
                                    type types-sros:long-description;
                                    description "The description of the place where the first IKE exchange failure happened.";
                                }

                                ///nokia-state/state/system/statistics/ipsec/ike-exchange-failure-rate/historical/non-proposal-chosen/last-failure
                                leaf last-failure {
                                    type yang:date-and-time;
                                    description
                                        "The time when the last IKE exchange failure happened
                                         in the corresponding sampling interval.";
                                }

                                ///nokia-state/state/system/statistics/ipsec/ike-exchange-failure-rate/historical/non-proposal-chosen/last-failure-description
                                leaf last-failure-description {
                                    type types-sros:long-description;
                                    description "The description of the place where the last IKE exchange failure happened.";
                                }

                            } // container non-proposal-chosen

                            ///nokia-state/state/system/statistics/ipsec/ike-exchange-failure-rate/historical/internal-address-assignment
                            container internal-address-assignment {
                                description "Enter the internal-address-assignment context";

                                ///nokia-state/state/system/statistics/ipsec/ike-exchange-failure-rate/historical/internal-address-assignment/count
                                leaf count {
                                    type decimal64 {
                                        fraction-digits 2;
                                    }
                                    units "failures per second";
                                    description "IKE exchange failure rate - address assignment.";
                                }

                                ///nokia-state/state/system/statistics/ipsec/ike-exchange-failure-rate/historical/internal-address-assignment/first-failure
                                leaf first-failure {
                                    type yang:date-and-time;
                                    description
                                        "The time when the first IKE exchange failure happened
                                         in the corresponding sampling interval.";
                                }

                                ///nokia-state/state/system/statistics/ipsec/ike-exchange-failure-rate/historical/internal-address-assignment/first-failure-description
                                leaf first-failure-description {
                                    type types-sros:long-description;
                                    description "The description of the place where the first IKE exchange failure happened.";
                                }

                                ///nokia-state/state/system/statistics/ipsec/ike-exchange-failure-rate/historical/internal-address-assignment/last-failure
                                leaf last-failure {
                                    type yang:date-and-time;
                                    description
                                        "The time when the last IKE exchange failure happened
                                         in the corresponding sampling interval.";
                                }

                                ///nokia-state/state/system/statistics/ipsec/ike-exchange-failure-rate/historical/internal-address-assignment/last-failure-description
                                leaf last-failure-description {
                                    type types-sros:long-description;
                                    description "The description of the place where the last IKE exchange failure happened.";
                                }

                            } // container internal-address-assignment

                            ///nokia-state/state/system/statistics/ipsec/ike-exchange-failure-rate/historical/invalid-ts
                            container invalid-ts {
                                description "Enter the invalid-ts context";

                                ///nokia-state/state/system/statistics/ipsec/ike-exchange-failure-rate/historical/invalid-ts/count
                                leaf count {
                                    type decimal64 {
                                        fraction-digits 2;
                                    }
                                    units "failures per second";
                                    description "IKE exchange failure rate - invalid traffic selector.";
                                }

                                ///nokia-state/state/system/statistics/ipsec/ike-exchange-failure-rate/historical/invalid-ts/first-failure
                                leaf first-failure {
                                    type yang:date-and-time;
                                    description
                                        "The time when the first IKE exchange failure happened
                                         in the corresponding sampling interval.";
                                }

                                ///nokia-state/state/system/statistics/ipsec/ike-exchange-failure-rate/historical/invalid-ts/first-failure-description
                                leaf first-failure-description {
                                    type types-sros:long-description;
                                    description "The description of the place where the first IKE exchange failure happened.";
                                }

                                ///nokia-state/state/system/statistics/ipsec/ike-exchange-failure-rate/historical/invalid-ts/last-failure
                                leaf last-failure {
                                    type yang:date-and-time;
                                    description
                                        "The time when the last IKE exchange failure happened
                                         in the corresponding sampling interval.";
                                }

                                ///nokia-state/state/system/statistics/ipsec/ike-exchange-failure-rate/historical/invalid-ts/last-failure-description
                                leaf last-failure-description {
                                    type types-sros:long-description;
                                    description "The description of the place where the last IKE exchange failure happened.";
                                }

                            } // container invalid-ts

                            ///nokia-state/state/system/statistics/ipsec/ike-exchange-failure-rate/historical/invalid-ke
                            container invalid-ke {
                                description "Enter the invalid-ke context";

                                ///nokia-state/state/system/statistics/ipsec/ike-exchange-failure-rate/historical/invalid-ke/count
                                leaf count {
                                    type decimal64 {
                                        fraction-digits 2;
                                    }
                                    units "failures per second";
                                    description "IKE exchange failure rate - invalid key exchange.";
                                }

                                ///nokia-state/state/system/statistics/ipsec/ike-exchange-failure-rate/historical/invalid-ke/first-failure
                                leaf first-failure {
                                    type yang:date-and-time;
                                    description
                                        "The time when the first IKE exchange failure happened
                                         in the corresponding sampling interval.";
                                }

                                ///nokia-state/state/system/statistics/ipsec/ike-exchange-failure-rate/historical/invalid-ke/first-failure-description
                                leaf first-failure-description {
                                    type types-sros:long-description;
                                    description "The description of the place where the first IKE exchange failure happened.";
                                }

                                ///nokia-state/state/system/statistics/ipsec/ike-exchange-failure-rate/historical/invalid-ke/last-failure
                                leaf last-failure {
                                    type yang:date-and-time;
                                    description
                                        "The time when the last IKE exchange failure happened
                                         in the corresponding sampling interval.";
                                }

                                ///nokia-state/state/system/statistics/ipsec/ike-exchange-failure-rate/historical/invalid-ke/last-failure-description
                                leaf last-failure-description {
                                    type types-sros:long-description;
                                    description "The description of the place where the last IKE exchange failure happened.";
                                }

                            } // container invalid-ke

                            ///nokia-state/state/system/statistics/ipsec/ike-exchange-failure-rate/historical/dpd-timeout
                            container dpd-timeout {
                                description "Enter the dpd-timeout context";

                                ///nokia-state/state/system/statistics/ipsec/ike-exchange-failure-rate/historical/dpd-timeout/count
                                leaf count {
                                    type decimal64 {
                                        fraction-digits 2;
                                    }
                                    units "failures per second";
                                    description "IKE exchange failure rate - DPD timeout.";
                                }

                                ///nokia-state/state/system/statistics/ipsec/ike-exchange-failure-rate/historical/dpd-timeout/first-failure
                                leaf first-failure {
                                    type yang:date-and-time;
                                    description
                                        "The time when the first IKE exchange failure happened
                                         in the corresponding sampling interval.";
                                }

                                ///nokia-state/state/system/statistics/ipsec/ike-exchange-failure-rate/historical/dpd-timeout/first-failure-description
                                leaf first-failure-description {
                                    type types-sros:long-description;
                                    description "The description of the place where the first IKE exchange failure happened.";
                                }

                                ///nokia-state/state/system/statistics/ipsec/ike-exchange-failure-rate/historical/dpd-timeout/last-failure
                                leaf last-failure {
                                    type yang:date-and-time;
                                    description
                                        "The time when the last IKE exchange failure happened
                                         in the corresponding sampling interval.";
                                }

                                ///nokia-state/state/system/statistics/ipsec/ike-exchange-failure-rate/historical/dpd-timeout/last-failure-description
                                leaf last-failure-description {
                                    type types-sros:long-description;
                                    description "The description of the place where the last IKE exchange failure happened.";
                                }

                            } // container dpd-timeout

                            ///nokia-state/state/system/statistics/ipsec/ike-exchange-failure-rate/historical/other
                            container other {
                                description "Enter the other context";

                                ///nokia-state/state/system/statistics/ipsec/ike-exchange-failure-rate/historical/other/count
                                leaf count {
                                    type decimal64 {
                                        fraction-digits 2;
                                    }
                                    units "failures per second";
                                    description "IKE exchange failure rate - other failure reasons.";
                                }

                                ///nokia-state/state/system/statistics/ipsec/ike-exchange-failure-rate/historical/other/first-failure
                                leaf first-failure {
                                    type yang:date-and-time;
                                    description
                                        "The time when the first IKE exchange failure happened
                                         in the corresponding sampling interval.";
                                }

                                ///nokia-state/state/system/statistics/ipsec/ike-exchange-failure-rate/historical/other/first-failure-description
                                leaf first-failure-description {
                                    type types-sros:long-description;
                                    description "The description of the place where the first IKE exchange failure happened.";
                                }

                                ///nokia-state/state/system/statistics/ipsec/ike-exchange-failure-rate/historical/other/last-failure
                                leaf last-failure {
                                    type yang:date-and-time;
                                    description
                                        "The time when the last IKE exchange failure happened
                                         in the corresponding sampling interval.";
                                }

                                ///nokia-state/state/system/statistics/ipsec/ike-exchange-failure-rate/historical/other/last-failure-description
                                leaf last-failure-description {
                                    type types-sros:long-description;
                                    description "The description of the place where the last IKE exchange failure happened.";
                                }

                            } // container other

                        } // list historical

                    } // container ike-exchange-failure-rate

                } // container ipsec

            } // container statistics


            ///nokia-state/state/system/resource-usage
            container resource-usage {
                description "Enter the resource-usage context";

                ///nokia-state/state/system/resource-usage/sap-ingress-qos-policies
                container sap-ingress-qos-policies {
                    description "Enter the sap-ingress-qos-policies context";

                    ///nokia-state/state/system/resource-usage/sap-ingress-qos-policies/total
                    leaf total {
                        type yang:counter32;
                        description "The total number of resources supported on this system.";
                    }

                    ///nokia-state/state/system/resource-usage/sap-ingress-qos-policies/allocated
                    leaf allocated {
                        type yang:counter32;
                        description "The total number of resources that are currently allocated on this system.";
                    }

                    ///nokia-state/state/system/resource-usage/sap-ingress-qos-policies/free
                    leaf free {
                        type yang:counter32;
                        description "The total number of resources that are remaining free on this system.";
                    }

                } // container sap-ingress-qos-policies

                ///nokia-state/state/system/resource-usage/sap-egress-qos-policies
                container sap-egress-qos-policies {
                    description "Enter the sap-egress-qos-policies context";

                    ///nokia-state/state/system/resource-usage/sap-egress-qos-policies/total
                    leaf total {
                        type yang:counter32;
                        description "The total number of resources supported on this system.";
                    }

                    ///nokia-state/state/system/resource-usage/sap-egress-qos-policies/allocated
                    leaf allocated {
                        type yang:counter32;
                        description "The total number of resources that are currently allocated on this system.";
                    }

                    ///nokia-state/state/system/resource-usage/sap-egress-qos-policies/free
                    leaf free {
                        type yang:counter32;
                        description "The total number of resources that are remaining free on this system.";
                    }

                } // container sap-egress-qos-policies

                ///nokia-state/state/system/resource-usage/ingress-queue-group-templates
                container ingress-queue-group-templates {
                    description "Enter the ingress-queue-group-templates context";

                    ///nokia-state/state/system/resource-usage/ingress-queue-group-templates/total
                    leaf total {
                        type yang:counter32;
                        description "The total number of resources supported on this system.";
                    }

                    ///nokia-state/state/system/resource-usage/ingress-queue-group-templates/allocated
                    leaf allocated {
                        type yang:counter32;
                        description "The total number of resources that are currently allocated on this system.";
                    }

                    ///nokia-state/state/system/resource-usage/ingress-queue-group-templates/free
                    leaf free {
                        type yang:counter32;
                        description "The total number of resources that are remaining free on this system.";
                    }

                } // container ingress-queue-group-templates

                ///nokia-state/state/system/resource-usage/egress-queue-group-templates
                container egress-queue-group-templates {
                    description "Enter the egress-queue-group-templates context";

                    ///nokia-state/state/system/resource-usage/egress-queue-group-templates/total
                    leaf total {
                        type yang:counter32;
                        description "The total number of resources supported on this system.";
                    }

                    ///nokia-state/state/system/resource-usage/egress-queue-group-templates/allocated
                    leaf allocated {
                        type yang:counter32;
                        description "The total number of resources that are currently allocated on this system.";
                    }

                    ///nokia-state/state/system/resource-usage/egress-queue-group-templates/free
                    leaf free {
                        type yang:counter32;
                        description "The total number of resources that are remaining free on this system.";
                    }

                } // container egress-queue-group-templates

                ///nokia-state/state/system/resource-usage/egress-port-queue-group-instances
                container egress-port-queue-group-instances {
                    description "Enter the egress-port-queue-group-instances context";

                    ///nokia-state/state/system/resource-usage/egress-port-queue-group-instances/total
                    leaf total {
                        type yang:counter32;
                        description "The total number of resources supported on this system.";
                    }

                    ///nokia-state/state/system/resource-usage/egress-port-queue-group-instances/allocated
                    leaf allocated {
                        type yang:counter32;
                        description "The total number of resources that are currently allocated on this system.";
                    }

                    ///nokia-state/state/system/resource-usage/egress-port-queue-group-instances/free
                    leaf free {
                        type yang:counter32;
                        description "The total number of resources that are remaining free on this system.";
                    }

                } // container egress-port-queue-group-instances

                ///nokia-state/state/system/resource-usage/ingress-fp-queue-group-instances
                container ingress-fp-queue-group-instances {
                    description "Enter the ingress-fp-queue-group-instances context";

                    ///nokia-state/state/system/resource-usage/ingress-fp-queue-group-instances/total
                    leaf total {
                        type yang:counter32;
                        description "The total number of resources supported on this system.";
                    }

                    ///nokia-state/state/system/resource-usage/ingress-fp-queue-group-instances/allocated
                    leaf allocated {
                        type yang:counter32;
                        description "The total number of resources that are currently allocated on this system.";
                    }

                    ///nokia-state/state/system/resource-usage/ingress-fp-queue-group-instances/free
                    leaf free {
                        type yang:counter32;
                        description "The total number of resources that are remaining free on this system.";
                    }

                } // container ingress-fp-queue-group-instances

                ///nokia-state/state/system/resource-usage/egress-port-vport
                container egress-port-vport {
                    description "Enter the egress-port-vport context";

                    ///nokia-state/state/system/resource-usage/egress-port-vport/total
                    leaf total {
                        type yang:counter32;
                        description "The total number of resources supported on this system.";
                    }

                    ///nokia-state/state/system/resource-usage/egress-port-vport/allocated
                    leaf allocated {
                        type yang:counter32;
                        description "The total number of resources that are currently allocated on this system.";
                    }

                    ///nokia-state/state/system/resource-usage/egress-port-vport/free
                    leaf free {
                        type yang:counter32;
                        description "The total number of resources that are remaining free on this system.";
                    }

                } // container egress-port-vport

                ///nokia-state/state/system/resource-usage/fast-depth-monitored-queues
                container fast-depth-monitored-queues {
                    description "Enter the fast-depth-monitored-queues context";

                    ///nokia-state/state/system/resource-usage/fast-depth-monitored-queues/total
                    leaf total {
                        type yang:counter32;
                        description "The total number of resources supported on this system.";
                    }

                    ///nokia-state/state/system/resource-usage/fast-depth-monitored-queues/allocated
                    leaf allocated {
                        type yang:counter32;
                        description "The total number of resources that are currently allocated on this system.";
                    }

                    ///nokia-state/state/system/resource-usage/fast-depth-monitored-queues/free
                    leaf free {
                        type yang:counter32;
                        description "The total number of resources that are remaining free on this system.";
                    }

                } // container fast-depth-monitored-queues

                ///nokia-state/state/system/resource-usage/input-output-capacity
                container input-output-capacity {
                    description "Enter the input-output-capacity context";

                    ///nokia-state/state/system/resource-usage/input-output-capacity/total
                    leaf total {
                        type yang:counter32;
                        description "The total number of resources supported on this system.";
                    }

                    ///nokia-state/state/system/resource-usage/input-output-capacity/allocated
                    leaf allocated {
                        type yang:counter32;
                        description "The total number of resources that are currently allocated on this system.";
                    }

                    ///nokia-state/state/system/resource-usage/input-output-capacity/free
                    leaf free {
                        type yang:counter32;
                        description "The total number of resources that are remaining free on this system.";
                    }

                } // container input-output-capacity

                ///nokia-state/state/system/resource-usage/dynamic-services-next-hop-entries
                container dynamic-services-next-hop-entries {
                    description "Enter the dynamic-services-next-hop-entries context";

                    ///nokia-state/state/system/resource-usage/dynamic-services-next-hop-entries/total
                    leaf total {
                        type yang:counter32;
                        description "The total number of resources supported on this system.";
                    }

                    ///nokia-state/state/system/resource-usage/dynamic-services-next-hop-entries/allocated
                    leaf allocated {
                        type yang:counter32;
                        description "The total number of resources that are currently allocated on this system.";
                    }

                    ///nokia-state/state/system/resource-usage/dynamic-services-next-hop-entries/free
                    leaf free {
                        type yang:counter32;
                        description "The total number of resources that are remaining free on this system.";
                    }

                } // container dynamic-services-next-hop-entries

                ///nokia-state/state/system/resource-usage/ipsec-next-hop-entries
                container ipsec-next-hop-entries {
                    description "Enter the ipsec-next-hop-entries context";

                    ///nokia-state/state/system/resource-usage/ipsec-next-hop-entries/total
                    leaf total {
                        type yang:counter32;
                        description "The total number of resources supported on this system.";
                    }

                    ///nokia-state/state/system/resource-usage/ipsec-next-hop-entries/allocated
                    leaf allocated {
                        type yang:counter32;
                        description "The total number of resources that are currently allocated on this system.";
                    }

                    ///nokia-state/state/system/resource-usage/ipsec-next-hop-entries/free
                    leaf free {
                        type yang:counter32;
                        description "The total number of resources that are remaining free on this system.";
                    }

                } // container ipsec-next-hop-entries

                ///nokia-state/state/system/resource-usage/subscriber-next-hop-entries
                container subscriber-next-hop-entries {
                    description "Enter the subscriber-next-hop-entries context";

                    ///nokia-state/state/system/resource-usage/subscriber-next-hop-entries/total
                    leaf total {
                        type yang:counter32;
                        description "The total number of resources supported on this system.";
                    }

                    ///nokia-state/state/system/resource-usage/subscriber-next-hop-entries/allocated
                    leaf allocated {
                        type yang:counter32;
                        description "The total number of resources that are currently allocated on this system.";
                    }

                    ///nokia-state/state/system/resource-usage/subscriber-next-hop-entries/free
                    leaf free {
                        type yang:counter32;
                        description "The total number of resources that are remaining free on this system.";
                    }

                } // container subscriber-next-hop-entries

                ///nokia-state/state/system/resource-usage/sap
                container sap {
                    description "Enter the sap context";

                    ///nokia-state/state/system/resource-usage/sap/total
                    leaf total {
                        type uint32;
                        description "Total number of SAPs available in the system.";
                    }

                    ///nokia-state/state/system/resource-usage/sap/allocated
                    leaf allocated {
                        type uint32;
                        description "Total number of SAPs allocated in the system.";
                    }

                    ///nokia-state/state/system/resource-usage/sap/free
                    leaf free {
                        type uint32;
                        description "total number of SAPs free in the system.";
                    }

                    ///nokia-state/state/system/resource-usage/sap/cpipe
                    container cpipe {
                        description "Enter the cpipe context";

                        ///nokia-state/state/system/resource-usage/sap/cpipe/allocated
                        leaf allocated {
                            type uint32;
                            description "Total number of SAPs per service allocated in the system.";
                        }

                    } // container cpipe

                    ///nokia-state/state/system/resource-usage/sap/epipe
                    container epipe {
                        description "Enter the epipe context";

                        ///nokia-state/state/system/resource-usage/sap/epipe/allocated
                        leaf allocated {
                            type uint32;
                            description "Total number of SAPs per service allocated in the system.";
                        }

                    } // container epipe

                    ///nokia-state/state/system/resource-usage/sap/ipipe
                    container ipipe {
                        description "Enter the ipipe context";

                        ///nokia-state/state/system/resource-usage/sap/ipipe/allocated
                        leaf allocated {
                            type uint32;
                            description "Total number of SAPs per service allocated in the system.";
                        }

                    } // container ipipe

                    ///nokia-state/state/system/resource-usage/sap/ies
                    container ies {
                        description "Enter the ies context";

                        ///nokia-state/state/system/resource-usage/sap/ies/allocated
                        leaf allocated {
                            type uint32;
                            description "Total number of SAPs per service allocated in the system.";
                        }

                    } // container ies

                    ///nokia-state/state/system/resource-usage/sap/mirror
                    container mirror {
                        description "Enter the mirror context";

                        ///nokia-state/state/system/resource-usage/sap/mirror/allocated
                        leaf allocated {
                            type uint32;
                            description "Total number of SAPs per service allocated in the system.";
                        }

                    } // container mirror

                    ///nokia-state/state/system/resource-usage/sap/vpls
                    container vpls {
                        description "Enter the vpls context";

                        ///nokia-state/state/system/resource-usage/sap/vpls/allocated
                        leaf allocated {
                            type uint32;
                            description "Total number of SAPs per service allocated in the system.";
                        }

                    } // container vpls

                    ///nokia-state/state/system/resource-usage/sap/vprn
                    container vprn {
                        description "Enter the vprn context";

                        ///nokia-state/state/system/resource-usage/sap/vprn/allocated
                        leaf allocated {
                            type uint32;
                            description "Total number of SAPs per service allocated in the system.";
                        }

                    } // container vprn

                } // container sap

                ///nokia-state/state/system/resource-usage/service
                container service {
                    description "Enter the service context";

                    ///nokia-state/state/system/resource-usage/service/cpipe
                    container cpipe {
                        description "Enter the cpipe context";

                        ///nokia-state/state/system/resource-usage/service/cpipe/allocated
                        leaf allocated {
                            type uint32;
                            description "Total number of services allocated in the system.";
                        }

                    } // container cpipe

                    ///nokia-state/state/system/resource-usage/service/epipe
                    container epipe {
                        description "Enter the epipe context";

                        ///nokia-state/state/system/resource-usage/service/epipe/allocated
                        leaf allocated {
                            type uint32;
                            description "Total number of services allocated in the system.";
                        }

                    } // container epipe

                    ///nokia-state/state/system/resource-usage/service/ipipe
                    container ipipe {
                        description "Enter the ipipe context";

                        ///nokia-state/state/system/resource-usage/service/ipipe/allocated
                        leaf allocated {
                            type uint32;
                            description "Total number of services allocated in the system.";
                        }

                    } // container ipipe

                    ///nokia-state/state/system/resource-usage/service/ies
                    container ies {
                        description "Enter the ies context";

                        ///nokia-state/state/system/resource-usage/service/ies/allocated
                        leaf allocated {
                            type uint32;
                            description "Total number of services allocated in the system.";
                        }

                    } // container ies

                    ///nokia-state/state/system/resource-usage/service/mirror
                    container mirror {
                        description "Enter the mirror context";

                        ///nokia-state/state/system/resource-usage/service/mirror/allocated
                        leaf allocated {
                            type uint32;
                            description "Total number of services allocated in the system.";
                        }

                    } // container mirror

                    ///nokia-state/state/system/resource-usage/service/vpls
                    container vpls {
                        description "Enter the vpls context";

                        ///nokia-state/state/system/resource-usage/service/vpls/allocated
                        leaf allocated {
                            type uint32;
                            description "Total number of services allocated in the system.";
                        }

                    } // container vpls

                    ///nokia-state/state/system/resource-usage/service/vprn
                    container vprn {
                        description "Enter the vprn context";

                        ///nokia-state/state/system/resource-usage/service/vprn/allocated
                        leaf allocated {
                            type uint32;
                            description "Total number of services allocated in the system.";
                        }

                    } // container vprn

                } // container service

                ///nokia-state/state/system/resource-usage/ixr
                container ixr {
                    description "Enter the ixr context";

                    ///nokia-state/state/system/resource-usage/ixr/common-lif
                    container common-lif {
                        description "Enter the common-lif context";

                        ///nokia-state/state/system/resource-usage/ixr/common-lif/total
                        leaf total {
                            type yang:counter32;
                            description "The total number of resources.";
                        }

                        ///nokia-state/state/system/resource-usage/ixr/common-lif/allocated
                        leaf allocated {
                            type yang:counter32;
                            description "The number of resources that are currently allocated.";
                        }

                        ///nokia-state/state/system/resource-usage/ixr/common-lif/free
                        leaf free {
                            type yang:counter32;
                            description "The number of free resources that are currently available.";
                        }

                        ///nokia-state/state/system/resource-usage/ixr/common-lif/by-owner
                        list by-owner {
                            key "owner";
                            description "Enter the by-owner list instance";

                            ///nokia-state/state/system/resource-usage/ixr/common-lif/by-owner/owner
                            leaf owner {
                                type types-system:ixr-resource-index-owner;
                                description "Application that uses the pool resources.";
                            }

                            ///nokia-state/state/system/resource-usage/ixr/common-lif/by-owner/total
                            leaf total {
                                type yang:counter32;
                                description "The total number of resources.";
                            }

                            ///nokia-state/state/system/resource-usage/ixr/common-lif/by-owner/allocated
                            leaf allocated {
                                type yang:counter32;
                                description "The number of resources that are currently allocated.";
                            }

                            ///nokia-state/state/system/resource-usage/ixr/common-lif/by-owner/free
                            leaf free {
                                type yang:counter32;
                                description "The number of free resources that are currently available.";
                            }

                        } // list by-owner

                    } // container common-lif

                    ///nokia-state/state/system/resource-usage/ixr/arp-lif
                    container arp-lif {
                        description "Enter the arp-lif context";

                        ///nokia-state/state/system/resource-usage/ixr/arp-lif/total
                        leaf total {
                            type yang:counter32;
                            description "The total number of resources.";
                        }

                        ///nokia-state/state/system/resource-usage/ixr/arp-lif/allocated
                        leaf allocated {
                            type yang:counter32;
                            description "The number of resources that are currently allocated.";
                        }

                        ///nokia-state/state/system/resource-usage/ixr/arp-lif/free
                        leaf free {
                            type yang:counter32;
                            description "The number of free resources that are currently available.";
                        }

                        ///nokia-state/state/system/resource-usage/ixr/arp-lif/by-owner
                        list by-owner {
                            key "owner";
                            description "Enter the by-owner list instance";

                            ///nokia-state/state/system/resource-usage/ixr/arp-lif/by-owner/owner
                            leaf owner {
                                type types-system:ixr-resource-index-owner;
                                description "Application that uses the pool resources.";
                            }

                            ///nokia-state/state/system/resource-usage/ixr/arp-lif/by-owner/allocated
                            leaf allocated {
                                type yang:counter32;
                                description "The number of resources that are currently allocated.";
                            }

                        } // list by-owner

                    } // container arp-lif

                    ///nokia-state/state/system/resource-usage/ixr/mpls-lif
                    container mpls-lif {
                        description "Enter the mpls-lif context";

                        ///nokia-state/state/system/resource-usage/ixr/mpls-lif/total
                        leaf total {
                            type yang:counter32;
                            description "The total number of resources.";
                        }

                        ///nokia-state/state/system/resource-usage/ixr/mpls-lif/allocated
                        leaf allocated {
                            type yang:counter32;
                            description "The number of resources that are currently allocated.";
                        }

                        ///nokia-state/state/system/resource-usage/ixr/mpls-lif/free
                        leaf free {
                            type yang:counter32;
                            description "The number of free resources that are currently available.";
                        }

                        ///nokia-state/state/system/resource-usage/ixr/mpls-lif/by-owner
                        list by-owner {
                            key "owner";
                            description "Enter the by-owner list instance";

                            ///nokia-state/state/system/resource-usage/ixr/mpls-lif/by-owner/owner
                            leaf owner {
                                type types-system:ixr-resource-index-owner;
                                description "Application that uses the pool resources.";
                            }

                            ///nokia-state/state/system/resource-usage/ixr/mpls-lif/by-owner/allocated
                            leaf allocated {
                                type yang:counter32;
                                description "The number of resources that are currently allocated.";
                            }

                        } // list by-owner

                    } // container mpls-lif

                    ///nokia-state/state/system/resource-usage/ixr/l3-vsi-rif
                    container l3-vsi-rif {
                        description "Enter the l3-vsi-rif context";

                        ///nokia-state/state/system/resource-usage/ixr/l3-vsi-rif/total
                        leaf total {
                            type yang:counter32;
                            description "The total number of resources.";
                        }

                        ///nokia-state/state/system/resource-usage/ixr/l3-vsi-rif/allocated
                        leaf allocated {
                            type yang:counter32;
                            description "The number of resources that are currently allocated.";
                        }

                        ///nokia-state/state/system/resource-usage/ixr/l3-vsi-rif/free
                        leaf free {
                            type yang:counter32;
                            description "The number of free resources that are currently available.";
                        }

                        ///nokia-state/state/system/resource-usage/ixr/l3-vsi-rif/by-owner
                        list by-owner {
                            key "owner";
                            description "Enter the by-owner list instance";

                            ///nokia-state/state/system/resource-usage/ixr/l3-vsi-rif/by-owner/owner
                            leaf owner {
                                type types-system:ixr-resource-index-owner;
                                description "Application that uses the pool resources.";
                            }

                            ///nokia-state/state/system/resource-usage/ixr/l3-vsi-rif/by-owner/allocated
                            leaf allocated {
                                type yang:counter32;
                                description "The number of resources that are currently allocated.";
                            }

                        } // list by-owner

                    } // container l3-vsi-rif

                    ///nokia-state/state/system/resource-usage/ixr/fec-system-wide
                    container fec-system-wide {
                        description "Enter the fec-system-wide context";

                        ///nokia-state/state/system/resource-usage/ixr/fec-system-wide/unpaired
                        container unpaired {
                            description "Enter the unpaired context";

                            ///nokia-state/state/system/resource-usage/ixr/fec-system-wide/unpaired/total
                            leaf total {
                                type yang:counter32;
                                description "The total number of resources.";
                            }

                            ///nokia-state/state/system/resource-usage/ixr/fec-system-wide/unpaired/allocated
                            leaf allocated {
                                type yang:counter32;
                                description "The number of resources that are currently allocated.";
                            }

                            ///nokia-state/state/system/resource-usage/ixr/fec-system-wide/unpaired/free
                            leaf free {
                                type yang:counter32;
                                description "The number of free resources that are currently available.";
                            }

                            ///nokia-state/state/system/resource-usage/ixr/fec-system-wide/unpaired/by-owner
                            list by-owner {
                                key "owner";
                                description "Enter the by-owner list instance";

                                ///nokia-state/state/system/resource-usage/ixr/fec-system-wide/unpaired/by-owner/owner
                                leaf owner {
                                    type types-system:ixr-resource-index-owner;
                                    description "Application that uses the pool resources.";
                                }

                                ///nokia-state/state/system/resource-usage/ixr/fec-system-wide/unpaired/by-owner/allocated
                                leaf allocated {
                                    type yang:counter32;
                                    description "The number of resources that are currently allocated.";
                                }

                            } // list by-owner

                        } // container unpaired

                        ///nokia-state/state/system/resource-usage/ixr/fec-system-wide/paired
                        container paired {
                            description "Enter the paired context";

                            ///nokia-state/state/system/resource-usage/ixr/fec-system-wide/paired/total
                            leaf total {
                                type yang:counter32;
                                description "The total number of resources.";
                            }

                            ///nokia-state/state/system/resource-usage/ixr/fec-system-wide/paired/allocated
                            leaf allocated {
                                type yang:counter32;
                                description "The number of resources that are currently allocated.";
                            }

                            ///nokia-state/state/system/resource-usage/ixr/fec-system-wide/paired/free
                            leaf free {
                                type yang:counter32;
                                description "The number of free resources that are currently available.";
                            }

                            ///nokia-state/state/system/resource-usage/ixr/fec-system-wide/paired/by-owner
                            list by-owner {
                                key "owner";
                                description "Enter the by-owner list instance";

                                ///nokia-state/state/system/resource-usage/ixr/fec-system-wide/paired/by-owner/owner
                                leaf owner {
                                    type types-system:ixr-resource-index-owner;
                                    description "Application that uses the pool resources.";
                                }

                                ///nokia-state/state/system/resource-usage/ixr/fec-system-wide/paired/by-owner/allocated
                                leaf allocated {
                                    type yang:counter32;
                                    description "The number of resources that are currently allocated.";
                                }

                            } // list by-owner

                        } // container paired

                    } // container fec-system-wide

                    ///nokia-state/state/system/resource-usage/ixr/oam-lm-ctr-id
                    container oam-lm-ctr-id {
                        description "Enter the oam-lm-ctr-id context";

                        ///nokia-state/state/system/resource-usage/ixr/oam-lm-ctr-id/total
                        leaf total {
                            type yang:counter32;
                            description "The total number of resources.";
                        }

                        ///nokia-state/state/system/resource-usage/ixr/oam-lm-ctr-id/allocated
                        leaf allocated {
                            type yang:counter32;
                            description "The number of resources that are currently allocated.";
                        }

                        ///nokia-state/state/system/resource-usage/ixr/oam-lm-ctr-id/free
                        leaf free {
                            type yang:counter32;
                            description "The number of free resources that are currently available.";
                        }

                        ///nokia-state/state/system/resource-usage/ixr/oam-lm-ctr-id/by-owner
                        list by-owner {
                            key "owner";
                            description "Enter the by-owner list instance";

                            ///nokia-state/state/system/resource-usage/ixr/oam-lm-ctr-id/by-owner/owner
                            leaf owner {
                                type types-system:ixr-resource-index-owner;
                                description "Application that uses the pool resources.";
                            }

                            ///nokia-state/state/system/resource-usage/ixr/oam-lm-ctr-id/by-owner/allocated
                            leaf allocated {
                                type yang:counter32;
                                description "The number of resources that are currently allocated.";
                            }

                        } // list by-owner

                    } // container oam-lm-ctr-id

                    ///nokia-state/state/system/resource-usage/ixr/ingress-classification-policies
                    container ingress-classification-policies {
                        description "Enter the ingress-classification-policies context";

                        ///nokia-state/state/system/resource-usage/ixr/ingress-classification-policies/total
                        leaf total {
                            type yang:counter32;
                            description "The total number of resources supported on this system.";
                        }

                        ///nokia-state/state/system/resource-usage/ixr/ingress-classification-policies/allocated
                        leaf allocated {
                            type yang:counter32;
                            description "The total number of resources that are currently allocated on this system.";
                        }

                        ///nokia-state/state/system/resource-usage/ixr/ingress-classification-policies/free
                        leaf free {
                            type yang:counter32;
                            description "The total number of resources that are remaining free on this system.";
                        }

                    } // container ingress-classification-policies

                    ///nokia-state/state/system/resource-usage/ixr/dot1p-fc-maps
                    container dot1p-fc-maps {
                        description "Enter the dot1p-fc-maps context";

                        ///nokia-state/state/system/resource-usage/ixr/dot1p-fc-maps/total
                        leaf total {
                            type yang:counter32;
                            description "The total number of resources supported on this system.";
                        }

                        ///nokia-state/state/system/resource-usage/ixr/dot1p-fc-maps/allocated
                        leaf allocated {
                            type yang:counter32;
                            description "The total number of resources that are currently allocated on this system.";
                        }

                        ///nokia-state/state/system/resource-usage/ixr/dot1p-fc-maps/free
                        leaf free {
                            type yang:counter32;
                            description "The total number of resources that are remaining free on this system.";
                        }

                    } // container dot1p-fc-maps

                    ///nokia-state/state/system/resource-usage/ixr/dscp-fc-maps
                    container dscp-fc-maps {
                        description "Enter the dscp-fc-maps context";

                        ///nokia-state/state/system/resource-usage/ixr/dscp-fc-maps/total
                        leaf total {
                            type yang:counter32;
                            description "The total number of resources supported on this system.";
                        }

                        ///nokia-state/state/system/resource-usage/ixr/dscp-fc-maps/allocated
                        leaf allocated {
                            type yang:counter32;
                            description "The total number of resources that are currently allocated on this system.";
                        }

                        ///nokia-state/state/system/resource-usage/ixr/dscp-fc-maps/free
                        leaf free {
                            type yang:counter32;
                            description "The total number of resources that are remaining free on this system.";
                        }

                    } // container dscp-fc-maps

                    ///nokia-state/state/system/resource-usage/ixr/lsp-exp-fc-maps
                    container lsp-exp-fc-maps {
                        description "Enter the lsp-exp-fc-maps context";

                        ///nokia-state/state/system/resource-usage/ixr/lsp-exp-fc-maps/total
                        leaf total {
                            type yang:counter32;
                            description "The total number of resources supported on this system.";
                        }

                        ///nokia-state/state/system/resource-usage/ixr/lsp-exp-fc-maps/allocated
                        leaf allocated {
                            type yang:counter32;
                            description "The total number of resources that are currently allocated on this system.";
                        }

                        ///nokia-state/state/system/resource-usage/ixr/lsp-exp-fc-maps/free
                        leaf free {
                            type yang:counter32;
                            description "The total number of resources that are remaining free on this system.";
                        }

                    } // container lsp-exp-fc-maps

                    ///nokia-state/state/system/resource-usage/ixr/egress-remark-policies
                    container egress-remark-policies {
                        description "Enter the egress-remark-policies context";

                        ///nokia-state/state/system/resource-usage/ixr/egress-remark-policies/total
                        leaf total {
                            type yang:counter32;
                            description "The total number of resources supported on this system.";
                        }

                        ///nokia-state/state/system/resource-usage/ixr/egress-remark-policies/allocated
                        leaf allocated {
                            type yang:counter32;
                            description "The total number of resources that are currently allocated on this system.";
                        }

                        ///nokia-state/state/system/resource-usage/ixr/egress-remark-policies/free
                        leaf free {
                            type yang:counter32;
                            description "The total number of resources that are remaining free on this system.";
                        }

                    } // container egress-remark-policies

                    ///nokia-state/state/system/resource-usage/ixr/fc-dot1p-maps
                    container fc-dot1p-maps {
                        description "Enter the fc-dot1p-maps context";

                        ///nokia-state/state/system/resource-usage/ixr/fc-dot1p-maps/total
                        leaf total {
                            type yang:counter32;
                            description "The total number of resources supported on this system.";
                        }

                        ///nokia-state/state/system/resource-usage/ixr/fc-dot1p-maps/allocated
                        leaf allocated {
                            type yang:counter32;
                            description "The total number of resources that are currently allocated on this system.";
                        }

                        ///nokia-state/state/system/resource-usage/ixr/fc-dot1p-maps/free
                        leaf free {
                            type yang:counter32;
                            description "The total number of resources that are remaining free on this system.";
                        }

                    } // container fc-dot1p-maps

                    ///nokia-state/state/system/resource-usage/ixr/fc-dscp-maps
                    container fc-dscp-maps {
                        description "Enter the fc-dscp-maps context";

                        ///nokia-state/state/system/resource-usage/ixr/fc-dscp-maps/total
                        leaf total {
                            type yang:counter32;
                            description "The total number of resources supported on this system.";
                        }

                        ///nokia-state/state/system/resource-usage/ixr/fc-dscp-maps/allocated
                        leaf allocated {
                            type yang:counter32;
                            description "The total number of resources that are currently allocated on this system.";
                        }

                        ///nokia-state/state/system/resource-usage/ixr/fc-dscp-maps/free
                        leaf free {
                            type yang:counter32;
                            description "The total number of resources that are remaining free on this system.";
                        }

                    } // container fc-dscp-maps

                    ///nokia-state/state/system/resource-usage/ixr/fc-lsp-exp-maps
                    container fc-lsp-exp-maps {
                        description "Enter the fc-lsp-exp-maps context";

                        ///nokia-state/state/system/resource-usage/ixr/fc-lsp-exp-maps/total
                        leaf total {
                            type yang:counter32;
                            description "The total number of resources supported on this system.";
                        }

                        ///nokia-state/state/system/resource-usage/ixr/fc-lsp-exp-maps/allocated
                        leaf allocated {
                            type yang:counter32;
                            description "The total number of resources that are currently allocated on this system.";
                        }

                        ///nokia-state/state/system/resource-usage/ixr/fc-lsp-exp-maps/free
                        leaf free {
                            type yang:counter32;
                            description "The total number of resources that are remaining free on this system.";
                        }

                    } // container fc-lsp-exp-maps

                    ///nokia-state/state/system/resource-usage/ixr/queue-mgmt-policies
                    container queue-mgmt-policies {
                        description "Enter the queue-mgmt-policies context";

                        ///nokia-state/state/system/resource-usage/ixr/queue-mgmt-policies/total
                        leaf total {
                            type yang:counter32;
                            description "The total number of resources supported on this system.";
                        }

                        ///nokia-state/state/system/resource-usage/ixr/queue-mgmt-policies/allocated
                        leaf allocated {
                            type yang:counter32;
                            description "The total number of resources that are currently allocated on this system.";
                        }

                        ///nokia-state/state/system/resource-usage/ixr/queue-mgmt-policies/free
                        leaf free {
                            type yang:counter32;
                            description "The total number of resources that are remaining free on this system.";
                        }

                    } // container queue-mgmt-policies

                    ///nokia-state/state/system/resource-usage/ixr/vlan-qos-voq-with-statistics
                    container vlan-qos-voq-with-statistics {
                        description "Enter the vlan-qos-voq-with-statistics context";

                        ///nokia-state/state/system/resource-usage/ixr/vlan-qos-voq-with-statistics/total
                        leaf total {
                            type yang:counter32;
                            description "The total number of resources supported on this system.";
                        }

                        ///nokia-state/state/system/resource-usage/ixr/vlan-qos-voq-with-statistics/allocated
                        leaf allocated {
                            type yang:counter32;
                            description "The total number of resources that are currently allocated on this system.";
                        }

                        ///nokia-state/state/system/resource-usage/ixr/vlan-qos-voq-with-statistics/free
                        leaf free {
                            type yang:counter32;
                            description "The total number of resources that are remaining free on this system.";
                        }

                    } // container vlan-qos-voq-with-statistics

                    ///nokia-state/state/system/resource-usage/ixr/vlan-qos-voq-without-statistics
                    container vlan-qos-voq-without-statistics {
                        description "Enter the vlan-qos-voq-without-statistics context";

                        ///nokia-state/state/system/resource-usage/ixr/vlan-qos-voq-without-statistics/total
                        leaf total {
                            type yang:counter32;
                            description "The total number of resources supported on this system.";
                        }

                        ///nokia-state/state/system/resource-usage/ixr/vlan-qos-voq-without-statistics/allocated
                        leaf allocated {
                            type yang:counter32;
                            description "The total number of resources that are currently allocated on this system.";
                        }

                        ///nokia-state/state/system/resource-usage/ixr/vlan-qos-voq-without-statistics/free
                        leaf free {
                            type yang:counter32;
                            description "The total number of resources that are remaining free on this system.";
                        }

                    } // container vlan-qos-voq-without-statistics

                } // container ixr

            } // container resource-usage

            ///nokia-state/state/system/switch-fabric
            container switch-fabric {
                description "Enter the switch-fabric context";

                ///nokia-state/state/system/switch-fabric/failure-recovery
                container failure-recovery {
                    description "Enter the failure-recovery context";

                    ///nokia-state/state/system/switch-fabric/failure-recovery/oper-state
                    leaf oper-state {
                        type enumeration {
                            enum disabled                       { value 0; }
                            enum hold-down                      { value 1; }
                            enum ready                          { value 2; }
                            enum recovery-in-progress           { value 3; }
                            enum detected-disabled              { value 4; }
                            enum detected-hold-down             { value 5; }
                            enum detected-xrs40-migration       { value 6; }
                            enum detected-sfm-upgrade-pending   { value 7; }
                        }
                        description
                            "Indicates the operational state of the automatic switch fabric
                             failure recovery process.";
                    }

                    ///nokia-state/state/system/switch-fabric/failure-recovery/sfm
                    list sfm {
                        key "sfm-slot";
                        description "Enter the sfm list instance";

                        ///nokia-state/state/system/switch-fabric/failure-recovery/sfm/sfm-slot
                        leaf sfm-slot {
                            type leafref {
                                path "../../../../../sfm/sfm-slot";
                            }
                            description
                                "The unique value which identifies this SFM slot within a
                                 chassis in the system.";
                        }

                        ///nokia-state/state/system/switch-fabric/failure-recovery/sfm/state
                        leaf state {
                            type enumeration {
                                enum complete                       { value 0; }
                                enum in-progress                    { value 1; }
                                enum pending                        { value 2; }
                                enum aborted                        { value 3; }
                                enum failed                         { value 4; }
                            }
                            description
                                "Indicates the current state of the SFM in the automatic
                                 switch fabric recovery process.

                                 Values:
                                     complete    - this SFM has already been reset as part of
                                                   the recovery process
                                     in-progress - this SFM is currently being reset
                                     pending     - this SFM has not yet been reset
                                     aborted     - the recovery was aborted before this SFM
                                                   was processed
                                     failed      - the SFM has not successfully completed";
                        }

                        ///nokia-state/state/system/switch-fabric/failure-recovery/sfm/state-time
                        leaf state-time {
                            type yang:date-and-time;
                            description "Indicates the date and time the state changed.";
                        }

                    } // list sfm

                } // container failure-recovery

            } // container switch-fabric


            uses state-system-bluetooth;
            uses state-system-bootup;
            uses state-system-cron;
            uses state-system-licensing;
            uses state-system-ptp;
            uses state-system-script-control;
            uses state-system-security;
            uses state-system-telemetry;
            uses state-system-time;
        } // container system

    } // grouping state-system

}
