submodule nokia-state-router-isis {

    yang-version "1.1";

    belongs-to nokia-state { prefix "state"; }

    import ietf-inet-types                { prefix "inet"; }
    import ietf-yang-types                { prefix "yang"; }
    import nokia-sros-yang-extensions     { prefix "sros-ext"; }
    import nokia-types-igp                { prefix "types-igp"; }
    import nokia-types-isis               { prefix "types-isis"; }
    import nokia-types-router             { prefix "types-router"; }
    import nokia-types-sros               { prefix "types-sros"; }

    sros-ext:sros-major-release "rel23";
    organization "Nokia";
    contact
        "Nokia SR OS Support
         Web: <http://www.nokia.com>";
    description
        "Nokia YANG Data model with operational state for router isis protocol attributes on SR OS based routers.

         Copyright 2016 Nokia. All rights reserved. Reproduction of this document
         is authorized on the condition that the foregoing copyright notice is included.

         This nokia-state-router-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-01";

    grouping state-router-isis {
        list isis {
            key "isis-instance";
            description "Enter the isis list instance";

            leaf isis-instance {
                type int32 {
                    range "0..127";
                }
                description "Instance ID for the IS-IS instance";
            }

            leaf oper-system-id {
                type types-igp:system-id;
                description "The ID for this instance of the Integrated IS-IS protocol.";
            }

            leaf oper-router-id {
                type types-sros:ipv4-address;
                description "Indicates a ipv4-address uniquely identifying the router in the Autonomous System.";
            }

            leaf oper-ipv6-te-router-id {
                type types-sros:ipv6-address;
                description "Indicates a ipv6-address identifying the TE router.";
            }

            leaf db-export-igp-asn {
                type inet:as-number;
                description "Indicates Autonomous System Number the IGP is using during its database export.";
            }

            leaf oper-state {
                type types-sros:oper-state;
                description
                    "The value of the this object indicates the operational
                     state of the destination.";
            }

            leaf last-enabled-time {
                type yang:date-and-time;
                description "Indicates the last system up time when the current IS-IS protocol instance was run.";
            }

            leaf last-spf {
                type yang:date-and-time;
                description
                    "Indicates the system up time when the last SPF run was performed for this
                     instance of the IS-IS protocol in the router.";
            }

            leaf prefix-limit-overload-time-left {
                type int32 {
                    range "0..1800";
                }
                description
                    "Indicates the remaining time in seconds before IS-IS will attempt to enter its
                     normal state to recover from the overload state due to prefix limit exceeded.

                     The value of 0 implies that the system is either not in overload or indefinitely in overload state.";
            }

            leaf version {
                type string;
                description "Indicates the version number of the IS-IS protocol to which this instance conforms.";
            }

            leaf l1-state {
                type types-isis:level-state;
                description "Indicates the state of the Level 1 database.";
            }

            leaf l2-state {
                type types-isis:level-state;
                description "Indicates the state of the Level 2 database.";
            }

            leaf spf-hold-time {
                type int32 {
                    range "0..65535";
                }
                units "seconds";
                description "Indicates the time interval at which SPF is run.";
            }

            container loopfree-alternate {
                description "Enable the loopfree-alternate context";

                container statistics {
                    description "Enter the statistics context";

                    container lfa {
                        description "Enter the lfa context";

                        leaf runs {
                            type yang:counter32;
                            description "Indicates the number of times the calculations have been made.";
                        }

                        leaf time {
                            type yang:date-and-time;
                            description "Indicates the time when the last lfa was scheduled.";
                        }

                        container partial {
                            description "Enter the partial context";

                            leaf runs {
                                type yang:counter32;
                                description "Indicates the number of times the calculations have been made.";
                            }

                            leaf time {
                                type yang:date-and-time;
                                description "Indicates the time when the last lfa was scheduled.";
                            }

                        } // container partial

                    } // container lfa

                    container remote-lfa {
                        description "Enter the remote-lfa context";

                        leaf runs {
                            type yang:counter32;
                            description "Indicates the number of times the calculations have been made.";
                        }

                        leaf time {
                            type yang:date-and-time;
                            description "Indicates the time when the last lfa was scheduled.";
                        }

                    } // container remote-lfa

                    container ti-lfa {
                        description "Enter the ti-lfa context";

                        leaf runs {
                            type yang:counter32;
                            description "Indicates the number of times the calculations have been made.";
                        }

                        leaf time {
                            type yang:date-and-time;
                            description "Indicates the time when the last lfa was scheduled.";
                        }

                    } // container ti-lfa

                } // container statistics

            } // container loopfree-alternate

            container statistics {
                description "Enter the statistics context";

                leaf lsp-regenerations {
                    type yang:counter32;
                    description "Indicates the count of LSP regenerations.";
                }

                leaf initiated-purges {
                    type yang:counter32;
                    description "Indicates the number of times purges have been initiated.";
                }

                leaf corrupted-lsps {
                    type yang:counter32;
                    description "Indicates the number of corrupted LSPs detected.";
                }

                leaf lsp-l1-db-overloads {
                    type yang:counter32;
                    description "Indicates the number of times the LSP L1 database has become overloaded.";
                }

                leaf lsp-l2-db-overloads {
                    type yang:counter32;
                    description "Indicates the number of times the Level 2 LSP database has become overloaded.";
                }

                leaf manual-address-dropped-from-areas {
                    type yang:counter32;
                    description "Indicates the number of times a manual address has been dropped from the area.";
                }

                leaf attempt-to-exceed-max-sequence-numbers {
                    type yang:counter32;
                    description "Indicates the number of times the IS has attempted to exceed the maximum sequence number.";
                }

                leaf sequence-number-skips {
                    type yang:counter32;
                    description "Indicates the number of times a sequence number skip has occurred.";
                }

                leaf own-lsp-purges {
                    type yang:counter32;
                    description
                        "Indicates the number of times a zero-aged copy of the system's own LSP
                         is received from some other node.";
                }

                leaf id-field-length-mismatches {
                    type yang:counter32;
                    description
                        "Indicates the number of times a PDU is received with a different value
                         for ID field length to that of the receiving system.";
                }

                leaf max-area-address-mismatches {
                    type yang:counter32;
                    description
                        "Indicates the number of times a PDU is received with a different value
                         for maximum area addresses from that of the receiving system.";
                }

                leaf authentication-failures {
                    type yang:counter32;
                    description "Indicates the number of authentication failures recognized by this instance of the protocol.";
                }

                leaf partition-changes {
                    type yang:counter32;
                    description "indicates the number of partition changes.";
                }

                container sid {
                    description "Enter the sid context";

                    leaf srgb-errors {
                        type yang:counter32;
                        description "Indicates the total number of errors for SIDs that are not within the label-range of the router.";
                    }

                    leaf duplicated-errors {
                        type yang:counter32;
                        description "Indicates the total number of errors for SIDs which are already assigned to another prefix.";
                    }

                } // container sid

                container spf {
                    description "Enter the spf context";

                    leaf runs {
                        type yang:counter32;
                        description "Indicates the number of times the calculations have been made.";
                    }

                    leaf time {
                        type yang:date-and-time;
                        description "Indicates the time when the last lfa was scheduled.";
                    }

                    container partial {
                        description "Enter the partial context";

                        leaf runs {
                            type yang:counter32;
                            description "Indicates the number of times the calculations have been made.";
                        }

                        leaf time {
                            type yang:date-and-time;
                            description "Indicates the time when the last lfa was scheduled.";
                        }

                    } // container partial

                } // container spf

                container cspf {
                    description "Enter the cspf context";

                    leaf requests {
                        type yang:counter32;
                        description "Indicates the number of CSPF requests made to the protocol.";
                    }

                    leaf dropped-requests {
                        type yang:counter32;
                        description "Indicates the number of dropped CSPF requests by the protocol.";
                    }

                    leaf paths-found {
                        type yang:counter32;
                        description
                            "Indicates the number of responses to CSPF requests for which paths satisfying
                             the constraints were found.";
                    }

                    leaf paths-not-found {
                        type yang:counter32;
                        description
                            "Indicates the number of responses to CSPF requests for which no paths satisfying
                             the constraints were found.";
                    }

                } // container cspf

                container lsp {
                    description "Enter the lsp context";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container lsp

                container iih {
                    description "Enter the iih context";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container iih

                container csnp {
                    description "Enter the csnp context";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container csnp

                container psnp {
                    description "Enter the psnp context";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container psnp

                container unknown {
                    description "Enter the unknown context";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container unknown

            } // container statistics

            container flexible-algorithms {
                description "Enter the flexible-algorithms context";

                list flex-algo {
                    key "flex-algo-id";
                    description "Enter the flex-algo list instance";

                    leaf flex-algo-id {
                        type uint32 {
                            range "128..255";
                        }
                        description "Flexible algorithm ID";
                    }

                    list level {
                        key "level-number";
                        description "Enter the level list instance";

                        leaf level-number {
                            type enumeration {
                                enum 1                              { value 1; }
                                enum 2                              { value 2; }
                            }
                            description "ISIS protocol level number";
                        }

                        leaf oper-state {
                            type types-sros:oper-state;
                            description
                                "The value of oper-state indicates the current operating
                                 state of the Flexible Algorithm participation in this
                                 ISIS level.";
                        }

                        leaf fad-count {
                            type uint32;
                            description
                                "The value of fad-count indicates the number of Flexible
                                 Algorithm Definitions (FAD) for the Flex Algo in the
                                 ISIS level.";
                        }

                        leaf selected-owner {
                            type types-igp:system-id;
                            description
                                "The value of selected-owner indicates the System ID of
                                 the owner of the selected Flexible Algorithm Definition
                                 (FAD).";
                        }

                        list flex-algo-definitions {
                            key "fad-owner-lsp-id priority";
                            description "Enter the flex-algo-definitions list instance";

                            leaf fad-owner-lsp-id {
                                type types-isis:lsp-id;
                                description
                                    "The lsp-id of the node advertising the flex-algo definition.
                                     The value given in the format as 6 octets of fad-owner's system-id followed by
                                     1 octet Lan-ID and 1 octet LSP Number.";
                            }

                            leaf priority {
                                type uint32;
                                description "The value of priority indicates the priority of the FAD.";
                            }

                            leaf supported {
                                type boolean;
                                description "The value of supported indicates if this FAD is supported by the router.";
                            }

                            leaf unsupported-reason {
                                type enumeration {
                                    enum none                           { value 0; }
                                    enum metric-type                    { value 1; }
                                    enum calculation-type               { value 2; }
                                    enum constraint                     { value 3; }
                                    enum flag                           { value 4; }
                                    enum subtlv                         { value 5; }
                                }
                                description "The value of unupported-reason indicates why this FAD is not supported.";
                            }

                            leaf metric-type {
                                type enumeration {
                                    enum igp                            { value 0; }
                                    enum delay                          { value 1; }
                                    enum te-metric                      { value 2; }
                                    enum unsupported-metric-type        { value 3; }
                                }
                                description "The value of metric-type indicates the metric type of the FAD.";
                            }

                            leaf calc-type {
                                type uint32;
                                description "The value of calc-type indicates the calculation type of the FAD.";
                            }

                            leaf exclude {
                                type types-sros:hex-string;
                                description "The value of exclude indicates the exclude rule that is used during the Flex-Algorithm path calculation.";
                            }

                            leaf include-any {
                                type types-sros:hex-string;
                                description "The value of include-any indicates the include-any rule that is used during the Flex-Algorithm path calculation.";
                            }

                            leaf include-all {
                                type types-sros:hex-string;
                                description "The value of include-all indicates the include-all rule that is used during the Flex-Algorithm path calculation.";
                            }

                            leaf flags {
                                type types-sros:hex-string;
                                description "The value of flags indicates the Flexible Algorithm Definition flags.";
                            }


                        } // list flex-algo-definitions

                    } // list level

                    list route {
                        key "multi-topology-id destination";
                        description "Enter the route list instance";

                        leaf multi-topology-id {
                            type uint32;
                            description
                                "The value specifies the multi-topology id number for the path.

                                 If multi-topology is not supported for the path then
                                 the value should be 0.";
                        }

                        leaf destination {
                            type types-sros:ip-prefix;
                            description "The value specifies the IP address and mask of the route destination.";
                        }

                        leaf level {
                            type types-isis:level;
                            description "The value indicates the IS-IS Level at which the prefix was learned.";
                        }

                        leaf status {
                            type enumeration {
                                enum active                         { value 0; }
                                enum rtm-add-failed                 { value 1; }
                                enum fib-add-failed                 { value 2; }
                            }
                            description "The value indicates the reason why a route is not active.";
                        }

                        leaf metric {
                            type uint32;
                            description
                                "The value indicates the routing metric for a backup route.

                                 The semantics of this metric are determined by the routing-protocol
                                 specified in the route's ipCidrRouteProto value.

                                 The value is only valid when backup-flags has a value of 'has-lfa'.";
                        }

                        leaf type {
                            type enumeration {
                                enum internal                       { value 1; }
                                enum external                       { value 2; }
                            }
                            description "The value indicates the type of route represented by this row entry.";
                        }

                        leaf tag {
                            type uint32;
                            description
                                "The value indicates a 32-bit integer route tag for this route.

                                 A value of 0 indicates that the tag has not been set.";
                        }

                        container backup {
                            description "Enter the backup context";

                            leaf next-hop-ip {
                                type types-sros:ip-address-with-zone;
                                description "The value specifies the IP address of the next hop for this route.";
                            }

                            leaf next-hop-type {
                                type types-isis:cidr-next-hop-type;
                                description "The value indicates the type of next hop for this backup route.";
                            }

                            leaf next-hop-owner {
                                type types-isis:cidr-next-hop-owner;
                                description "The value indicates the owner of next hop for this backup route.";
                            }

                            leaf next-hop-tunnel-id {
                                type uint32;
                                description
                                    "The value indicates the auxiliary information, for next hop owner as indicated by
                                     backup-next-hop-owner.

                                     The value of indicates the tunnel-id existing for this backup next hop type and owner.";
                            }

                            leaf type {
                                type enumeration {
                                    enum node-protection                { value 1; }
                                    enum link-protection                { value 2; }
                                }
                                description
                                    "The value indicates the type of protection used by the backup next-hop.

                                     The value 'not-applicable' indicates that the backup next hop type
                                     is not applicable
                                     the value 'node-protection' indicates that the backup next hop uses a
                                     node-protection mechanism
                                     the value 'link-protection' indicates that the backup next hop uses
                                     link-protection mechanism.";
                            }

                            leaf metric {
                                type uint32;
                                description
                                    "The value indicates the routing metric for a backup route.

                                     The semantics of this metric are determined by the routing-protocol
                                     specified in the route's ipCidrRouteProto value.

                                     The value is only valid when backup-flags has a value of 'has-lfa'.";
                            }

                            leaf flags {
                                type enumeration {
                                    enum none                           { value 0; }
                                    enum has-lfa                        { value 1; }
                                }
                                description
                                    "The value indicates the presence or absence of LFA next-hops.

                                     The value 'none' indicates that no next hop is present
                                     the value 'has-lfa' indicates that an LFA next hop is present in addition
                                     to the regular next-hop.";
                            }

                        } // container backup

                        container prefix-sid {
                            description "Enter the prefix-sid context";

                            leaf label {
                                type uint32;
                                description "The value specifies the SID label or index for this prefix.";
                            }

                            leaf flags {
                                type bits {
                                    bit bit-r                          { position 0; }
                                    bit bit-n                          { position 1; }
                                    bit bit-p                          { position 2; }
                                    bit bit-e                          { position 3; }
                                    bit bit-v                          { position 4; }
                                    bit bit-l                          { position 5; }
                                }
                                description
                                    "The value indicates the flags of a Prefix-SID advertised by
                                     an IP Reach or Label Binding TLV.

                                     bit-r   (0)  - Re-advertisement flag.  If set, then the prefix to
                                       which this Prefix-SID is attached, has been propagated by the
                                       router either from another level (i.e.: from level-1 to level-2
                                       or the opposite) or from redistribution (e.g.: from another
                                       protocol).
                                     bit-n   (1)  - Node-SID flag. The N-Flag is set on Prefix-SIDs
                                       attached to a router loopback address.
                                     bit-p   (2)  - no-PHP flag. If set, then the penultimate hop MUST NOT
                                       pop the Prefix-SID before delivering the packet to the node
                                       that advertised the Prefix-SID.
                                     bit-e   (3)  - Explicit-Null Flag.  If set, any upstream neighbor
                                       of the Prefix-SID originator MUST replace the Prefix-SID with
                                       a Prefix-SID having an Explicit-NULL value (0 for IPv4 and 2 for
                                       IPv6) before forwarding the packet.
                                     bit-v   (4)  - Value flag. If set, then the Prefix-SID carries a
                                       value (instead of an index).
                                     bit-l   (5)  - Local Flag.  If set, then the value/index carried by
                                       the Prefix-SID has local significance.";
                            }

                        } // container prefix-sid

                        list next-hop {
                            key "ecmp-index";
                            description "Enter the next-hop list instance";

                            leaf ecmp-index {
                                type types-router:ip-ecmp;
                                description "ECMP index of this route next-hop.";
                            }

                            leaf next-hop-ip {
                                type types-sros:ip-address-with-zone;
                                description "The value specifies the IP address of the next hop for this route.";
                            }

                            leaf next-hop-type {
                                type types-isis:cidr-next-hop-type;
                                description "The value indicates the type of next hop for this backup route.";
                            }

                            leaf next-hop-owner {
                                type types-isis:cidr-next-hop-owner;
                                description "The value indicates the owner of next hop for this backup route.";
                            }

                            leaf next-hop-tunnel-id {
                                type uint32;
                                description
                                    "The value indicates the auxiliary information, for next hop owner as indicated by
                                     backup-next-hop-owner.

                                     The value of indicates the tunnel-id existing for this backup next hop type and owner.";
                            }

                            leaf spf-version {
                                type yang:counter32;
                                description "The value indicates the run of SPF calculation in which this route was selected.";
                            }

                            leaf next-hop-system-id {
                                type types-igp:system-id;
                                description
                                    "The value indicates the system-id of the next hop IS through
                                     which this route is reachable.";
                            }

                            leaf rtm-status {
                                type enumeration {
                                    enum success                        { value 0; }
                                    enum discarded                      { value 1; }
                                }
                                description "Indicates the next hop status in RTM";
                            }

                        } // list next-hop

                    } // list route

                    list sr-lfa-coverage {
                        key "level-number multi-topology-id sid-type protocol-version";
                        description "Enter the sr-lfa-coverage list instance";

                        leaf level-number {
                            type types-isis:level;
                            description "Specifies the IS-IS protocol level to which these attributes are applied.";
                        }

                        leaf multi-topology-id {
                            type enumeration {
                                enum ipv4                           { value 0; }
                                enum ipv6                           { value 1; }
                                enum ipv4-mcast                     { value 2; }
                                enum ipv6-mcast                     { value 3; }
                            }
                            description
                                "The value specifies the multi-topology id number for the path.

                                 Possible values are:

                                 ipv4(0)      - indicates MT0 or standard topology
                                 ipv6(1)      - indicates MT2 or IPv6 routing topology
                                 ipv4-mcast(2) - indicates MT3 or IPv4 multicast routing topology
                                 ipv6-mcast(3) - indicates MT4 or IPv6 multicast routing topology.";
                        }

                        leaf sid-type {
                            type enumeration {
                                enum node-sid                       { value 0; }
                                enum adj-sid                        { value 1; }
                            }
                            description
                                "The value specifies the SID type for which SR LFA coverage
                                 has been computed.";
                        }

                        leaf protocol-version {
                            type enumeration {
                                enum ipv4                           { value 0; }
                                enum ipv6                           { value 1; }
                            }
                            description "The value specifies the protocol version for which SR LFA coverage has been computed.";
                        }

                        leaf lfa-covered {
                            type uint32;
                            description "The value indicates the number of SIDs for which an LFA is found.";
                        }

                        leaf lfa-covered-percent {
                            type types-sros:percent;
                            description "The value indicates the portion of SIDs for which an LFA is found.";
                        }

                        leaf remote-lfa-covered {
                            type uint32;
                            description "The value indicates the number of SIDs for which an Remote LFA is found.";
                        }

                        leaf remote-lfa-covered-percent {
                            type types-sros:percent;
                            description "The value indicates the portion of SIDs for which an Remote LFA is found.";
                        }

                        leaf ti-lfa-covered {
                            type uint32;
                            description "The value indicates the number of SIDs for which an Topology Independent LFA is found.";
                        }

                        leaf ti-lfa-covered-percent {
                            type types-sros:percent;
                            description "The value indicates the portion of SIDs for which an LFA is found.";
                        }

                        leaf total-sid {
                            type uint32;
                            description "The value indicates the number of SIDs eligible for SR LFA calculation";
                        }

                        leaf backup-total-sid {
                            type uint32;
                            description "The value indicates the number of SIDs for which an LFA, Remote LFA or Topology Independent LFA is found";
                        }

                        leaf backup-total-sid-percent {
                            type uint32;
                            description "The value indicates the portion of SIDs for which an LFA, Remote LFA or Topology Independent LFA is found";
                        }

                    } // list sr-lfa-coverage

                } // list flex-algo

            } // container flexible-algorithms

            container segment-routing {
                description "Enter the segment-routing context";

                list adjacency-set {
                    key "id";
                    description "Enter the adjacency-set list instance";

                    leaf id {
                        type uint32 {
                            range "1..max";
                        }
                        description "Identifier for specified adjacency set";
                    }

                    leaf dynamic-sid-value {
                        type uint32;
                        description
                            "The value indicates the IPvx SID label for this adjacency-set
                             allocated dynamically when none is configured.";
                    }

                    leaf tunl-dest-ip {
                        type types-sros:ip-address;
                        description
                            "Indicates the IP address of the adjacency-set tunnel destination. An
                             adjacency-set with links to different neighbors will have dest@ set
                             to 0.0.0.0.";
                    }

                    leaf neighbor-system-id {
                        type types-igp:system-id;
                        description
                            "Specifies the system-id of the node where all links are terminated in case the
                             adjacency-set is of type parallel.";
                    }

                    leaf members-count {
                        type uint32;
                        description
                            "The value indicates the number of interfaces that are a member of the
                             adjacency-set.";
                    }

                    leaf active-members {
                        type uint32;
                        description
                            "The value indicates the number of active adajcencies that are a member
                             of the adjacancy-set.";
                    }

                    leaf status {
                        type enumeration {
                            enum not-active                     { value 0; }
                            enum active                         { value 1; }
                            enum active-incomplete              { value 2; }
                            enum fib-add-failed                 { value 3; }
                        }
                        description "The value indicates the reason why an adjacency-set is not active.";
                    }

                    leaf uptime {
                        type int32;
                        units "seconds";
                        description
                            "The amount of time in seconds since this adjacency-set
                             was last programmed.";
                    }

                    leaf mtu {
                        type uint32;
                        description
                            "The MTU of the adjacency-set tunnel. This value takes into account the lowest
                             value of active links, the label overhead and the segment-routing
                             tunnel-mtu";
                    }

                    list next-hop {
                        key "system-id interface-name";
                        description "Enter the next-hop list instance";

                        leaf system-id {
                            type types-igp:system-id;
                            description "The system-id of the node that terminates an adjacency-set link.";
                        }

                        leaf interface-name {
                            type types-sros:interface-name;
                            description "Router interface name.";
                        }

                        leaf next-hop-ip {
                            type types-sros:ip-address;
                            description "The value specifies the IP address of the next hop for this adjacency-set link.";
                        }

                        leaf usage {
                            type enumeration {
                                enum undefined                      { value 1; }
                                enum level1                         { value 2; }
                                enum level2                         { value 3; }
                                enum level1and2                     { value 4; }
                            }
                            description
                                "An adjacency-set link of type level1 is used for level 1 traffic only. An
                                 adjacency-set link of type level2 is used for level 2 traffic only. An
                                 adjacency-set link of type level1and2 is used for both level 1 and level 2 traffic.";
                        }

                        leaf level {
                            type enumeration {
                                enum level1                         { value 1; }
                                enum level2                         { value 2; }
                                enum level1-l2                      { value 3; }
                                enum unknown                        { value 4; }
                            }
                            description "The value indicates the circuit type of the adjacency-set link.";
                        }

                    } // list next-hop

                } // list adjacency-set

            } // container segment-routing

            container segment-routing-v6 {
                description "Enter the segment-routing-v6 context";

                list locator-state {
                    key "multi-topology-id locator advertising-system-id level-number";
                    description "Enter the locator-state list instance";

                    leaf multi-topology-id {
                        type uint32;
                        description
                            "The value specifies the multi-topology id number for the locator.
                             If multi-topology is not supported for the locator then
                             the value should be 0.";
                    }

                    leaf locator {
                        type types-sros:ip-prefix;
                        description "The value specifies the IP address and mask of the locator.";
                    }

                    leaf advertising-system-id {
                        type types-igp:system-id;
                        description
                            "The value specifies the system-id of the advertising
                             IS through which this locator is reachable.";
                    }

                    leaf level-number {
                        type enumeration {
                            enum 1                              { value 1; }
                            enum 2                              { value 2; }
                        }
                        description "ISIS protocol level number";
                    }

                    leaf type {
                        type enumeration {
                            enum internal                       { value 1; }
                            enum external                       { value 2; }
                        }
                        description "The value indicates the type of route represented by this row entry.";
                    }

                    leaf locator-flags {
                        type bits {
                            bit bit-d                          { position 0; }
                        }
                        description
                            "The value indicates the flags advertised in the SRv6 Locator TLV.

                             bit-d   (0)  - Down flag.  If set, then the Locator has been leaked 
                                 from Level-2 to Level-1 (only downwards, not upwards to prevent
                                 looping).";
                    }

                    leaf algorithm {
                        type int32 {
                            range "0|128..255";
                        }
                        description "The value indicates the algorithm related to the SID.";
                    }

                    leaf admin-tag {
                        type uint32;
                        description "The value indicates the administrative tag advertised in the sub-TLV.";
                    }

                    leaf attribute-flags {
                        type bits {
                            bit bit-x                          { position 0; }
                            bit bit-r                          { position 1; }
                            bit bit-n                          { position 2; }
                            bit bit-e                          { position 3; }
                            bit bit-a                          { position 4; }
                        }
                        description
                            "The value indicates the Prefix Attribute Flags advertised in the sub-TLV.

                             bit-x   (0)  - External Prefix flag. If set, then the prefix
                                           has been redistributed from another protocol.
                             bit-r   (1)  - Re-advertisement flag.  If set, then the prefix 
                                           has been leaked from one level to another (upwards or downwards).
                             bit-n   (2)  - Node flag. If set, then the prefix identifies the 
                                           advertising router. The advertising router may choose to not set
                                           this flag.
                             bit-e   (3)  - ELC flag. If set, then the local host prefix supports 
                                           Entropy Label Capability (ELC) on all interfaces. 
                             bit-a   (4)  - Anycast flag. If set, then the prefix/SRv6 locator
                                           is configured as anycast.";
                    }

                    list end-sid {
                        key "end-sid";
                        description "Enter the end-sid list instance";

                        leaf end-sid {
                            type types-sros:ipv6-address;
                            description "The value specifies the IPv6 address of the end SID.";
                        }

                        leaf endpoint-behavior {
                            type types-isis:srv6-endpoint-behavior-type;
                            description "The value indicates the SRv6 endpoint behavior advertised in the SID sub-TLV.";
                        }

                    } // list end-sid

                } // list locator-state

                list micro-segment-locator-state {
                    key "multi-topology-id micro-segment-locator advertising-system-id level-number";
                    description "Enter the micro-segment-locator-state list instance";

                    leaf multi-topology-id {
                        type uint32;
                        description
                            "The value specifies the multi-topology id number for the
                             micro-segment locator.
                             If multi-topology is not supported for the micro-segment locator
                             then the value should be 0.";
                    }

                    leaf micro-segment-locator {
                        type types-sros:ip-prefix;
                        description "The value specifies the IP address and mask of the micro-segment locator.";
                    }

                    leaf advertising-system-id {
                        type types-igp:system-id;
                        description
                            "The value specifies the system-id of the advertising
                             IS through which this micro-segment locator is reachable.";
                    }

                    leaf level-number {
                        type enumeration {
                            enum 1                              { value 1; }
                            enum 2                              { value 2; }
                        }
                        description "ISIS protocol level number";
                    }

                    leaf type {
                        type enumeration {
                            enum internal                       { value 1; }
                            enum external                       { value 2; }
                        }
                        description "The value indicates the type of route represented by this row entry.";
                    }

                    leaf locator-flags {
                        type bits {
                            bit bit-d                          { position 0; }
                        }
                        description
                            "The value indicates the flags advertised in the SRv6 Locator TLV.

                             bit-d   (0)  - Down flag.  If set, then the Locator has been leaked 
                                 from Level-2 to Level-1 (only downwards, not upwards to prevent
                                 looping).";
                    }

                    leaf algorithm {
                        type int32 {
                            range "0|128..255";
                        }
                        description "The value indicates the algorithm related to the SID.";
                    }

                    leaf admin-tag {
                        type uint32;
                        description "The value indicates the administrative tag advertised in the sub-TLV.";
                    }

                    leaf attribute-flags {
                        type bits {
                            bit bit-x                          { position 0; }
                            bit bit-r                          { position 1; }
                            bit bit-n                          { position 2; }
                            bit bit-e                          { position 3; }
                            bit bit-a                          { position 4; }
                        }
                        description
                            "The value indicates the Prefix Attribute Flags advertised in the sub-TLV.

                             bit-x   (0)  - External Prefix flag. If set, then the prefix
                                           has been redistributed from another protocol.
                             bit-r   (1)  - Re-advertisement flag.  If set, then the prefix 
                                           has been leaked from one level to another (upwards or downwards).
                             bit-n   (2)  - Node flag. If set, then the prefix identifies the 
                                           advertising router. The advertising router may choose to not set
                                           this flag.
                             bit-e   (3)  - ELC flag. If set, then the local host prefix supports 
                                           Entropy Label Capability (ELC) on all interfaces. 
                             bit-a   (4)  - Anycast flag. If set, then the prefix/SRv6 locator
                                           is configured as anycast.";
                    }

                    list un-sid {
                        key "sid";
                        description "Enter the un-sid list instance";

                        leaf sid {
                            type types-sros:ipv6-address;
                            description "The value specifies the IPv6 address of the uN SID.";
                        }

                        leaf endpoint-behavior {
                            type types-isis:srv6-un-endpoint-behavior-type;
                            description "The value indicates the SRv6 endpoint behavior advertised in the SID sub-TLV.";
                        }

                    } // list un-sid

                } // list micro-segment-locator-state

                container last-sid-error {
                    description "Enter the last-sid-error context";

                    leaf type {
                        type enumeration {
                            enum duplicate-sid                  { value 1; }
                            enum nexthop-ies                    { value 2; }
                            enum algo-not-supported             { value 3; }
                            enum proto-not-supported            { value 4; }
                            enum flags-not-supported            { value 5; }
                            enum no-resource                    { value 6; }
                        }
                        description "The value indicates the error type that last occured.";
                    }

                    leaf multi-topology-id {
                        type uint32;
                        description
                            "The value specifies the multi-topology id number for the end-sid.
                             If multi-topology is not supported for the end-sid then
                             the value should be 0.";
                    }

                    leaf prefix {
                        type types-sros:ip-prefix;
                        description "The value specifies the IP address and mask of the sid.";
                    }

                    leaf advertising-system-id {
                        type types-igp:system-id;
                        description
                            "The value specifies the system-id of the advertising
                             IS through which this SID is reachable.";
                    }

                    leaf level-number {
                        type enumeration {
                            enum 1                              { value 1; }
                            enum 2                              { value 2; }
                        }
                        description "Specifies the IS-IS protocol level to which these attributes are applied.";
                    }

                    leaf flex-algo-id {
                        type uint32;
                        description "The value specifies the flexible algorithm.";
                    }

                    leaf last-occurrence {
                        type yang:date-and-time;
                        description "Indicates the timestamp of the last time the error was detected.";
                    }

                } // container last-sid-error

            } // container segment-routing-v6

            list interface {
                key "interface-name";
                description "Enter the interface list instance";

                leaf interface-name {
                    type types-sros:interface-name;
                    description "Router interface name";
                }

                leaf oper-state {
                    type types-sros:oper-state;
                    description "Indicates the current operational state of IS-IS protocol on this interface.";
                }

                leaf mtu {
                    type uint32;
                    description
                        "Indicates the operational size of the largest packet which can be
                         sent/received on this IS-IS interface, specified in octets.
                         This size does not include the underlying layer headers/trailers.";
                }

                leaf circuit-index {
                    type uint32 {
                        range "1..2000000000";
                    }
                    description "Indicates a cross reference index to the isis circ table.";
                }

                leaf oper-type {
                    type types-isis:interface-type;
                    description "Indicates the operational type on this IS-IS interface.";
                }

                leaf ber-state {
                    type enumeration {
                        enum none                           { value 0; }
                        enum sd                             { value 1; }
                        enum sf                             { value 2; }
                    }
                    description "Indicates the Bit Error Rate (BER) state of this interface.";
                }

                leaf te-metric {
                    type types-isis:oper-metric;
                    description
                        "Indicates the MPLS TE metric configured for this interface.
                         This metric is flooded out in the TE metric sub-tlv in the IS-IS LSPs.
                         Depending on the configuration, either the TE metric value or the
                         native IS-IS metric values are used in CSPF computations.";
                }

                leaf te-state {
                    type types-sros:oper-state;
                    description "Indicates the MPLS interface TE status from the IS-IS standpoint.";
                }

                leaf point-to-point-circuit-id {
                    type types-isis:circuit-id;
                    description "Indicates the ID of the circuit allocated during initialization.";
                }

                leaf up-time {
                    type int32;
                    units "seconds";
                    description
                        "If the circuit is up, indicates the amount of time in seconds since this circuit entered state 'up'.

                         If the circuit is not up, indicates the number of seconds since the circuit was up,
                         or since the system started, if the circuit has never been up.";
                }

                container statistics {
                    description "Enter the statistics context";

                    leaf initialization-failures {
                        type yang:counter32;
                        description "Indicates the number of times initialization of this circuit has failed.";
                    }

                    leaf adjacency-state-change {
                        type yang:counter32;
                        description "Indicates the number of times an adjacency state change has occurred on this circuit.";
                    }

                    leaf adjacency-rejection {
                        type yang:counter32;
                        description "Indicates the number of times an adjacency has been rejected on this circuit.";
                    }

                    leaf control-pdu-sent {
                        type yang:counter32;
                        description "Indicates the number of IS-IS control PDUs sent on this circuit.";
                    }

                    leaf control-pdu-received {
                        type yang:counter32;
                        description "Indicates the number of IS-IS control PDUs received on this circuit.";
                    }

                    leaf control-pdu-id-length-mismatch-received {
                        type yang:counter32;
                        description
                            "Indicates the number an IS-IS control PDU with an ID
                             field length different to that for this system has been received.";
                    }

                    leaf max-area-address-mismatches {
                        type yang:counter32;
                        description
                            "Number of times an IS-IS control PDU with a max area address field
                             different from that for this system has been received. MIB Entry:
                             CircMaxAreaAddrMismatches.";
                    }

                    leaf area-address-mismatches {
                        type yang:counter32;
                        description
                            "Number of times an IS-IS control PDU with no area address common
                             with this system has been received. MIB Entry:
                             CircMaxAreaAddrMismatches.";
                    }

                    leaf auth-type-fails {
                        type yang:counter32;
                        description
                            "Number of times an IS-IS control PDU with an auth type field different
                             from that for this system has been received. MIB Entry:
                             CircAuthTypeFails.";
                    }

                    leaf auth-fails {
                        type yang:counter32;
                        description
                            "Number of times an IS-IS control PDU with the correct auth type has
                             failed to pass authentication validation. MIB Entry: CircAuthFails.";
                    }

                    leaf lan-dis-changes {
                        type yang:counter32;
                        description
                            "Number of times the Designated IS has changed on this circuit at this
                             level. If the circuit is point to point, this count is zero. MIB Entry:
                             CircLANDesISChanges.";
                    }

                    leaf end-x-install-failures {
                        type yang:counter32;
                        description
                            "Number of times an end-x could not be installed on this circuit due to
                             resource problems.";
                    }

                    leaf adj-number {
                        type uint32;
                        description
                            "Number of adjacencies on this circuit.
                             MIB Entry: CircNumAdj.";
                    }

                } // container statistics

                container ldp-sync {
                    description "Enter the ldp-sync context";

                    leaf state {
                        type types-sros:oper-state;
                        description "Indicates if IGP-LDP synchronization is enabled on this interface.";
                    }

                    leaf max-metric {
                        type boolean;
                        description "Indicates if IS-IS advertised maximum metric value is enabled on this interface.";
                    }

                    leaf timer-state {
                        type enumeration {
                            enum wait-for-ldp-adj               { value 1; }
                            enum timer-active                   { value 2; }
                            enum ldp-exchg-done                 { value 3; }
                            enum timer-expired                  { value 4; }
                            enum manual-exit                    { value 5; }
                            enum disabled                       { value 6; }
                        }
                        description "Indicates the state of the time-left on this IS-IS interface.";
                    }

                    leaf time-left {
                        type uint32 {
                            range "0..1800";
                        }
                        units "seconds";
                        description
                            "Indicates the time left before IS-IS reverts back to advertising the normal metric for
                             this interface. This is applicable only when max-metric is 'true'.";
                    }

                } // container ldp-sync

                container ipv4-shared-sid {
                    description "Enter the ipv4-shared-sid context";

                    choice type {
                        case label {

                            leaf label {
                                type int64 {
                                    range "1..4294967295";
                                }
                                description "Specifies IPvX node SID label for this interface.";
                            }

                        }
                        case index {

                            leaf index {
                                type int64 {
                                    range "0..4294967295";
                                }
                                description "Specifies IPvX node SID index for this interface.";
                            }

                        }
                    }
                } // container ipv4-shared-sid

                container ipv6-shared-sid {
                    description "Enter the ipv6-shared-sid context";

                    choice type {
                        case label {

                            leaf label {
                                type int64 {
                                    range "1..4294967295";
                                }
                                description "Specifies IPvX node SID label for this interface.";
                            }

                        }
                        case index {

                            leaf index {
                                type int64 {
                                    range "0..4294967295";
                                }
                                description "Specifies IPvX node SID index for this interface.";
                            }

                        }
                    }
                } // container ipv6-shared-sid

                list level {
                    key "level-number";
                    description "Enter the level list instance";

                    leaf level-number {
                        type enumeration {
                            enum 1                              { value 1; }
                            enum 2                              { value 2; }
                        }
                        description "ISIS protocol level number";
                    }

                    leaf adjacencies-number {
                        type uint32;
                        description "Indicates the number of adjacencies on this particular level of the interface.";
                    }

                    leaf designated-intermediate-system {
                        type types-igp:system-id;
                        description "Indicates the ID of the LAN Designated Intermediate System on this circuit at this level.";
                    }

                    leaf lsp-transmit-queue-count {
                        type uint32;
                        description "Indicates how many LSPs are in the transmit queue of this interface for this IS-IS level.";
                    }

                    leaf circuit-id {
                        type types-isis:circuit-id;
                        description "Indicates the ID of the circuit allocated during initialization.";
                    }

                    container oper-metric {
                        description "Enter the oper-metric context";

                        leaf ipv4-unicast {
                            type types-isis:oper-metric;
                            description "Indicates the operational value of the IPv4 unicast metric being used with this interface level.";
                        }

                        leaf ipv6-unicast {
                            type types-isis:oper-metric;
                            description "Indicates the operational value of the IPv6 unicast metric being used with this interface level.";
                        }

                        leaf ipv4-multicast {
                            type types-isis:oper-metric;
                            description "Indicates the operational value of the interface level metric for IPv4 multicast.";
                        }

                        leaf ipv6-multicast {
                            type types-isis:oper-metric;
                            description "Indicates the operational value of the interface level metric for IPv6 multicast.";
                        }

                    } // container oper-metric

                    container statistics {
                        description "Enter the statistics context";

                        leaf designated-intermediate-system-changes {
                            type yang:counter32;
                            description "Indicates the number of times the LAN Designated Intermediate System has changed at this level.";
                        }

                        list packets {
                            key "direction";
                            description "Enter the packets list instance";

                            leaf direction {
                                type enumeration {
                                    enum sending                        { value 1; }
                                    enum receiving                      { value 2; }
                                }
                                description "Were we sending or receiving these PDUs?";
                            }

                            leaf hello {
                                type yang:counter32;
                                description
                                    "The number of IS-IS Hello PDUs seen in this
                                     direction at this level.";
                            }

                            leaf lsp {
                                type yang:counter32;
                                description
                                    "The number of IS-IS LSPs seen in this
                                     direction at this level.";
                            }

                            leaf csnp {
                                type yang:counter32;
                                description
                                    "The number of IS-IS CSNPs seen in this
                                     direction at this level.";
                            }

                            leaf psnp {
                                type yang:counter32;
                                description
                                    "The number of IS-IS PSNPs seen in this
                                     direction at this level.";
                            }

                        } // list packets

                    } // container statistics

                } // list level

                list adjacency {
                    key "adjacency-index";
                    description "Enter the adjacency list instance";

                    leaf adjacency-index {
                        type int32 {
                            range "1..2000000000";
                        }
                        description
                            "A unique value identifying the IS adjacency from all
                             other such adjacencies on this circuit. This value is
                             assigned by the system when the adjacency is created
                             automatically.";
                    }

                    leaf oper-state {
                        type enumeration {
                            enum initializing                   { value 1; }
                            enum up                             { value 2; }
                            enum failed                         { value 3; }
                            enum down                           { value 4; }
                        }
                        description "The state of the adjacency";
                    }

                    leaf usage {
                        type enumeration {
                            enum undefined                      { value 1; }
                            enum level1                         { value 2; }
                            enum level2                         { value 3; }
                            enum level1and2                     { value 4; }
                        }
                        description
                            "An adjacency of type level1 is used for level 1
                             traffic only. An adjacency of type level2 is used
                             for level 2 traffic only. An adjacency of type level1and2
                             is used for both level 1 and level 2 traffic. There
                             may be two adjacencies (of types level1 and level2)
                             between the same pair of Intermediate Systems.";
                    }

                    leaf hold-timer {
                        type int32 {
                            range "1..65535";
                        }
                        units "seconds";
                        description
                            "The holding time for this adjacency updated from
                             received IIH PDUs.";
                    }

                    leaf uptime {
                        type int32;
                        units "seconds";
                        description
                            "If the adjacency is up, the amount of time in seconds
                             since this adjacency entered state 'up'.  If the adjacency
                             is not up, the number of seconds since the adjacency was
                             up, or since the system started, if the adjacency has
                             never been up.

                             Note: This can be implemented as start time less
                             the current time.";
                    }

                    leaf expires-in {
                        type int32 {
                            range "0..65535";
                        }
                        units "seconds";
                        description "The value indicates the time in which the adjacency will expire if no hello packets are received.";
                    }

                    leaf level {
                        type enumeration {
                            enum level1                         { value 1; }
                            enum level2                         { value 2; }
                            enum level1-l2                      { value 3; }
                            enum unknown                        { value 4; }
                        }
                        description "The value indicates the circuit type of the adjacency as advertised.";
                    }

                    container restart {
                        description "Enter the restart context";

                        leaf support {
                            type boolean;
                            description
                                "The value indicates whether adjacency supports ISIS graceful restart.

                                 If support has a value of 'true' the adjacency
                                 supports graceful restart.";
                        }

                        leaf status {
                            type enumeration {
                                enum not-helping                    { value 1; }
                                enum restarting                     { value 2; }
                                enum restart-complete               { value 3; }
                                enum helping                        { value 4; }
                                enum aborted                        { value 5; }
                            }
                            description "The value indicates the graceful restart status of the adjacency.";
                        }

                        leaf suppressed {
                            type boolean;
                            description
                                "The value indicates if the adjacency has requested this router to suppress advertisement of
                                 the adjacency in this router's LSPs.

                                 If suppressed has a value of 'true' the adjacency
                                 has requested to suppress advertisement of the LSPs.";
                        }

                        leaf num-restarts {
                            type uint32;
                            description "The value indicates the number of times the adjacency has attempted restart.";
                        }

                        leaf last-restart {
                            type yang:date-and-time;
                            description "The value indicates the last time the adjacency attempted restart.";
                        }

                    } // container restart

                    container neighbor {
                        description "Enter the neighbor context";

                        leaf snpa-address {
                            type types-isis:snpa-address;
                            description "The SNPA address of the neighboring system.";
                        }

                        leaf system-type {
                            type enumeration {
                                enum l1-is                          { value 1; }
                                enum l2-is                          { value 2; }
                                enum l1-l2-is                       { value 3; }
                                enum unknown                        { value 4; }
                            }
                            description "The type of the neighboring system.";
                        }

                        leaf system-id {
                            type string {
                                length "0..24";
                            }
                            description
                                "The system ID and 4 byte circuit ID of the
                                 neighboring Intermediate System set from
                                 the source ID field of the Three-Way-Handshake
                                 information from the neighbor's IIH PDUs.";
                        }

                        leaf priority {
                            type int32 {
                                range "0..127";
                            }
                            description
                                "Priority of the neighboring Intermediate System for
                                 becoming the LAN Level 1 Designated Intermediate System
                                 if the value of isisISAdjNeighSysType is
                                 L1IntermediateSystem or LAN Level 2 Designated
                                 Intermediate System if the value of
                                 isisISAdjNeighSysType is L2IntermediateSystem.";
                        }

                        leaf ipv4 {
                            type types-sros:ipv4-address;
                            description "The value indicates the ip-address of the neighbor with which adjacency is formed.";
                        }

                        leaf ipv6 {
                            type types-sros:ipv6-address;
                            description
                                "The value indicates the IP address of the neighbor with which an IPv6-adjacency is formed
                                 this will always be an IPv6 address.";
                        }

                    } // container neighbor

                    container multi-topology {
                        description "Enter the multi-topology context";

                        leaf enabled {
                            type boolean;
                            description
                                "The value indicates if the ISIS multi-topology protocol is supported on the neighbor.

                                 If the value is 'true', ISIS multi-topology
                                 protocol is enabled on the neighbor.";
                        }

                        container id0 {
                            description "Enter the id0 context";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id0

                        container id2 {
                            description "Enter the id2 context";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id2

                        container id3 {
                            description "Enter the id3 context";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id3

                        container id4 {
                            description "Enter the id4 context";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id4

                    } // container multi-topology

                    container sr-ipv4 {
                        description "Enter the sr-ipv4 context";

                        leaf sid-type {
                            type enumeration {
                                enum none                           { value 0; }
                                enum index                          { value 1; }
                                enum mpls-label                     { value 2; }
                                enum ipv6-label                     { value 3; }
                            }
                            description "The value indicates how the value of sid-value shall be interpreted.";
                        }

                        leaf sid-value {
                            type uint32;
                            description "The value indicates the IPvx SID label or index for this adjacency.";
                        }

                        leaf sid-protected {
                            type boolean;
                            description "The value of the object sid-protected indicates the if the SID for this adjacency is eligible for protection.";
                        }

                        leaf secondary-sid-type {
                            type enumeration {
                                enum none                           { value 0; }
                                enum index                          { value 1; }
                                enum mpls-label                     { value 2; }
                                enum ipv6-label                     { value 3; }
                            }
                            description "the value of secondary-sid-type indicates how the value of secondary-sid-value shall be interpreted.";
                        }

                        leaf secondary-sid-value {
                            type uint32;
                            description "the value of the object sid-value indicates the secondary SID label or index for this adjacency.";
                        }

                        leaf secondary-sid-protected {
                            type boolean;
                            description "The value of the object secondary-sid-protected indicates the if the secondary SID for this adjacency is eligible for protection.";
                        }

                        leaf secondary-sid-mtu {
                            type uint32;
                            description "The MTU of the link used by this adjacency using the secondary sid.";
                        }

                        leaf sid-hold-timer {
                            type int32 {
                                range "0..65535";
                            }
                            units "seconds";
                            description "The remaining holding time for this adjacency-sid.";
                        }

                        leaf sid-retry-timer {
                            type int32 {
                                range "0..65535";
                            }
                            units "seconds";
                            description
                                "The remaining time before allocating an adjacency-sid in
                                 case the previous allocation failed";
                        }

                        leaf pgid {
                            type uint32;
                            description "The value indicates the PGID for this adjacency.";
                        }

                        leaf mtu {
                            type uint32;
                            description "The MTU of the link used by this adjacency.";
                        }

                        leaf lfa-nhop {
                            type types-sros:ip-address;
                            description
                                "The value indicates the ip-address of the neighbor with which adjacency
                                 has formed a backup.";
                        }

                        leaf lfa-interface {
                            type types-sros:interface-name;
                            description "The value specifies the interface index of the outgoing interface for the adjacency backup.";
                        }

                        leaf lfa-tunnel-type {
                            type enumeration {
                                enum none                           { value 0; }
                                enum rsvp                           { value 1; }
                                enum ldp                            { value 2; }
                            }
                            description "Type of tunnel used for LFA";
                        }

                        leaf lfa-tunnel-id {
                            type types-sros:tunnel-id;
                        }

                        leaf lfa-mtu {
                            type uint32;
                            description "The MTU of the backup link attached to this entry.";
                        }

                        leaf lfa-type {
                            type enumeration {
                                enum none                           { value 0; }
                                enum lfa                            { value 1; }
                                enum rlfa                           { value 2; }
                                enum tilfa                          { value 3; }
                            }
                            description "LFA run that resulted in this backup";
                        }

                        leaf lfa-num-labels {
                            type uint32;
                            description "The value indicates the number of backup labels.";
                        }

                        leaf mtu-sr {
                            type uint32;
                            description
                                "The MTU of the adj-sid tunnel. This value takes into account the lowest
                                 value of the primary & backup mtu, the label overhead and the segment-routing
                                 tunnel-mtu";
                        }

                        list lfa-label-stack {
                            key "label-index";
                            description "Enter the lfa-label-stack list instance";

                            leaf label-index {
                                type uint32;
                                description
                                    "An adjacency can have a backup label stack.
                                     Label-index 0 indicates the first label which can be a destination
                                     node-sid , a node-sid towards a P or PQ node or an adj-sid to a
                                     Q node. The last label always indicates the destination label
                                     unless PHP is enabled.";
                            }

                            leaf label {
                                type uint32;
                                description
                                    "A label from an adjacency backup. The label can be a destination
                                     node-sid, an adj-sid or a node-sid towards a P or PQ node.";
                            }

                        } // list lfa-label-stack

                    } // container sr-ipv4

                    container sr-ipv6 {
                        description "Enter the sr-ipv6 context";

                        leaf sid-type {
                            type enumeration {
                                enum none                           { value 0; }
                                enum index                          { value 1; }
                                enum mpls-label                     { value 2; }
                                enum ipv6-label                     { value 3; }
                            }
                            description "The value indicates how the value of sid-value shall be interpreted.";
                        }

                        leaf sid-value {
                            type uint32;
                            description "The value indicates the IPvx SID label or index for this adjacency.";
                        }

                        leaf sid-protected {
                            type boolean;
                            description "The value of the object sid-protected indicates the if the SID for this adjacency is eligible for protection.";
                        }

                        leaf secondary-sid-type {
                            type enumeration {
                                enum none                           { value 0; }
                                enum index                          { value 1; }
                                enum mpls-label                     { value 2; }
                                enum ipv6-label                     { value 3; }
                            }
                            description "the value of secondary-sid-type indicates how the value of secondary-sid-value shall be interpreted.";
                        }

                        leaf secondary-sid-value {
                            type uint32;
                            description "the value of the object sid-value indicates the secondary SID label or index for this adjacency.";
                        }

                        leaf secondary-sid-protected {
                            type boolean;
                            description "The value of the object secondary-sid-protected indicates the if the secondary SID for this adjacency is eligible for protection.";
                        }

                        leaf secondary-sid-mtu {
                            type uint32;
                            description "The MTU of the link used by this adjacency using the secondary sid.";
                        }

                        leaf sid-hold-timer {
                            type int32 {
                                range "0..65535";
                            }
                            units "seconds";
                            description "The remaining holding time for this adjacency-sid.";
                        }

                        leaf sid-retry-timer {
                            type int32 {
                                range "0..65535";
                            }
                            units "seconds";
                            description
                                "The remaining time before allocating an adjacency-sid in
                                 case the previous allocation failed";
                        }

                        leaf pgid {
                            type uint32;
                            description "The value indicates the PGID for this adjacency.";
                        }

                        leaf mtu {
                            type uint32;
                            description "The MTU of the link used by this adjacency.";
                        }

                        leaf lfa-nhop {
                            type types-sros:ip-address;
                            description
                                "The value indicates the ip-address of the neighbor with which adjacency
                                 has formed a backup.";
                        }

                        leaf lfa-interface {
                            type types-sros:interface-name;
                            description "The value specifies the interface index of the outgoing interface for the adjacency backup.";
                        }

                        leaf lfa-tunnel-type {
                            type enumeration {
                                enum none                           { value 0; }
                                enum rsvp                           { value 1; }
                                enum ldp                            { value 2; }
                            }
                            description "Type of tunnel used for LFA";
                        }

                        leaf lfa-tunnel-id {
                            type types-sros:tunnel-id;
                        }

                        leaf lfa-mtu {
                            type uint32;
                            description "The MTU of the backup link attached to this entry.";
                        }

                        leaf lfa-type {
                            type enumeration {
                                enum none                           { value 0; }
                                enum lfa                            { value 1; }
                                enum rlfa                           { value 2; }
                                enum tilfa                          { value 3; }
                            }
                            description "LFA run that resulted in this backup";
                        }

                        leaf lfa-num-labels {
                            type uint32;
                            description "The value indicates the number of backup labels.";
                        }

                        leaf mtu-sr {
                            type uint32;
                            description
                                "The MTU of the adj-sid tunnel. This value takes into account the lowest
                                 value of the primary & backup mtu, the label overhead and the segment-routing
                                 tunnel-mtu";
                        }

                        list lfa-label-stack {
                            key "label-index";
                            description "Enter the lfa-label-stack list instance";

                            leaf label-index {
                                type uint32;
                                description
                                    "An adjacency can have a backup label stack.
                                     Label-index 0 indicates the first label which can be a destination
                                     node-sid , a node-sid towards a P or PQ node or an adj-sid to a
                                     Q node. The last label always indicates the destination label
                                     unless PHP is enabled.";
                            }

                            leaf label {
                                type uint32;
                                description
                                    "A label from an adjacency backup. The label can be a destination
                                     node-sid, an adj-sid or a node-sid towards a P or PQ node.";
                            }

                        } // list lfa-label-stack

                    } // container sr-ipv6

                    list area-address {
                        key "area-address";
                        description "Enter the area-address list instance";

                        leaf area-address {
                            type types-isis:area-address;
                            description
                                "An area address reported in a Level 1 LSP received by
                                 this instance of the protocol.";
                        }

                    } // list area-address

                    list supported-protocol {
                        key "protocol";
                        description "Enter the supported-protocol list instance";

                        leaf protocol {
                            type enumeration {
                                enum iso8473                        { value 129; }
                                enum ipv6                           { value 142; }
                                enum ip                             { value 204; }
                            }
                            description
                                "One supported protocol as reported in IIH PDUs received
                                 from the neighbor.";
                        }

                    } // list supported-protocol

                } // list adjacency

                list admin-group {
                    key "group-name";
                    description "Enter the admin-group list instance";

                    leaf group-name {
                        type types-sros:named-item;
                        description
                            "Indicates the interface admin-goup inherited from MPLS interface.
                             It identifies the admin groups to which the interface belongs.";
                    }

                } // list admin-group

            } // list interface

            list level {
                key "level-number";
                description "Enter the level list instance";

                leaf level-number {
                    type enumeration {
                        enum 1                              { value 1; }
                        enum 2                              { value 2; }
                    }
                    description "ISIS protocol level number";
                }

                leaf oper-lsp-mtu-size {
                    type int32;
                    description "Indicates the operational size of Level 1 LSPs and SNPs originated by this instance.";
                }

                leaf total-exported-routes {
                    type yang:counter32;
                    description
                        "Indicates the total number of routes exported into ISIS level 1 from the route table manager
                         when an export policy is configured";
                }

                leaf lsps {
                    type uint32;
                    description "Indicates the number of LSPs existing in the system for the particular level.";
                }

                leaf max-oper-lsp-mtu-size {
                    type int32;
                    description
                        "Indicates the maximum size of LSPs and SNPs that can be originated on
                         any circuit by this instance for the particular level.";
                }

                container overload {
                    description "Enter the overload context";

                    leaf status {
                        type types-isis:overload-status;
                        description "Indicates whether or not this level is in overload state.";
                    }

                    leaf time-left {
                        type types-sros:time-interval;
                        units "deciseconds";
                        description
                            "Indicates the remaining time, measured in units of deciseconds, before this level
                             will attempt to enter its normal state.";
                    }

                } // container overload

            } // list level

            list link-group {
                key "link-group-name";
                description "Enter the link-group list instance";

                leaf link-group-name {
                    type types-sros:named-item;
                    description "Link group name for the IS-IS protocol";
                }

                list level {
                    key "level-number";
                    description "Enter the level list instance";

                    leaf level-number {
                        type enumeration {
                            enum 1                              { value 1; }
                            enum 2                              { value 2; }
                        }
                        description "ISIS protocol level number";
                    }

                    leaf oper-state {
                        type enumeration {
                            enum normal                         { value 1; }
                            enum offset-applied                 { value 2; }
                        }
                        description "The value indicates the state of the link group at this IS-IS level.";
                    }

                    leaf oper-oper-members {
                        type uint32;
                        description
                            "The value indicates the operational value of the number of operational links below which the
                             metric of the member interfaces is increased by the configured offsets.";
                    }

                    leaf oper-revert-members {
                        type uint32;
                        description
                            "The value indicates the operational value of the minimum number of links that must be
                             operational after the offsets were applied in order for the metrics of
                             the member interfaces to be returned to normal.";
                    }

                    leaf members-count {
                        type uint32;
                        description
                            "The value indicates the number of interfaces that are a member of the
                             link group indicated by name at this IS-IS level.";
                    }

                    leaf active-members {
                        type uint32;
                        description
                            "The value indicates the number of active interfaces that are a member
                             of the link group indicated by name at this IS-IS level.";
                    }

                    list member {
                        key "interface-name";
                        description "Add a list entry for member";

                        leaf interface-name {
                            type leafref {
                                path "../../../../interface/interface-name";
                            }
                            description "Router interface name for this link group";
                        }

                        leaf oper-state {
                            type enumeration {
                                enum up                             { value 1; }
                                enum down                           { value 2; }
                                enum bit-error-rate                 { value 3; }
                            }
                            description
                                "The value indicates the state of this interface at this IS-IS level associated
                                 with the link group indicated by name.";
                        }

                    } // list member

                } // list level

            } // list link-group

            list lfa-coverage {
                key "level-number family-coverage";
                description "Enter the lfa-coverage list instance";

                leaf level-number {
                    type enumeration {
                        enum 1                              { value 1; }
                        enum 2                              { value 2; }
                    }
                    description "ISIS protocol level number";
                }

                leaf family-coverage {
                    type enumeration {
                        enum ipv4                           { value 0; }
                        enum ipv6                           { value 1; }
                        enum ipv4-mcast                     { value 2; }
                        enum ipv6-mcast                     { value 3; }
                    }
                    description
                        "The value of the object tmnxIsisLfaFamilyCoverage specifies the
                         multi topology (MT's) for which LFA coverage has been computed.

                         Possible values are:

                         ipv4(0)      - indicates MT0 or standard topology
                         ipv6(1)      - indicates MT2 or IPv6 routing topology
                         ipv4-mcast(2) - indicates MT3 or IPv4 multicast routing topology
                         ipv6-mcast(3) - indicates MT4 or IPv6 multicast routing topology.";
                }

                container nodes {
                    description "Enter the nodes context";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container nodes

                container ipv4 {
                    description "Enter the ipv4 context";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container ipv4

                container ipv6 {
                    description "Enter the ipv6 context";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container ipv6

            } // list lfa-coverage

            list sr-lfa-coverage {
                key "level-number multi-topology-id sid-type protocol-version";
                description "Enter the sr-lfa-coverage list instance";

                leaf level-number {
                    type types-isis:level;
                    description "Specifies the IS-IS protocol level to which these attributes are applied.";
                }

                leaf multi-topology-id {
                    type enumeration {
                        enum ipv4                           { value 0; }
                        enum ipv6                           { value 1; }
                        enum ipv4-mcast                     { value 2; }
                        enum ipv6-mcast                     { value 3; }
                    }
                    description
                        "The value specifies the multi-topology id number for the path.

                         Possible values are:

                         ipv4(0)      - indicates MT0 or standard topology
                         ipv6(1)      - indicates MT2 or IPv6 routing topology
                         ipv4-mcast(2) - indicates MT3 or IPv4 multicast routing topology
                         ipv6-mcast(3) - indicates MT4 or IPv6 multicast routing topology.";
                }

                leaf sid-type {
                    type enumeration {
                        enum node-sid                       { value 0; }
                        enum adj-sid                        { value 1; }
                    }
                    description
                        "The value specifies the SID type for which SR LFA coverage
                         has been computed.";
                }

                leaf protocol-version {
                    type enumeration {
                        enum ipv4                           { value 0; }
                        enum ipv6                           { value 1; }
                    }
                    description "The value specifies the protocol version for which SR LFA coverage has been computed.";
                }

                leaf lfa-covered {
                    type uint32;
                    description "The value indicates the number of SIDs for which an LFA is found.";
                }

                leaf lfa-covered-percent {
                    type types-sros:percent;
                    description "The value indicates the portion of SIDs for which an LFA is found.";
                }

                leaf remote-lfa-covered {
                    type uint32;
                    description "The value indicates the number of SIDs for which an Remote LFA is found.";
                }

                leaf remote-lfa-covered-percent {
                    type types-sros:percent;
                    description "The value indicates the portion of SIDs for which an Remote LFA is found.";
                }

                leaf ti-lfa-covered {
                    type uint32;
                    description "The value indicates the number of SIDs for which an Topology Independent LFA is found.";
                }

                leaf ti-lfa-covered-percent {
                    type types-sros:percent;
                    description "The value indicates the portion of SIDs for which an LFA is found.";
                }

                leaf total-sid {
                    type uint32;
                    description "The value indicates the number of SIDs eligible for SR LFA calculation";
                }

                leaf backup-total-sid {
                    type uint32;
                    description "The value indicates the number of SIDs for which an LFA, Remote LFA or Topology Independent LFA is found";
                }

                leaf backup-total-sid-percent {
                    type uint32;
                    description "The value indicates the portion of SIDs for which an LFA, Remote LFA or Topology Independent LFA is found";
                }

            } // list sr-lfa-coverage

            list database {
                key "level-number lsp-id";
                description "Enter the database list instance";

                leaf level-number {
                    type enumeration {
                        enum 1                              { value 1; }
                        enum 2                              { value 2; }
                    }
                    description "ISIS protocol level number";
                }

                leaf lsp-id {
                    type types-isis:lsp-id;
                    description
                        "The value specifies the LSP Id and is given in the format as 6 octets of adjacency system-id followed by
                         1 octet Lan-ID and 1 octet LSP Number.";
                }

                leaf seq {
                    type yang:counter32;
                    description
                        "The value indicates the sequence number of
                         an LSP and is a four byte quantity that represents the version of an LSP.

                         The higher the sequence number, the more up to date the information.

                         The sequence number is always incremented by the system that originated
                         the LSP and ensures that there is only one version of that LSP in the
                         entire network.";
                }

                leaf checksum {
                    type int32 {
                        range "0..65535";
                    }
                    description
                        "The value indicates the checksum of
                         contents of LSP from the SourceID field in the LSP till the end.

                         The checksum is computed using the Fletcher checksum algorithm. ";
                }

                leaf zero-rtl {
                    type boolean;
                    description
                        "The value indicates the LSP state if
                         it has once reached zero remaining lifetime.

                         If this object is 'true' then the object lifetime-remain will
                         maintain the time remaining after which this LSP will be discarded.";
                }

                leaf lifetime-remain {
                    type int32 {
                        range "0..65535";
                    }
                    units "seconds";
                    description
                        "The value indicates the
                         Remaining lifetime of this LSP and is a decrementing counter that
                         decrements in seconds starting from the value as received in the
                         LSP if not self-originated OR from lsp-life-time for self
                         originated LSPs.

                         When the remaining lifetime becomes zero, the contents of the LSP
                         should not be considered for SPF calculation.";
                }

                leaf version {
                    type int32;
                    description
                        "The value indicates the version of
                         the ISIS protocol that has generated the LSP";
                }

                leaf pkt-type {
                    type int32;
                    description
                        "The value indicates the packet type
                         for instance Hello PDUs, LSPs, CSNPs OR PSNPs at both IS-IS protocol
                         levels i.e. L1 and L2 as maintained in of the object packet-type.";
                }

                leaf pkt-version {
                    type int32;
                    description
                        "The value indicates the version of
                         the ISIS protocol that has generated the Packet.";
                }

                leaf attributes {
                    type int32;
                    description
                        "The value indicates the attributes
                         associated with the LSP and these include the attached bit,
                         overload bit, IS type of the system originating the LSP and the
                         partition repair capability.

                         The attached bit and the overload bit are of significance only when
                         present in the LSP numbered zero and should be ignored on receipt in
                         any other LSP.";
                }

                leaf max-area {
                    type int32;
                    description
                        "The value indicates the maximum number
                         of areas supported by the originator of the LSP.

                         A value of 0 indicates a default of 3 areas. ";
                }

                leaf alloc-len {
                    type int32;
                    description
                        "The value indicates the length
                         allocated for the LSP to be stored.";
                }

                leaf system-id {
                    type types-igp:system-id;
                    description "The value indicates the system-id as part of lsp-id used by the originator.";
                }

                leaf system-id-len {
                    type int32;
                    description
                        "The value indicates the length of
                         the system-id as used by the originator.";
                }

                leaf used-len {
                    type int32;
                    description
                        "The value indicates the used length
                         for the LSP.

                         For an LSP that is not self originated, the used length is always equal
                         to alloc-len for self originated LSPs, the used length is
                         less than or equal to alloc-len.";
                }

                leaf value {
                    type string {
                        length "27..9778";
                    }
                    description "Contents of the LSP.";
                }

            } // list database

            list capabilities {
                key "level-number lsp-id";
                description "Enter the capabilities list instance";

                leaf level-number {
                    type enumeration {
                        enum 1                              { value 1; }
                        enum 2                              { value 2; }
                    }
                    description "ISIS protocol level number";
                }

                leaf lsp-id {
                    type leafref {
                        path "../../database[level-number=current()/../level-number]/lsp-id";
                    }
                    description
                        "The value specifies the LSP Id and is given in the format as 6 octets of adjacency system-id followed by
                         1 octet Lan-ID and 1 octet LSP Number.";
                }

                leaf tlv-buffer {
                    type string {
                        length "0..9778";
                    }
                    description "The capability TLV.";
                }

                leaf router-id {
                    type types-sros:ipv4-address;
                    description "IPv4 router-id.";
                }

                leaf s-flag {
                    type boolean;
                    description " Value of the S-flag in the router capability TLV.";
                }

                leaf d-flag {
                    type boolean;
                    description " Value of the D-flag in the router capability TLV.";
                }

            } // list capabilities

            list hostname {
                key "system-id";
                description "Enter the hostname list instance";

                leaf system-id {
                    type types-igp:system-id;
                    description "Specifies the ID for this instance of the Integrated IS-IS protocol.";
                }

                leaf host-name {
                    type types-sros:display-string;
                    description "The value indicates the mapping hostname for the corresponding system-id.";
                }

            } // list hostname

            list route {
                key "multi-topology-id destination";
                description "Enter the route list instance";

                leaf multi-topology-id {
                    type uint32;
                    description
                        "The value specifies the multi-topology id number for the path.

                         If multi-topology is not supported for the path then
                         the value should be 0.";
                }

                leaf destination {
                    type types-sros:ip-prefix;
                    description "The value specifies the IP address and mask of the route destination.";
                }

                leaf level {
                    type types-isis:level;
                    description "The value indicates the IS-IS Level at which the prefix was learned.";
                }

                leaf status {
                    type enumeration {
                        enum active                         { value 0; }
                        enum rtm-add-failed                 { value 1; }
                        enum fib-add-failed                 { value 2; }
                    }
                    description "The value indicates the reason why a route is not active.";
                }

                leaf metric {
                    type uint32;
                    description
                        "The value indicates the routing metric for a backup route.

                         The semantics of this metric are determined by the routing-protocol
                         specified in the route's ipCidrRouteProto value.

                         The value is only valid when backup-flags has a value of 'has-lfa'.";
                }

                leaf type {
                    type enumeration {
                        enum internal                       { value 1; }
                        enum external                       { value 2; }
                    }
                    description "The value indicates the type of route represented by this row entry.";
                }

                leaf tag {
                    type uint32;
                    description
                        "The value indicates a 32-bit integer route tag for this route.

                         A value of 0 indicates that the tag has not been set.";
                }

                leaf algorithm {
                    type int32 {
                        range "0|128..255";
                    }
                    description "The value indicates the algorithm.";
                }

                container backup {
                    description "Enter the backup context";

                    leaf next-hop-ip {
                        type types-sros:ip-address-with-zone;
                        description "The value specifies the IP address of the next hop for this route.";
                    }

                    leaf next-hop-type {
                        type types-isis:cidr-next-hop-type;
                        description "The value indicates the type of next hop for this backup route.";
                    }

                    leaf next-hop-owner {
                        type types-isis:cidr-next-hop-owner;
                        description "The value indicates the owner of next hop for this backup route.";
                    }

                    leaf next-hop-tunnel-id {
                        type uint32;
                        description
                            "The value indicates the auxiliary information, for next hop owner as indicated by
                             backup-next-hop-owner.

                             The value of indicates the tunnel-id existing for this backup next hop type and owner.";
                    }

                    leaf type {
                        type enumeration {
                            enum node-protection                { value 1; }
                            enum link-protection                { value 2; }
                        }
                        description
                            "The value indicates the type of protection used by the backup next-hop.

                             The value 'not-applicable' indicates that the backup next hop type
                             is not applicable
                             the value 'node-protection' indicates that the backup next hop uses a
                             node-protection mechanism
                             the value 'link-protection' indicates that the backup next hop uses
                             link-protection mechanism.";
                    }

                    leaf metric {
                        type uint32;
                        description
                            "The value indicates the routing metric for a backup route.

                             The semantics of this metric are determined by the routing-protocol
                             specified in the route's ipCidrRouteProto value.

                             The value is only valid when backup-flags has a value of 'has-lfa'.";
                    }

                    leaf flags {
                        type enumeration {
                            enum none                           { value 0; }
                            enum has-lfa                        { value 1; }
                        }
                        description
                            "The value indicates the presence or absence of LFA next-hops.

                             The value 'none' indicates that no next hop is present
                             the value 'has-lfa' indicates that an LFA next hop is present in addition
                             to the regular next-hop.";
                    }

                } // container backup

                container prefix-sid {
                    description "Enter the prefix-sid context";

                    leaf label {
                        type uint32;
                        description "The value specifies the SID label or index for this prefix.";
                    }

                    leaf flags {
                        type bits {
                            bit bit-r                          { position 0; }
                            bit bit-n                          { position 1; }
                            bit bit-p                          { position 2; }
                            bit bit-e                          { position 3; }
                            bit bit-v                          { position 4; }
                            bit bit-l                          { position 5; }
                        }
                        description
                            "The value indicates the flags of a Prefix-SID advertised by
                             an IP Reach or Label Binding TLV.

                             bit-r   (0)  - Re-advertisement flag.  If set, then the prefix to
                               which this Prefix-SID is attached, has been propagated by the
                               router either from another level (i.e.: from level-1 to level-2
                               or the opposite) or from redistribution (e.g.: from another
                               protocol).
                             bit-n   (1)  - Node-SID flag. The N-Flag is set on Prefix-SIDs
                               attached to a router loopback address.
                             bit-p   (2)  - no-PHP flag. If set, then the penultimate hop MUST NOT
                               pop the Prefix-SID before delivering the packet to the node
                               that advertised the Prefix-SID.
                             bit-e   (3)  - Explicit-Null Flag.  If set, any upstream neighbor
                               of the Prefix-SID originator MUST replace the Prefix-SID with
                               a Prefix-SID having an Explicit-NULL value (0 for IPv4 and 2 for
                               IPv6) before forwarding the packet.
                             bit-v   (4)  - Value flag. If set, then the Prefix-SID carries a
                               value (instead of an index).
                             bit-l   (5)  - Local Flag.  If set, then the value/index carried by
                               the Prefix-SID has local significance.";
                    }

                } // container prefix-sid

                list next-hop {
                    key "ecmp-index";
                    description "Enter the next-hop list instance";

                    leaf ecmp-index {
                        type types-router:ip-ecmp;
                        description "ECMP index of this route next-hop.";
                    }

                    leaf next-hop-ip {
                        type types-sros:ip-address-with-zone;
                        description "The value specifies the IP address of the next hop for this route.";
                    }

                    leaf next-hop-type {
                        type types-isis:cidr-next-hop-type;
                        description "The value indicates the type of next hop for this backup route.";
                    }

                    leaf next-hop-owner {
                        type types-isis:cidr-next-hop-owner;
                        description "The value indicates the owner of next hop for this backup route.";
                    }

                    leaf next-hop-tunnel-id {
                        type uint32;
                        description
                            "The value indicates the auxiliary information, for next hop owner as indicated by
                             backup-next-hop-owner.

                             The value of indicates the tunnel-id existing for this backup next hop type and owner.";
                    }

                    leaf spf-version {
                        type yang:counter32;
                        description "The value indicates the run of SPF calculation in which this route was selected.";
                    }

                    leaf next-hop-system-id {
                        type types-igp:system-id;
                        description
                            "The value indicates the system-id of the next hop IS through
                             which this route is reachable.";
                    }

                    leaf rtm-status {
                        type enumeration {
                            enum success                        { value 0; }
                            enum discarded                      { value 1; }
                        }
                        description "Indicates the next hop status in RTM";
                    }

                } // list next-hop

            } // list route

            list spf-log {
                key "time-stamp";
                description "Enter the spf-log list instance";

                leaf time-stamp {
                    type yang:timeticks;
                    units "centiseconds";
                    description "The value specifies the time (in centiseconds) since system-up when the SPF was ran.";
                }

                leaf duration {
                    type yang:timeticks;
                    units "centiseconds";
                    description "The value indicates the time (in centiseconds) required to complete the SPF run.";
                }

                leaf l1-nodes {
                    type uint32;
                    description "The value indicates the number of L1 nodes involved in the SPF run.";
                }

                leaf l2-nodes {
                    type uint32;
                    description "The value indicates the number of L2 nodes involved in the SPF run.";
                }

                leaf trigger-lsp-id {
                    type types-isis:lsp-id;
                    description "The value indicates the LSP-Id of the last LSP processed before the SPF run.";
                }

                leaf event-count {
                    type uint32;
                    description "The value indicates the number of SPF events that triggered the SPF calculation.";
                }

                leaf type {
                    type enumeration {
                        enum regular                        { value 0; }
                        enum lfa                            { value 1; }
                        enum partial-spf                    { value 2; }
                        enum partial-lfa                    { value 3; }
                        enum remote-lfa                     { value 4; }
                        enum ti-lfa                         { value 5; }
                    }
                    description "The value indicates the type of SPF calculation.";
                }

                leaf trigger-reason {
                    type bits {
                        bit new-adjacency                  { position 0; }
                        bit new-lsp                        { position 1; }
                        bit new-area                       { position 2; }
                        bit reach                          { position 3; }
                        bit ecmp-changed                   { position 4; }
                        bit new-metric                     { position 5; }
                        bit te-changed                     { position 6; }
                        bit restart                        { position 7; }
                        bit lsp-expired                    { position 8; }
                        bit lsp-db-changed                 { position 9; }
                        bit lsp-changed                    { position 10; }
                        bit new-preference                 { position 11; }
                        bit new-nlp-id                     { position 12; }
                        bit manual-run                     { position 13; }
                        bit admin-tag-changed              { position 14; }
                        bit tunnel-changed                 { position 15; }
                        bit throttle-end                   { position 16; }
                        bit lfa-changed                    { position 17; }
                    }
                    description
                        "The value indicates the reasons that triggered this SPF run.

                         new-sdjacency (0)      - a new adjacency was formed.
                         new-ldp (1)            - a new LSP was received.
                         new-srea (2)           - a new area was joined.
                         reach (3)              - a new prefix can be reached.
                         ecmp-changed (4)       - the number of ecmp routes to a destination changed.
                         new-metric (5)         - a route has a new metric.
                         te-changed (6)         - traffic engineering changed.
                         restart (7)            - the IS-IS router was restarted.
                         lsp-expired (8)        - an LSP expired.
                         lsp-db-changed (9)     - the IS-IS LSP database was cleared.
                         lsp-changed (10)       - an LSP changed.
                         new-preference (11)    - a route preference changed.
                         new-nlp-id (12)        - a Network Layer Protocol was added to the
                                                  IS-IS router protocol set.
                         manual-run (13)        - Manual request issued.
                         admin-tag-changed (14) - admin tag has changed.
                         tunnel-changed (15)    - list of tunnels has changed.
                         throttle-end (16)      - throttling of SPF ended.
                         lfa-changed (17)       - lfa changed.";
                }

            } // list spf-log

            list received-area-address {
                key "area-address";
                description "Enter the received-area-address list instance";

                leaf area-address {
                    type types-isis:area-address;
                    description
                        "An area address reported in a Level 1 LSP received by
                         this instance of the protocol.";
                }

            } // list received-area-address

            list topology {
                key "level-number multi-topology-id path-id";
                description "Enter the topology list instance";

                leaf level-number {
                    type enumeration {
                        enum 1                              { value 1; }
                        enum 2                              { value 2; }
                    }
                    description "ISIS protocol level number";
                }

                leaf multi-topology-id {
                    type uint32;
                    description
                        "The value specifies the multi-topology id number for the path.

                         If multi-topology is not supported for the path then
                         the value should be 0.";
                }

                leaf path-id {
                    type string {
                        length "16";
                    }
                    description
                        "The value specifies the path identifier
                         and has first 6 octets as the system-id followed by one octet
                         of the Lan-ID.";
                }

                leaf metric {
                    type uint32;
                    description
                        "The value indicates the metric
                         assigned to this path entry after SPF calculations.

                         The lower the metric value, the shorter the path and hence more
                         preferred by the protocol.";
                }

                leaf route-type {
                    type enumeration {
                        enum spf                            { value 0; }
                        enum lfa                            { value 1; }
                    }
                    description "The value indicates whether a backup route exists for this row entry.";
                }

                container lfa {
                    description "Enter the lfa context";

                    leaf type {
                        type enumeration {
                            enum none                           { value 0; }
                            enum node-link                      { value 1; }
                            enum path-link                      { value 2; }
                        }
                        description "The value indicates the type of route represented by this row entry.";
                    }

                    leaf interface {
                        type types-sros:interface-name;
                        description
                            "The value indicates the
                             loopfree-alternate ifIndex of the outgoing interface for the path.";
                    }

                    leaf next-hop {
                        type types-igp:system-id;
                        description
                            "The value indicates the
                             loopfree-alternate next hop and is referenced by the system-id.";
                    }

                    leaf metric {
                        type uint32;
                        description
                            "The value indicates the metric assigned to this entry which are a result
                             of loopfree-alternate calculations.

                             The lower the metric value, the shorter is the path and hence more
                             preferred by the protocol.";
                    }

                } // container lfa

                list next-hop {
                    key "ecmp-index";
                    description "Enter the next-hop list instance";

                    leaf ecmp-index {
                        type uint32;
                        description "ECMP index of this route next-hop.";
                    }

                    leaf interface {
                        type types-sros:interface-name;
                        description "The value specifies the outgoing interface for the path.";
                    }

                    leaf next-hop-system-id {
                        type types-igp:system-id;
                        description
                            "The value specifies the system-id of the next hop and is used to reference the
                             next hop for this route.";
                    }

                    leaf snpa {
                        type types-isis:snpa-address;
                        description "The value indicates the subnet point of attachment for this path.";
                    }

                } // list next-hop

            } // list topology

            list prefix-sid {
                key "multi-topology-id destination advertising-system-id level-number label";
                description "Enter the prefix-sid list instance";

                leaf multi-topology-id {
                    type uint32;
                    description
                        "The value specifies the multi-topology id number for the path.

                         If multi-topology is not supported for the path then
                         the value should be 0.";
                }

                leaf destination {
                    type types-sros:ip-prefix;
                    description "The value specifies the IP address and mask of the route destination.";
                }

                leaf advertising-system-id {
                    type types-igp:system-id;
                    description
                        "The value specifies the system-id of the advertising
                         IS through which this prefix/SID is reachable.";
                }

                leaf level-number {
                    type enumeration {
                        enum 1                              { value 1; }
                        enum 2                              { value 2; }
                    }
                    description "ISIS protocol level number";
                }

                leaf label {
                    type uint32;
                    description "The value specifies the SID label for this prefix.";
                }

                leaf flags {
                    type bits {
                        bit bit-r                          { position 0; }
                        bit bit-n                          { position 1; }
                        bit bit-p                          { position 2; }
                        bit bit-e                          { position 3; }
                        bit bit-v                          { position 4; }
                        bit bit-l                          { position 5; }
                    }
                    description
                        "The value indicates the flags of a Prefix-SID advertised by
                         an IP Reach or Label Binding TLV.

                         bit-r   (0)  - Re-advertisement flag.  If set, then the prefix to
                           which this Prefix-SID is attached, has been propagated by the
                           router either from another level (i.e.: from level-1 to level-2
                           or the opposite) or from redistribution (e.g.: from another
                           protocol).
                         bit-n   (1)  - Node-SID flag. The N-Flag is set on Prefix-SIDs
                           attached to a router loopback address.
                         bit-p   (2)  - no-PHP flag. If set, then the penultimate hop MUST NOT
                           pop the Prefix-SID before delivering the packet to the node
                           that advertised the Prefix-SID.
                         bit-e   (3)  - Explicit-Null Flag.  If set, any upstream neighbor
                           of the Prefix-SID originator MUST replace the Prefix-SID with
                           a Prefix-SID having an Explicit-NULL value (0 for IPv4 and 2 for
                           IPv6) before forwarding the packet.
                         bit-v   (4)  - Value flag. If set, then the Prefix-SID carries a
                           value (instead of an index).
                         bit-l   (5)  - Local Flag.  If set, then the value/index carried by
                           the Prefix-SID has local significance.";
                }

                leaf algorithm {
                    type int32 {
                        range "0|128..255";
                    }
                    description "The value indicates the algorithm related to the prefix SID.";
                }

                leaf type {
                    type enumeration {
                        enum internal                       { value 1; }
                        enum external                       { value 2; }
                    }
                    description "The value indicates the type of route represented by this row entry.";
                }

                leaf srms {
                    type boolean;
                    description
                        "The value indicates whether or not the Prefix/SID is advertised by a
                         Segment Routing Mapping Server.";
                }

                leaf srms-selected {
                    type boolean;
                    description
                        "The value indicates whether or not the prefix SID received in the
                         SRMS TLV is selected to be programmed.

                         When there is however a SID for the same prefix received in a
                         prefix TLV, that prefix SID will be programmed and not the
                         SRMS prefix SID.";
                }

                leaf shared-sid {
                    type boolean;
                    description
                        "The value indicates wheter or not the prefix SID is a
                         shared node SID that was configured system wide.

                         Can only be true for self-originated prefix-sids.";
                }

            } // list prefix-sid

            list sid-statistics {
                key "label";
                description "Enter the sid-statistics list instance";

                leaf label {
                    type uint32;
                    description "The value specifies the SID label";
                }

                leaf type {
                    type enumeration {
                        enum node                           { value 0; }
                        enum adjacency                      { value 1; }
                        enum adjacency-set                  { value 2; }
                    }
                    description "The type of SID for which statistics are collected";
                }

                leaf prefix {
                    type types-sros:ip-prefix;
                    description "The IP address type";
                }

                leaf adjacency-set {
                    type uint32 {
                        range "0..max";
                    }
                    description "When type is adjacency-set then this is the adjacency-set for whcih the sid is used";
                }

                leaf interface {
                    type types-sros:interface-name;
                    description "When type is adjacency then this is the interface on which the adjacency is formed";
                }

                leaf algorithm {
                    type uint8;
                    description
                        "The value indicates the algorithm related to the prefix SID.

                         The value can indicate a defined IGP Algorithm (value 0 is SPF) or
                         a Flexible Algorithm (range 128..255).";
                }

                container egress {
                    description "Enter the egress context";

                    leaf oper-state {
                        type enumeration {
                            enum enabled                        { value 1; }
                            enum disabled                       { value 2; }
                            enum no-resource                    { value 3; }
                        }
                        description "The statistics operational state of this SID for this direction";
                    }

                    leaf octets {
                        type yang:counter64;
                        description "The number of octets";
                    }

                    leaf packets {
                        type yang:counter64;
                        description "The number of packets";
                    }

                } // container egress

                container ingress {
                    description "Enter the ingress context";

                    leaf oper-state {
                        type enumeration {
                            enum enabled                        { value 1; }
                            enum disabled                       { value 2; }
                            enum no-resource                    { value 3; }
                        }
                        description "The statistics operational state of this SID for this direction";
                    }

                    leaf octets {
                        type yang:counter64;
                        description "The number of octets";
                    }

                    leaf packets {
                        type yang:counter64;
                        description "The number of packets";
                    }

                } // container ingress

            } // list sid-statistics

        } // list isis

    } // grouping state-router-isis

}
