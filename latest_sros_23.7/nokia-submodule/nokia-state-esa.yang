submodule nokia-state-esa {

    yang-version "1.1";

    belongs-to nokia-state { prefix "state"; }

    import ietf-yang-types                { prefix "yang"; }
    import nokia-sros-yang-extensions     { prefix "sros-ext"; }
    import nokia-types-esa                { prefix "types-esa"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for ESA configuration on SR OS based routers.

         Copyright 2016 Nokia. All rights reserved. Reproduction of this document
         is authorized on the condition that the foregoing copyright notice is included.

         This nokia-state-esa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-19";

    grouping state-esa {
        ///nokia-state/state/esa
        list esa {
            key "esa-id";
            description "Enter the esa list instance";

            ///nokia-state/state/esa/esa-id
            leaf esa-id {
                type types-esa:esa-id;
                description "ESA ID";
            }

            ///nokia-state/state/esa/oper-state
            leaf oper-state {
                type enumeration {
                    enum unknown                        { value 1; }
                    enum in-service                     { value 2; }
                    enum out-of-service                 { value 3; }
                    enum booting                        { value 4; }
                    enum failed                         { value 5; }
                    enum provisioned                    { value 6; }
                    enum unprovisioned                  { value 7; }
                    enum upgrade                        { value 8; }
                    enum fw-upgrade                     { value 9; }
                }
                description "Indicates the operational state of the ESA.";
            }

            ///nokia-state/state/esa/oper-flags
            leaf oper-flags {
                type bits {
                    bit admin-down                     { position 0; }
                    bit esa-sw-mismatch                { position 1; }
                    bit esa-mismatch                   { position 2; }
                    bit connect-failed                 { position 3; }
                    bit fw-update-failed               { position 4; }
                    bit boot-failed                    { position 5; }
                }
                description
                    "Indicates the operational flags that determine the status
                     of the ESA.";
            }

            ///nokia-state/state/esa/cores-available
            leaf cores-available {
                type yang:gauge32;
                description "Indicates the total number of available cores on the ESA.";
            }

            ///nokia-state/state/esa/cores-allocated
            leaf cores-allocated {
                type yang:gauge32;
                description "Indicates the total number of allocated cores on the ESA.";
            }

            ///nokia-state/state/esa/memory-available
            leaf memory-available {
                type yang:gauge32;
                units "gigabytes";
                description
                    "Indicates the total amount of available memory (in GigaBytes)
                     on the ESA.";
            }

            ///nokia-state/state/esa/memory-allocated
            leaf memory-allocated {
                type yang:gauge32;
                units "gigabytes";
                description
                    "Indicates the total amount of allocated memory (in GigaBytes)
                     on the ESA.";
            }

            ///nokia-state/state/esa/software-version
            leaf software-version {
                type string {
                    length "0..255";
                }
                description "Indicates the software version currently running on the ESA.";
            }

            ///nokia-state/state/esa/time-of-boot
            leaf time-of-boot {
                type yang:date-and-time;
                description
                    "Indicates date and time the software running on this
                     ESA was last rebooted.";
            }

            ///nokia-state/state/esa/system-manufacturer
            leaf system-manufacturer {
                type string {
                    length "0..255";
                }
                description "Indicates the system manufacturer of the ESA.";
            }

            ///nokia-state/state/esa/system-product-name
            leaf system-product-name {
                type string {
                    length "0..255";
                }
                description "Indicates the system product name of the ESA.";
            }

            ///nokia-state/state/esa/system-serial-number
            leaf system-serial-number {
                type string {
                    length "0..255";
                }
                description "Indicates the system serial number of the ESA.";
            }

            ///nokia-state/state/esa/performance-mode
            leaf performance-mode {
                type boolean;
                description
                    "Indicates whether the ESA is in performance (true)
                     or functional (false) mode.";
            }

            ///nokia-state/state/esa/export-restricted
            leaf export-restricted {
                type boolean;
                description
                    "Indicates whether the ESA is in export restricted mode or not.
                     In this mode, some restrictions apply to certain vm types.";
            }

            ///nokia-state/state/esa/hardware-status
            leaf hardware-status {
                type enumeration {
                    enum unknown                        { value 1; }
                    enum ok                             { value 2; }
                    enum degraded                       { value 3; }
                    enum critical                       { value 4; }
                    enum unsupported                    { value 5; }
                }
                description "Indicates the hardware status reported by the ESA.";
            }

            ///nokia-state/state/esa/power-supply-1-status
            leaf power-supply-1-status {
                type types-esa:esa-device-state;
                description "Indicates the status of power supply 1 as reported by the ESA.";
            }

            ///nokia-state/state/esa/power-supply-2-status
            leaf power-supply-2-status {
                type types-esa:esa-device-state;
                description "Indicates the status of power supply 2 as reported by the ESA.";
            }

            ///nokia-state/state/esa/power-supply-1-temp
            leaf power-supply-1-temp {
                type int32;
                units "degrees celsius";
                description
                    "Indicates the temperature of power supply 1 as reported by the ESA.
                     This is only supported on ESA-100G.
                     A temperature of 0 means that this is not supported and
                     not possible to retrieve on the ESA.";
            }

            ///nokia-state/state/esa/power-supply-2-temp
            leaf power-supply-2-temp {
                type int32;
                units "degrees celsius";
                description
                    "Indicates the temperature of power supply 2 as reported by the ESA.
                     This is only supported on ESA-100G.
                     A temperature of 0 means that this is not supported and
                     not possible to retrieve on the ESA.";
            }

            ///nokia-state/state/esa/fan-redundancy
            leaf fan-redundancy {
                type types-esa:esa-device-redundancy-state;
                description "Indicates the fan redundancy status as reported by the ESA.";
            }

            ///nokia-state/state/esa/fan-status
            leaf fan-status {
                type types-esa:esa-device-state;
                description "Indicates the fan status as reported by the ESA.";
            }

            ///nokia-state/state/esa/power-supply-mismatch-status
            leaf power-supply-mismatch-status {
                type types-esa:esa-device-mismatch-state;
                description "Indicates the mismatch status of power supplies as reported by the ESA.";
            }

            ///nokia-state/state/esa/power-supply-redundancy
            leaf power-supply-redundancy {
                type types-esa:esa-device-redundancy-state;
                description "Indicates the redundancy status of power supplies as reported by the ESA.";
            }

            ///nokia-state/state/esa/temperature-status
            leaf temperature-status {
                type types-esa:esa-device-state;
                description
                    "Indicates the temperature status as reported by the ESA, as follows:
                        - Ok      : Temperature within normal operating range.
                        - Degraded: Temperature is outside the normal operating range.
                                    Depending on the system configuration, this system
                                    might be shut down.
                        - Failed  : Temperature exceeded on the ESA.";
            }

            ///nokia-state/state/esa/cpu-1-temperature
            leaf cpu-1-temperature {
                type int32;
                units "degrees celsius";
                description
                    "Indicates the CPU temperature as reported by the ESA.
                     This is only supported on ESA-100G.
                     A temperature of 0 means that this is not supported and
                     not possible to retrieve on the ESA. ";
            }

            ///nokia-state/state/esa/cpu-2-temperature
            leaf cpu-2-temperature {
                type int32;
                units "degrees celsius";
                description
                    "Indicates the CPU temperature as reported by the ESA.
                     This is only supported on ESA-100G.
                     A temperature of 0 means that this is not supported and
                     not possible to retrieve on the ESA. ";
            }

            ///nokia-state/state/esa/host-port
            list host-port {
                key "host-port";
                description "Add a list entry for host-port";

                ///nokia-state/state/esa/host-port/host-port
                leaf host-port {
                    type types-sros:port;
                    description "Ethernet port associated with the ESA";
                }

                ///nokia-state/state/esa/host-port/socket-id
                leaf socket-id {
                    type uint32;
                    description "Indicates the socket number that the ESA host port resides on.";
                }

                ///nokia-state/state/esa/host-port/nic-if-name
                leaf nic-if-name {
                    type types-sros:display-string;
                    description "Indicates the nic interface name that the ESA host port is connected to.";
                }

            } // list host-port

            ///nokia-state/state/esa/vm
            list vm {
                key "vm-id";
                description "Enter the vm list instance";

                ///nokia-state/state/esa/vm/vm-id
                leaf vm-id {
                    type types-esa:vm-id;
                    description "VM ID";
                }

                ///nokia-state/state/esa/vm/oper-state
                leaf oper-state {
                    type enumeration {
                        enum unknown                        { value 1; }
                        enum in-service                     { value 2; }
                        enum out-of-service                 { value 3; }
                        enum booting                        { value 4; }
                        enum failed                         { value 5; }
                        enum provisioned                    { value 6; }
                        enum unprovisioned                  { value 7; }
                        enum upgrade                        { value 8; }
                    }
                    description "Indicates the operational state of the ESA VM.";
                }

                ///nokia-state/state/esa/vm/oper-flags
                leaf oper-flags {
                    type bits {
                        bit admin-down                     { position 0; }
                        bit boot-failure                   { position 1; }
                        bit out-of-esa-rsrcs               { position 2; }
                        bit connect-failed                 { position 3; }
                        bit provision-fail                 { position 4; }
                        bit core-failure                   { position 5; }
                        bit forced-failure                 { position 6; }
                        bit icc-failure                    { position 7; }
                        bit export-restricted              { position 8; }
                        bit sw-ver-mismatch                { position 9; }
                        bit insufficient-core-allocation   { position 10; }
                        bit insufficient-memory-allocation { position 11; }
                        bit host-port-conn-fail            { position 12; }
                        bit vm-cores-exceed-os-limit       { position 13; }
                    }
                    description
                        "Indicates the operational flags that determine the status of
                         the ESA VM.";
                }

                ///nokia-state/state/esa/vm/time-of-boot
                leaf time-of-boot {
                    type yang:date-and-time;
                    description
                        "Indicates date and time the software running on this ESA VM was
                         last rebooted.";
                }

                ///nokia-state/state/esa/vm/software-version
                leaf software-version {
                    type string {
                        length "0..255";
                    }
                    description "Indicates the software version currently running on the ESA VM.";
                }

                ///nokia-state/state/esa/vm/core-util-last-coll
                leaf core-util-last-coll {
                    type yang:date-and-time;
                    description
                        "Indicates the time since system startup, when the core utilization
                         statistics were last collected.";
                }

                ///nokia-state/state/esa/vm/tunnel
                container tunnel {
                    description "Enter the tunnel context";

                    ///nokia-state/state/esa/vm/tunnel/ipsec
                    container ipsec {
                        description "Enter the ipsec context";

                        ///nokia-state/state/esa/vm/tunnel/ipsec/lockout-client
                        list lockout-client {
                            key "public-service local-gateway-address address port";
                            description "Enter the lockout-client list instance";

                            ///nokia-state/state/esa/vm/tunnel/ipsec/lockout-client/public-service
                            leaf public-service {
                                type types-services:service-name;
                                description
                                    "The value of router-service-name is 'Base' for IES services.
                                     The value of router-service-name is the name of the service for VPRN services.";
                            }

                            ///nokia-state/state/esa/vm/tunnel/ipsec/lockout-client/local-gateway-address
                            leaf local-gateway-address {
                                type types-sros:ip-address;
                                description "The IP address of the local SAP IPsec gateway.";
                            }

                            ///nokia-state/state/esa/vm/tunnel/ipsec/lockout-client/address
                            leaf address {
                                type types-sros:ip-address;
                                description "The IP address of the lockout client.";
                            }

                            ///nokia-state/state/esa/vm/tunnel/ipsec/lockout-client/port
                            leaf port {
                                type union {
                                    type enumeration {
                                        enum all {
                                            value 0;
                                            description "all ports under the lockout client address are locked out";
                                        }
                                    }
                                    type types-sros:tcp-udp-port-non-zero;
                                }
                                description
                                    "The port number of the lockout client.
                                     The value 'all' means that all ports under
                                     the lockout client address are locked out.";
                            }

                            ///nokia-state/state/esa/vm/tunnel/ipsec/lockout-client/lockout
                            leaf lockout {
                                type boolean;
                                description
                                    "Indicates whether a client is locked out by the system.

                                     The value of 'true' indicates that the client is locked out and
                                     all IKE traffics from this client are rejected by the system.
                                     The value of 'false' indicates that the system still accepts IKE
                                     traffic from this client but the client has failed on certain
                                     IKE authentications.";
                            }

                            ///nokia-state/state/esa/vm/tunnel/ipsec/lockout-client/remaining-block-time
                            leaf remaining-block-time {
                                type union {
                                    type enumeration {
                                        enum infinite {
                                            value 0;
                                            description "the client will never be unblocked";
                                        }
                                    }
                                    type types-sros:time-duration {
                                        range "1..max";
                                    }
                                }
                                description
                                    "The time remaining until this client is unblocked.

                                     A value of 'infinite' indicates that this client will never be unblocked.";
                            }

                            ///nokia-state/state/esa/vm/tunnel/ipsec/lockout-client/statistics
                            container statistics {
                                description "Enter the statistics context";

                                ///nokia-state/state/esa/vm/tunnel/ipsec/lockout-client/statistics/failed-attempts
                                leaf failed-attempts {
                                    type yang:counter32;
                                    description
                                        "The number of failed authentication attempts from the lockout client
                                         within the lockout duration.";
                                }

                                ///nokia-state/state/esa/vm/tunnel/ipsec/lockout-client/statistics/dropped-packets
                                leaf dropped-packets {
                                    type yang:counter32;
                                    description "The number of dropped packets for the lockout client.";
                                }

                            } // container statistics

                        } // list lockout-client

                    } // container ipsec

                    ///nokia-state/state/esa/vm/tunnel/statistics
                    container statistics {
                        description "Enter the statistics context";

                        ///nokia-state/state/esa/vm/tunnel/statistics/datapath
                        container datapath {
                            description "Enter the datapath context";

                            ///nokia-state/state/esa/vm/tunnel/statistics/datapath/encrypted-packets
                            leaf encrypted-packets {
                                type yang:counter64;
                                description "The number of packets encrypted by the IPsec data path";
                            }

                            ///nokia-state/state/esa/vm/tunnel/statistics/datapath/encrypted-bytes
                            leaf encrypted-bytes {
                                type yang:counter64;
                                description "The number of bytes encrypted by the IPsec data path";
                            }

                            ///nokia-state/state/esa/vm/tunnel/statistics/datapath/decrypted-packets
                            leaf decrypted-packets {
                                type yang:counter64;
                                description "The number of packets decrypted by the IPsec data path";
                            }

                            ///nokia-state/state/esa/vm/tunnel/statistics/datapath/decrypted-bytes
                            leaf decrypted-bytes {
                                type yang:counter64;
                                description "The number of bytes decrypted by the IPsec data path";
                            }

                            ///nokia-state/state/esa/vm/tunnel/statistics/datapath/outbound-dropped-packets
                            leaf outbound-dropped-packets {
                                type yang:counter64;
                                description
                                    "The number of packets dropped before and during outbound (encryption)
                                     processing by the IPsec data path.";
                            }

                            ///nokia-state/state/esa/vm/tunnel/statistics/datapath/outbound-sa-misses
                            leaf outbound-sa-misses {
                                type yang:counter64;
                                description
                                    "The number of packets dropped before outbound (encryption) processing by
                                     the IPsec data path due to no SA (security association) present.";
                            }

                            ///nokia-state/state/esa/vm/tunnel/statistics/datapath/outbound-policy-entry-misses
                            leaf outbound-policy-entry-misses {
                                type yang:counter32;
                                description
                                    "The number of packets dropped before outbound (encryption) processing
                                     by the IPsec data path due to no matching Policy Entry.";
                            }

                            ///nokia-state/state/esa/vm/tunnel/statistics/datapath/inbound-dropped-packets
                            leaf inbound-dropped-packets {
                                type yang:counter64;
                                description
                                    "The number of packets dropped before and during inbound (decryption)
                                     processing by the IPsec data path.";
                            }

                            ///nokia-state/state/esa/vm/tunnel/statistics/datapath/inbound-sa-misses
                            leaf inbound-sa-misses {
                                type yang:counter64;
                                description
                                    "The number of packets dropped before inbound (decryption) processing by
                                     the IPsec data path due to no SA (security association) present.";
                            }

                            ///nokia-state/state/esa/vm/tunnel/statistics/datapath/inbound-ip-dst-src-mismatches
                            leaf inbound-ip-dst-src-mismatches {
                                type yang:counter32;
                                description
                                    "The the number of packets dropped before inbound (decryption) processing
                                     by the IPsec data path due to the received packet's outer IP
                                     destination or source address does not match the Tunnel's local or
                                     peer gateway address.";
                            }

                            ///nokia-state/state/esa/vm/tunnel/statistics/datapath/transmit-packet-errors
                            leaf transmit-packet-errors {
                                type yang:counter32;
                                description "The number of packets transmit failures by the IPsec data path.";
                            }

                            ///nokia-state/state/esa/vm/tunnel/statistics/datapath/fragments-received
                            leaf fragments-received {
                                type yang:counter64;
                                description "The number of fragments received by the IPsec data path.";
                            }

                            ///nokia-state/state/esa/vm/tunnel/statistics/datapath/reassembled-packets
                            leaf reassembled-packets {
                                type yang:counter64;
                                description "The number of packets reassembled by the IPsec data path.";
                            }

                            ///nokia-state/state/esa/vm/tunnel/statistics/datapath/fragment-timeout-drops
                            leaf fragment-timeout-drops {
                                type yang:counter64;
                                description "The number of fragments dropped due to timeout by the IPsec data path.";
                            }

                            ///nokia-state/state/esa/vm/tunnel/statistics/datapath/fragments-total-drops
                            leaf fragments-total-drops {
                                type yang:counter64;
                                description "The number of total fragments dropped by the IPsec data path.";
                            }

                            ///nokia-state/state/esa/vm/tunnel/statistics/datapath/drop-too-big-df-set-packets
                            leaf drop-too-big-df-set-packets {
                                type yang:counter64;
                                description
                                    "The number of packets with DF bit set dropped in this Tunnel exceeding MTU size
                                     and with clear tunnel DF bit not set.";
                            }

                            ///nokia-state/state/esa/vm/tunnel/statistics/datapath/gre-ip-tnl
                            container gre-ip-tnl {
                                description "Enter the gre-ip-tnl context";

                                ///nokia-state/state/esa/vm/tunnel/statistics/datapath/gre-ip-tnl/received-packets
                                leaf received-packets {
                                    type yang:counter64;
                                    description "The number of packets received by the GRE tunnel data path.";
                                }

                                ///nokia-state/state/esa/vm/tunnel/statistics/datapath/gre-ip-tnl/received-bytes
                                leaf received-bytes {
                                    type yang:counter64;
                                    description "The number of bytes received by the GRE tunnel data path.";
                                }

                                ///nokia-state/state/esa/vm/tunnel/statistics/datapath/gre-ip-tnl/received-errors
                                leaf received-errors {
                                    type yang:counter64;
                                    description "The number of packets dropped while receiving by the GRE tunnel data path";
                                }

                                ///nokia-state/state/esa/vm/tunnel/statistics/datapath/gre-ip-tnl/sent-packets
                                leaf sent-packets {
                                    type yang:counter64;
                                    description "The number of packets transmitted by the GRE tunnel data path.";
                                }

                                ///nokia-state/state/esa/vm/tunnel/statistics/datapath/gre-ip-tnl/sent-bytes
                                leaf sent-bytes {
                                    type yang:counter64;
                                    description "The number of bytes transmitted by the GRE tunnel data path.";
                                }

                                ///nokia-state/state/esa/vm/tunnel/statistics/datapath/gre-ip-tnl/sent-errors
                                leaf sent-errors {
                                    type yang:counter64;
                                    description "The number of packets dropped while transmitting by the GRE tunnel data path";
                                }

                            } // container gre-ip-tnl

                            ///nokia-state/state/esa/vm/tunnel/statistics/datapath/l2tpv3-tnl
                            container l2tpv3-tnl {
                                description "Enter the l2tpv3-tnl context";

                                ///nokia-state/state/esa/vm/tunnel/statistics/datapath/l2tpv3-tnl/received-packets
                                leaf received-packets {
                                    type yang:counter64;
                                    description "The number of packets received by the L2TPv3 tunnel data path.";
                                }

                                ///nokia-state/state/esa/vm/tunnel/statistics/datapath/l2tpv3-tnl/received-bytes
                                leaf received-bytes {
                                    type yang:counter64;
                                    description "The number of bytes received by the L2TPv3 tunnel data path.";
                                }

                                ///nokia-state/state/esa/vm/tunnel/statistics/datapath/l2tpv3-tnl/received-errors
                                leaf received-errors {
                                    type yang:counter64;
                                    description "The number of packets dropped while receiving by the L2TPv3 tunnel data path";
                                }

                                ///nokia-state/state/esa/vm/tunnel/statistics/datapath/l2tpv3-tnl/sent-packets
                                leaf sent-packets {
                                    type yang:counter64;
                                    description "The number of packets transmitted by the L2TPv3 tunnel data path.";
                                }

                                ///nokia-state/state/esa/vm/tunnel/statistics/datapath/l2tpv3-tnl/sent-bytes
                                leaf sent-bytes {
                                    type yang:counter64;
                                    description "The number of bytes transmitted by the L2TPv3 tunnel data path.";
                                }

                                ///nokia-state/state/esa/vm/tunnel/statistics/datapath/l2tpv3-tnl/sent-errors
                                leaf sent-errors {
                                    type yang:counter64;
                                    description "The number of packets dropped while transmitting by the L2TPv3 tunnel data path.";
                                }

                            } // container l2tpv3-tnl

                        } // container datapath

                        ///nokia-state/state/esa/vm/tunnel/statistics/control
                        container control {
                            description "Enter the control context";

                            ///nokia-state/state/esa/vm/tunnel/statistics/control/static-ipsec-tunnels
                            leaf static-ipsec-tunnels {
                                type yang:counter32;
                                description "The number of configured static IPsec tunnels on the MDA.";
                            }

                            ///nokia-state/state/esa/vm/tunnel/statistics/control/dynamic-ipsec-tunnels
                            leaf dynamic-ipsec-tunnels {
                                type yang:counter32;
                                description "The number of dynamic IPsec tunnels in use on the MDA.";
                            }

                            ///nokia-state/state/esa/vm/tunnel/statistics/control/ip-gre-tunnels
                            leaf ip-gre-tunnels {
                                type yang:counter32;
                                description "The number of configured IP tunnels (with GRE headers) on the MDA.";
                            }

                            ///nokia-state/state/esa/vm/tunnel/statistics/control/ip-tunnels
                            leaf ip-tunnels {
                                type yang:counter32;
                                description "The number of configured IPv4 tunnels on the MDA.";
                            }

                            ///nokia-state/state/esa/vm/tunnel/statistics/control/l2tpv3-tunnels
                            leaf l2tpv3-tunnels {
                                type yang:counter32;
                                description "The number of configured L2TPv3 tunnels on the MDA.";
                            }

                        } // container control

                        ///nokia-state/state/esa/vm/tunnel/statistics/cpu-usage
                        container cpu-usage {
                            description "Enter the cpu-usage context";

                            ///nokia-state/state/esa/vm/tunnel/statistics/cpu-usage/control-plane
                            container control-plane {
                                description "Enter the control-plane context";

                                ///nokia-state/state/esa/vm/tunnel/statistics/cpu-usage/control-plane/current
                                container current {
                                    description "Enter the current context";

                                    ///nokia-state/state/esa/vm/tunnel/statistics/cpu-usage/control-plane/current/count
                                    leaf count {
                                        type decimal64 {
                                            range "0..100";
                                            fraction-digits 2;
                                        }
                                        units "percent";
                                        description "ISA Control Plane CPU Usage.";
                                    }

                                    ///nokia-state/state/esa/vm/tunnel/statistics/cpu-usage/control-plane/current/start-time
                                    leaf start-time {
                                        type yang:date-and-time;
                                        description "The time when the sampling interval started.";
                                    }

                                    ///nokia-state/state/esa/vm/tunnel/statistics/cpu-usage/control-plane/current/sampling-duration
                                    leaf sampling-duration {
                                        type types-sros:time-duration;
                                        description "The duration of the corresponding sampling interval.";
                                    }

                                } // container current

                                ///nokia-state/state/esa/vm/tunnel/statistics/cpu-usage/control-plane/historical
                                list historical {
                                    key "index";
                                    description "Enter the historical list instance";

                                    ///nokia-state/state/esa/vm/tunnel/statistics/cpu-usage/control-plane/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/cpu-usage/control-plane/historical/count
                                    leaf count {
                                        type decimal64 {
                                            range "0..100";
                                            fraction-digits 2;
                                        }
                                        units "percent";
                                        description "ISA Control Plane CPU Usage.";
                                    }

                                    ///nokia-state/state/esa/vm/tunnel/statistics/cpu-usage/control-plane/historical/start-time
                                    leaf start-time {
                                        type yang:date-and-time;
                                        description "The time when the sampling interval started.";
                                    }

                                    ///nokia-state/state/esa/vm/tunnel/statistics/cpu-usage/control-plane/historical/sampling-duration
                                    leaf sampling-duration {
                                        type types-sros:time-duration;
                                        description "The duration of the corresponding sampling interval.";
                                    }

                                } // list historical

                            } // container control-plane

                            ///nokia-state/state/esa/vm/tunnel/statistics/cpu-usage/data-plane
                            container data-plane {
                                description "Enter the data-plane context";

                                ///nokia-state/state/esa/vm/tunnel/statistics/cpu-usage/data-plane/current
                                container current {
                                    description "Enter the current context";

                                    ///nokia-state/state/esa/vm/tunnel/statistics/cpu-usage/data-plane/current/cpu-usage
                                    leaf cpu-usage {
                                        type decimal64 {
                                            range "0..100";
                                            fraction-digits 2;
                                        }
                                        units "percent";
                                        description "ISA Data Plane CPU Usage.";
                                    }

                                    ///nokia-state/state/esa/vm/tunnel/statistics/cpu-usage/data-plane/current/start-time
                                    leaf start-time {
                                        type yang:date-and-time;
                                        description "The time when the sampling interval started.";
                                    }

                                    ///nokia-state/state/esa/vm/tunnel/statistics/cpu-usage/data-plane/current/sampling-duration
                                    leaf sampling-duration {
                                        type types-sros:time-duration;
                                        description "The duration of the corresponding sampling interval.";
                                    }

                                } // container current

                                ///nokia-state/state/esa/vm/tunnel/statistics/cpu-usage/data-plane/historical
                                list historical {
                                    key "index";
                                    description "Enter the historical list instance";

                                    ///nokia-state/state/esa/vm/tunnel/statistics/cpu-usage/data-plane/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/cpu-usage/data-plane/historical/cpu-usage
                                    leaf cpu-usage {
                                        type decimal64 {
                                            range "0..100";
                                            fraction-digits 2;
                                        }
                                        units "percent";
                                        description "ISA Data Plane CPU Usage.";
                                    }

                                    ///nokia-state/state/esa/vm/tunnel/statistics/cpu-usage/data-plane/historical/start-time
                                    leaf start-time {
                                        type yang:date-and-time;
                                        description "The time when the sampling interval started.";
                                    }

                                    ///nokia-state/state/esa/vm/tunnel/statistics/cpu-usage/data-plane/historical/sampling-duration
                                    leaf sampling-duration {
                                        type types-sros:time-duration;
                                        description "The duration of the corresponding sampling interval.";
                                    }

                                } // list historical

                            } // container data-plane

                        } // container cpu-usage

                        ///nokia-state/state/esa/vm/tunnel/statistics/memory-allocation-failure-rate
                        container memory-allocation-failure-rate {
                            description "Enter the memory-allocation-failure-rate context";

                            ///nokia-state/state/esa/vm/tunnel/statistics/memory-allocation-failure-rate/current
                            container current {
                                description "Enter the current context";

                                ///nokia-state/state/esa/vm/tunnel/statistics/memory-allocation-failure-rate/current/count
                                leaf count {
                                    type yang:counter64;
                                    units "failures per hour";
                                    description "ISA Memory Allocation Failure Rate.";
                                }

                                ///nokia-state/state/esa/vm/tunnel/statistics/memory-allocation-failure-rate/current/start-time
                                leaf start-time {
                                    type yang:date-and-time;
                                    description "The time when the sampling interval started.";
                                }

                                ///nokia-state/state/esa/vm/tunnel/statistics/memory-allocation-failure-rate/current/sampling-duration
                                leaf sampling-duration {
                                    type types-sros:time-duration;
                                    description "The duration of the corresponding sampling interval.";
                                }

                            } // container current

                            ///nokia-state/state/esa/vm/tunnel/statistics/memory-allocation-failure-rate/historical
                            list historical {
                                key "index";
                                description "Enter the historical list instance";

                                ///nokia-state/state/esa/vm/tunnel/statistics/memory-allocation-failure-rate/historical/index
                                leaf index {
                                    type uint32 {
                                        range "2..max";
                                    }
                                    description
                                        "The index of the finished sampling interval period for this statistic.
                                         It starts with '2' and is ordered by start time of intervals so that
                                         smaller index indicate more recent intervals.";
                                }

                                ///nokia-state/state/esa/vm/tunnel/statistics/memory-allocation-failure-rate/historical/count
                                leaf count {
                                    type yang:counter64;
                                    units "failures per hour";
                                    description "ISA Memory Allocation Failure Rate.";
                                }

                                ///nokia-state/state/esa/vm/tunnel/statistics/memory-allocation-failure-rate/historical/start-time
                                leaf start-time {
                                    type yang:date-and-time;
                                    description "The time when the sampling interval started.";
                                }

                                ///nokia-state/state/esa/vm/tunnel/statistics/memory-allocation-failure-rate/historical/sampling-duration
                                leaf sampling-duration {
                                    type types-sros:time-duration;
                                    description "The duration of the corresponding sampling interval.";
                                }

                            } // list historical

                        } // container memory-allocation-failure-rate

                        ///nokia-state/state/esa/vm/tunnel/statistics/ip-tunnel
                        container ip-tunnel {
                            description "Enter the ip-tunnel context";

                            ///nokia-state/state/esa/vm/tunnel/statistics/ip-tunnel/number-of-tunnels
                            container number-of-tunnels {
                                description "Enter the number-of-tunnels context";

                                ///nokia-state/state/esa/vm/tunnel/statistics/ip-tunnel/number-of-tunnels/current
                                container current {
                                    description "Enter the current context";

                                    ///nokia-state/state/esa/vm/tunnel/statistics/ip-tunnel/number-of-tunnels/current/gre
                                    leaf gre {
                                        type yang:counter64;
                                        description "Number of GRE tunnels.";
                                    }

                                    ///nokia-state/state/esa/vm/tunnel/statistics/ip-tunnel/number-of-tunnels/current/ip
                                    leaf ip {
                                        type yang:counter64;
                                        description "Number of IP tunnels.";
                                    }

                                    ///nokia-state/state/esa/vm/tunnel/statistics/ip-tunnel/number-of-tunnels/current/start-time
                                    leaf start-time {
                                        type yang:date-and-time;
                                        description "The time when the sampling interval started.";
                                    }

                                } // container current

                            } // container number-of-tunnels

                            ///nokia-state/state/esa/vm/tunnel/statistics/ip-tunnel/throughput
                            container throughput {
                                description "Enter the throughput context";

                                ///nokia-state/state/esa/vm/tunnel/statistics/ip-tunnel/throughput/gre
                                container gre {
                                    description "Enter the gre context";

                                    ///nokia-state/state/esa/vm/tunnel/statistics/ip-tunnel/throughput/gre/current
                                    container current {
                                        description "Enter the current context";

                                        ///nokia-state/state/esa/vm/tunnel/statistics/ip-tunnel/throughput/gre/current/start-time
                                        leaf start-time {
                                            type yang:date-and-time;
                                            description "The time when the sampling interval started.";
                                        }

                                        ///nokia-state/state/esa/vm/tunnel/statistics/ip-tunnel/throughput/gre/current/sampling-duration
                                        leaf sampling-duration {
                                            type types-sros:time-duration;
                                            description "The duration of the corresponding sampling interval.";
                                        }

                                        ///nokia-state/state/esa/vm/tunnel/statistics/ip-tunnel/throughput/gre/current/packets
                                        container packets {
                                            description "Enter the packets context";

                                            ///nokia-state/state/esa/vm/tunnel/statistics/ip-tunnel/throughput/gre/current/packets/encapsulated
                                            leaf encapsulated {
                                                type yang:counter64;
                                                units "packets per second";
                                                description "Encapsulated GRE tunnel throughput.";
                                            }

                                            ///nokia-state/state/esa/vm/tunnel/statistics/ip-tunnel/throughput/gre/current/packets/decapsulated
                                            leaf decapsulated {
                                                type yang:counter64;
                                                units "packets per second";
                                                description "Decapsulated GRE tunnel throughput.";
                                            }

                                            ///nokia-state/state/esa/vm/tunnel/statistics/ip-tunnel/throughput/gre/current/packets/total
                                            leaf total {
                                                type yang:counter64;
                                                units "packets per second";
                                                description "Encapsulated and decapsulated GRE tunnel throughput.";
                                            }

                                        } // container packets

                                        ///nokia-state/state/esa/vm/tunnel/statistics/ip-tunnel/throughput/gre/current/bytes
                                        container bytes {
                                            description "Enter the bytes context";

                                            ///nokia-state/state/esa/vm/tunnel/statistics/ip-tunnel/throughput/gre/current/bytes/encapsulated
                                            leaf encapsulated {
                                                type yang:counter64;
                                                units "megabps";
                                                description "Encapsulated GRE tunnel throughput.";
                                            }

                                            ///nokia-state/state/esa/vm/tunnel/statistics/ip-tunnel/throughput/gre/current/bytes/decapsulated
                                            leaf decapsulated {
                                                type yang:counter64;
                                                units "megabps";
                                                description "Decapsulated GRE tunnel throughput.";
                                            }

                                            ///nokia-state/state/esa/vm/tunnel/statistics/ip-tunnel/throughput/gre/current/bytes/total
                                            leaf total {
                                                type yang:counter64;
                                                units "megabps";
                                                description "Encapsulated and decapsulated GRE tunnel throughput.";
                                            }

                                        } // container bytes

                                    } // container current

                                    ///nokia-state/state/esa/vm/tunnel/statistics/ip-tunnel/throughput/gre/historical
                                    list historical {
                                        key "index";
                                        description "Enter the historical list instance";

                                        ///nokia-state/state/esa/vm/tunnel/statistics/ip-tunnel/throughput/gre/historical/index
                                        leaf index {
                                            type uint32 {
                                                range "2..max";
                                            }
                                            description
                                                "The index of the finished sampling interval period for this statistic.
                                                 It starts with '2' and is ordered by start time of intervals so that
                                                 smaller index indicate more recent intervals.";
                                        }

                                        ///nokia-state/state/esa/vm/tunnel/statistics/ip-tunnel/throughput/gre/historical/start-time
                                        leaf start-time {
                                            type yang:date-and-time;
                                            description "The time when the sampling interval started.";
                                        }

                                        ///nokia-state/state/esa/vm/tunnel/statistics/ip-tunnel/throughput/gre/historical/sampling-duration
                                        leaf sampling-duration {
                                            type types-sros:time-duration;
                                            description "The duration of the corresponding sampling interval.";
                                        }

                                        ///nokia-state/state/esa/vm/tunnel/statistics/ip-tunnel/throughput/gre/historical/packets
                                        container packets {
                                            description "Enter the packets context";

                                            ///nokia-state/state/esa/vm/tunnel/statistics/ip-tunnel/throughput/gre/historical/packets/encapsulated
                                            leaf encapsulated {
                                                type yang:counter64;
                                                units "packets per second";
                                                description "Encapsulated GRE tunnel throughput.";
                                            }

                                            ///nokia-state/state/esa/vm/tunnel/statistics/ip-tunnel/throughput/gre/historical/packets/decapsulated
                                            leaf decapsulated {
                                                type yang:counter64;
                                                units "packets per second";
                                                description "Decapsulated GRE tunnel throughput.";
                                            }

                                            ///nokia-state/state/esa/vm/tunnel/statistics/ip-tunnel/throughput/gre/historical/packets/total
                                            leaf total {
                                                type yang:counter64;
                                                units "packets per second";
                                                description "Encapsulated and decapsulated GRE tunnel throughput.";
                                            }

                                        } // container packets

                                        ///nokia-state/state/esa/vm/tunnel/statistics/ip-tunnel/throughput/gre/historical/bytes
                                        container bytes {
                                            description "Enter the bytes context";

                                            ///nokia-state/state/esa/vm/tunnel/statistics/ip-tunnel/throughput/gre/historical/bytes/encapsulated
                                            leaf encapsulated {
                                                type yang:counter64;
                                                units "megabps";
                                                description "Encapsulated GRE tunnel throughput.";
                                            }

                                            ///nokia-state/state/esa/vm/tunnel/statistics/ip-tunnel/throughput/gre/historical/bytes/decapsulated
                                            leaf decapsulated {
                                                type yang:counter64;
                                                units "megabps";
                                                description "Decapsulated GRE tunnel throughput.";
                                            }

                                            ///nokia-state/state/esa/vm/tunnel/statistics/ip-tunnel/throughput/gre/historical/bytes/total
                                            leaf total {
                                                type yang:counter64;
                                                units "megabps";
                                                description "Encapsulated and decapsulated GRE tunnel throughput.";
                                            }

                                        } // container bytes

                                    } // list historical

                                } // container gre

                                ///nokia-state/state/esa/vm/tunnel/statistics/ip-tunnel/throughput/ip
                                container ip {
                                    description "Enter the ip context";

                                    ///nokia-state/state/esa/vm/tunnel/statistics/ip-tunnel/throughput/ip/current
                                    container current {
                                        description "Enter the current context";

                                        ///nokia-state/state/esa/vm/tunnel/statistics/ip-tunnel/throughput/ip/current/start-time
                                        leaf start-time {
                                            type yang:date-and-time;
                                            description "The time when the sampling interval started.";
                                        }

                                        ///nokia-state/state/esa/vm/tunnel/statistics/ip-tunnel/throughput/ip/current/sampling-duration
                                        leaf sampling-duration {
                                            type types-sros:time-duration;
                                            description "The duration of the corresponding sampling interval.";
                                        }

                                        ///nokia-state/state/esa/vm/tunnel/statistics/ip-tunnel/throughput/ip/current/packets
                                        container packets {
                                            description "Enter the packets context";

                                            ///nokia-state/state/esa/vm/tunnel/statistics/ip-tunnel/throughput/ip/current/packets/encapsulated
                                            leaf encapsulated {
                                                type yang:counter64;
                                                units "packets per second";
                                                description "Encapsulated IP tunnel throughput.";
                                            }

                                            ///nokia-state/state/esa/vm/tunnel/statistics/ip-tunnel/throughput/ip/current/packets/decapsulated
                                            leaf decapsulated {
                                                type yang:counter64;
                                                units "packets per second";
                                                description "Decapsulated IP tunnel throughput.";
                                            }

                                            ///nokia-state/state/esa/vm/tunnel/statistics/ip-tunnel/throughput/ip/current/packets/total
                                            leaf total {
                                                type yang:counter64;
                                                units "packets per second";
                                                description "Encapsulated and decapsulated IP tunnel throughput.";
                                            }

                                        } // container packets

                                        ///nokia-state/state/esa/vm/tunnel/statistics/ip-tunnel/throughput/ip/current/bytes
                                        container bytes {
                                            description "Enter the bytes context";

                                            ///nokia-state/state/esa/vm/tunnel/statistics/ip-tunnel/throughput/ip/current/bytes/encapsulated
                                            leaf encapsulated {
                                                type yang:counter64;
                                                units "megabps";
                                                description "Encapsulated IP tunnel throughput.";
                                            }

                                            ///nokia-state/state/esa/vm/tunnel/statistics/ip-tunnel/throughput/ip/current/bytes/decapsulated
                                            leaf decapsulated {
                                                type yang:counter64;
                                                units "megabps";
                                                description "Decapsulated IP tunnel throughput.";
                                            }

                                            ///nokia-state/state/esa/vm/tunnel/statistics/ip-tunnel/throughput/ip/current/bytes/total
                                            leaf total {
                                                type yang:counter64;
                                                units "megabps";
                                                description "Encapsulated and decapsulated IP tunnel throughput.";
                                            }

                                        } // container bytes

                                    } // container current

                                    ///nokia-state/state/esa/vm/tunnel/statistics/ip-tunnel/throughput/ip/historical
                                    list historical {
                                        key "index";
                                        description "Enter the historical list instance";

                                        ///nokia-state/state/esa/vm/tunnel/statistics/ip-tunnel/throughput/ip/historical/index
                                        leaf index {
                                            type uint32 {
                                                range "2..max";
                                            }
                                            description
                                                "The index of the finished sampling interval period for this statistic.
                                                 It starts with '2' and is ordered by start time of intervals so that
                                                 smaller index indicate more recent intervals.";
                                        }

                                        ///nokia-state/state/esa/vm/tunnel/statistics/ip-tunnel/throughput/ip/historical/start-time
                                        leaf start-time {
                                            type yang:date-and-time;
                                            description "The time when the sampling interval started.";
                                        }

                                        ///nokia-state/state/esa/vm/tunnel/statistics/ip-tunnel/throughput/ip/historical/sampling-duration
                                        leaf sampling-duration {
                                            type types-sros:time-duration;
                                            description "The duration of the corresponding sampling interval.";
                                        }

                                        ///nokia-state/state/esa/vm/tunnel/statistics/ip-tunnel/throughput/ip/historical/packets
                                        container packets {
                                            description "Enter the packets context";

                                            ///nokia-state/state/esa/vm/tunnel/statistics/ip-tunnel/throughput/ip/historical/packets/encapsulated
                                            leaf encapsulated {
                                                type yang:counter64;
                                                units "packets per second";
                                                description "Encapsulated IP tunnel throughput.";
                                            }

                                            ///nokia-state/state/esa/vm/tunnel/statistics/ip-tunnel/throughput/ip/historical/packets/decapsulated
                                            leaf decapsulated {
                                                type yang:counter64;
                                                units "packets per second";
                                                description "Decapsulated IP tunnel throughput.";
                                            }

                                            ///nokia-state/state/esa/vm/tunnel/statistics/ip-tunnel/throughput/ip/historical/packets/total
                                            leaf total {
                                                type yang:counter64;
                                                units "packets per second";
                                                description "Encapsulated and decapsulated IP tunnel throughput.";
                                            }

                                        } // container packets

                                        ///nokia-state/state/esa/vm/tunnel/statistics/ip-tunnel/throughput/ip/historical/bytes
                                        container bytes {
                                            description "Enter the bytes context";

                                            ///nokia-state/state/esa/vm/tunnel/statistics/ip-tunnel/throughput/ip/historical/bytes/encapsulated
                                            leaf encapsulated {
                                                type yang:counter64;
                                                units "megabps";
                                                description "Encapsulated IP tunnel throughput.";
                                            }

                                            ///nokia-state/state/esa/vm/tunnel/statistics/ip-tunnel/throughput/ip/historical/bytes/decapsulated
                                            leaf decapsulated {
                                                type yang:counter64;
                                                units "megabps";
                                                description "Decapsulated IP tunnel throughput.";
                                            }

                                            ///nokia-state/state/esa/vm/tunnel/statistics/ip-tunnel/throughput/ip/historical/bytes/total
                                            leaf total {
                                                type yang:counter64;
                                                units "megabps";
                                                description "Encapsulated and decapsulated IP tunnel throughput.";
                                            }

                                        } // container bytes

                                    } // list historical

                                } // container ip

                                ///nokia-state/state/esa/vm/tunnel/statistics/ip-tunnel/throughput/l2tpv3
                                container l2tpv3 {
                                    description "Enter the l2tpv3 context";

                                    ///nokia-state/state/esa/vm/tunnel/statistics/ip-tunnel/throughput/l2tpv3/current
                                    container current {
                                        description "Enter the current context";

                                        ///nokia-state/state/esa/vm/tunnel/statistics/ip-tunnel/throughput/l2tpv3/current/start-time
                                        leaf start-time {
                                            type yang:date-and-time;
                                            description "The time when the sampling interval started.";
                                        }

                                        ///nokia-state/state/esa/vm/tunnel/statistics/ip-tunnel/throughput/l2tpv3/current/sampling-duration
                                        leaf sampling-duration {
                                            type types-sros:time-duration;
                                            description "The duration of the corresponding sampling interval.";
                                        }

                                        ///nokia-state/state/esa/vm/tunnel/statistics/ip-tunnel/throughput/l2tpv3/current/packets
                                        container packets {
                                            description "Enter the packets context";

                                            ///nokia-state/state/esa/vm/tunnel/statistics/ip-tunnel/throughput/l2tpv3/current/packets/encapsulated
                                            leaf encapsulated {
                                                type yang:counter64;
                                                units "packets per second";
                                                description "Encapsulated L2TPv3 tunnel throughput.";
                                            }

                                            ///nokia-state/state/esa/vm/tunnel/statistics/ip-tunnel/throughput/l2tpv3/current/packets/decapsulated
                                            leaf decapsulated {
                                                type yang:counter64;
                                                units "packets per second";
                                                description "Decapsulated L2TPv3 tunnel throughput.";
                                            }

                                            ///nokia-state/state/esa/vm/tunnel/statistics/ip-tunnel/throughput/l2tpv3/current/packets/total
                                            leaf total {
                                                type yang:counter64;
                                                units "packets per second";
                                                description "Encapsulated and decapsulated L2TPv3 tunnel throughput.";
                                            }

                                        } // container packets

                                        ///nokia-state/state/esa/vm/tunnel/statistics/ip-tunnel/throughput/l2tpv3/current/bytes
                                        container bytes {
                                            description "Enter the bytes context";

                                            ///nokia-state/state/esa/vm/tunnel/statistics/ip-tunnel/throughput/l2tpv3/current/bytes/encapsulated
                                            leaf encapsulated {
                                                type yang:counter64;
                                                units "megabps";
                                                description "Encapsulated L2TPv3 tunnel throughput.";
                                            }

                                            ///nokia-state/state/esa/vm/tunnel/statistics/ip-tunnel/throughput/l2tpv3/current/bytes/decapsulated
                                            leaf decapsulated {
                                                type yang:counter64;
                                                units "megabps";
                                                description "Decapsulated L2TPv3 tunnel throughput.";
                                            }

                                            ///nokia-state/state/esa/vm/tunnel/statistics/ip-tunnel/throughput/l2tpv3/current/bytes/total
                                            leaf total {
                                                type yang:counter64;
                                                units "megabps";
                                                description "Encapsulated and decapsulated L2TPv3 tunnel throughput.";
                                            }

                                        } // container bytes

                                    } // container current

                                    ///nokia-state/state/esa/vm/tunnel/statistics/ip-tunnel/throughput/l2tpv3/historical
                                    list historical {
                                        key "index";
                                        description "Enter the historical list instance";

                                        ///nokia-state/state/esa/vm/tunnel/statistics/ip-tunnel/throughput/l2tpv3/historical/index
                                        leaf index {
                                            type uint32 {
                                                range "2..max";
                                            }
                                            description
                                                "The index of the finished sampling interval period for this statistic.
                                                 It starts with '2' and is ordered by start time of intervals so that
                                                 smaller index indicate more recent intervals.";
                                        }

                                        ///nokia-state/state/esa/vm/tunnel/statistics/ip-tunnel/throughput/l2tpv3/historical/start-time
                                        leaf start-time {
                                            type yang:date-and-time;
                                            description "The time when the sampling interval started.";
                                        }

                                        ///nokia-state/state/esa/vm/tunnel/statistics/ip-tunnel/throughput/l2tpv3/historical/sampling-duration
                                        leaf sampling-duration {
                                            type types-sros:time-duration;
                                            description "The duration of the corresponding sampling interval.";
                                        }

                                        ///nokia-state/state/esa/vm/tunnel/statistics/ip-tunnel/throughput/l2tpv3/historical/packets
                                        container packets {
                                            description "Enter the packets context";

                                            ///nokia-state/state/esa/vm/tunnel/statistics/ip-tunnel/throughput/l2tpv3/historical/packets/encapsulated
                                            leaf encapsulated {
                                                type yang:counter64;
                                                units "packets per second";
                                                description "Encapsulated L2TPv3 tunnel throughput.";
                                            }

                                            ///nokia-state/state/esa/vm/tunnel/statistics/ip-tunnel/throughput/l2tpv3/historical/packets/decapsulated
                                            leaf decapsulated {
                                                type yang:counter64;
                                                units "packets per second";
                                                description "Decapsulated L2TPv3 tunnel throughput.";
                                            }

                                            ///nokia-state/state/esa/vm/tunnel/statistics/ip-tunnel/throughput/l2tpv3/historical/packets/total
                                            leaf total {
                                                type yang:counter64;
                                                units "packets per second";
                                                description "Encapsulated and decapsulated L2TPv3 tunnel throughput.";
                                            }

                                        } // container packets

                                        ///nokia-state/state/esa/vm/tunnel/statistics/ip-tunnel/throughput/l2tpv3/historical/bytes
                                        container bytes {
                                            description "Enter the bytes context";

                                            ///nokia-state/state/esa/vm/tunnel/statistics/ip-tunnel/throughput/l2tpv3/historical/bytes/encapsulated
                                            leaf encapsulated {
                                                type yang:counter64;
                                                units "megabps";
                                                description "Encapsulated L2TPv3 tunnel throughput.";
                                            }

                                            ///nokia-state/state/esa/vm/tunnel/statistics/ip-tunnel/throughput/l2tpv3/historical/bytes/decapsulated
                                            leaf decapsulated {
                                                type yang:counter64;
                                                units "megabps";
                                                description "Decapsulated L2TPv3 tunnel throughput.";
                                            }

                                            ///nokia-state/state/esa/vm/tunnel/statistics/ip-tunnel/throughput/l2tpv3/historical/bytes/total
                                            leaf total {
                                                type yang:counter64;
                                                units "megabps";
                                                description "Encapsulated and decapsulated L2TPv3 tunnel throughput.";
                                            }

                                        } // container bytes

                                    } // list historical

                                } // container l2tpv3

                            } // container throughput

                            ///nokia-state/state/esa/vm/tunnel/statistics/ip-tunnel/traffic-forward
                            container traffic-forward {
                                description "Enter the traffic-forward context";

                                ///nokia-state/state/esa/vm/tunnel/statistics/ip-tunnel/traffic-forward/gre
                                container gre {
                                    description "Enter the gre context";

                                    ///nokia-state/state/esa/vm/tunnel/statistics/ip-tunnel/traffic-forward/gre/current
                                    container current {
                                        description "Enter the current context";

                                        ///nokia-state/state/esa/vm/tunnel/statistics/ip-tunnel/traffic-forward/gre/current/start-time
                                        leaf start-time {
                                            type yang:date-and-time;
                                            description "The time when the sampling interval started.";
                                        }

                                        ///nokia-state/state/esa/vm/tunnel/statistics/ip-tunnel/traffic-forward/gre/current/sampling-duration
                                        leaf sampling-duration {
                                            type types-sros:time-duration;
                                            description "The duration of the corresponding sampling interval.";
                                        }

                                        ///nokia-state/state/esa/vm/tunnel/statistics/ip-tunnel/traffic-forward/gre/current/packets
                                        container packets {
                                            description "Enter the packets context";

                                            ///nokia-state/state/esa/vm/tunnel/statistics/ip-tunnel/traffic-forward/gre/current/packets/encapsulated
                                            leaf encapsulated {
                                                type yang:counter64;
                                                units "packets";
                                                description "Number of encaped GRE tunnel packets.";
                                            }

                                            ///nokia-state/state/esa/vm/tunnel/statistics/ip-tunnel/traffic-forward/gre/current/packets/decapsulated
                                            leaf decapsulated {
                                                type yang:counter64;
                                                units "packets";
                                                description "Number of decaped GRE tunnel packets.";
                                            }

                                            ///nokia-state/state/esa/vm/tunnel/statistics/ip-tunnel/traffic-forward/gre/current/packets/total
                                            leaf total {
                                                type yang:counter64;
                                                units "packets";
                                                description "Number of encaped and decaped GRE tunnel packets.";
                                            }

                                        } // container packets

                                        ///nokia-state/state/esa/vm/tunnel/statistics/ip-tunnel/traffic-forward/gre/current/bytes
                                        container bytes {
                                            description "Enter the bytes context";

                                            ///nokia-state/state/esa/vm/tunnel/statistics/ip-tunnel/traffic-forward/gre/current/bytes/encapsulated
                                            leaf encapsulated {
                                                type yang:counter64;
                                                units "kilobytes";
                                                description "Number of kilobytes in the encaped GRE tunnel packets.";
                                            }

                                            ///nokia-state/state/esa/vm/tunnel/statistics/ip-tunnel/traffic-forward/gre/current/bytes/decapsulated
                                            leaf decapsulated {
                                                type yang:counter64;
                                                units "kilobytes";
                                                description "Number of kilobytes in the decaped GRE tunnel packets.";
                                            }

                                            ///nokia-state/state/esa/vm/tunnel/statistics/ip-tunnel/traffic-forward/gre/current/bytes/total
                                            leaf total {
                                                type yang:counter64;
                                                units "kilobytes";
                                                description "Number of kilobytes in the encaped and decaped GRE tunnel packets.";
                                            }

                                        } // container bytes

                                    } // container current

                                } // container gre

                                ///nokia-state/state/esa/vm/tunnel/statistics/ip-tunnel/traffic-forward/ip
                                container ip {
                                    description "Enter the ip context";

                                    ///nokia-state/state/esa/vm/tunnel/statistics/ip-tunnel/traffic-forward/ip/current
                                    container current {
                                        description "Enter the current context";

                                        ///nokia-state/state/esa/vm/tunnel/statistics/ip-tunnel/traffic-forward/ip/current/start-time
                                        leaf start-time {
                                            type yang:date-and-time;
                                            description "The time when the sampling interval started.";
                                        }

                                        ///nokia-state/state/esa/vm/tunnel/statistics/ip-tunnel/traffic-forward/ip/current/sampling-duration
                                        leaf sampling-duration {
                                            type types-sros:time-duration;
                                            description "The duration of the corresponding sampling interval.";
                                        }

                                        ///nokia-state/state/esa/vm/tunnel/statistics/ip-tunnel/traffic-forward/ip/current/packets
                                        container packets {
                                            description "Enter the packets context";

                                            ///nokia-state/state/esa/vm/tunnel/statistics/ip-tunnel/traffic-forward/ip/current/packets/encapsulated
                                            leaf encapsulated {
                                                type yang:counter64;
                                                units "packets";
                                                description "Number of encaped IP tunnel packets.";
                                            }

                                            ///nokia-state/state/esa/vm/tunnel/statistics/ip-tunnel/traffic-forward/ip/current/packets/decapsulated
                                            leaf decapsulated {
                                                type yang:counter64;
                                                units "packets";
                                                description "Number of decaped IP tunnel packets.";
                                            }

                                            ///nokia-state/state/esa/vm/tunnel/statistics/ip-tunnel/traffic-forward/ip/current/packets/total
                                            leaf total {
                                                type yang:counter64;
                                                units "packets";
                                                description "Number of encaped and decaped IP tunnel packets.";
                                            }

                                        } // container packets

                                        ///nokia-state/state/esa/vm/tunnel/statistics/ip-tunnel/traffic-forward/ip/current/bytes
                                        container bytes {
                                            description "Enter the bytes context";

                                            ///nokia-state/state/esa/vm/tunnel/statistics/ip-tunnel/traffic-forward/ip/current/bytes/encapsulated
                                            leaf encapsulated {
                                                type yang:counter64;
                                                units "kilobytes";
                                                description "Number of kilobytes in the encaped IP tunnel packets.";
                                            }

                                            ///nokia-state/state/esa/vm/tunnel/statistics/ip-tunnel/traffic-forward/ip/current/bytes/decapsulated
                                            leaf decapsulated {
                                                type yang:counter64;
                                                units "kilobytes";
                                                description "Number of kilobytes in the decaped IP tunnel packets.";
                                            }

                                            ///nokia-state/state/esa/vm/tunnel/statistics/ip-tunnel/traffic-forward/ip/current/bytes/total
                                            leaf total {
                                                type yang:counter64;
                                                units "kilobytes";
                                                description "Number of kilobytes in the encaped and decaped IP tunnel packets.";
                                            }

                                        } // container bytes

                                    } // container current

                                } // container ip

                                ///nokia-state/state/esa/vm/tunnel/statistics/ip-tunnel/traffic-forward/l2tpv3
                                container l2tpv3 {
                                    description "Enter the l2tpv3 context";

                                    ///nokia-state/state/esa/vm/tunnel/statistics/ip-tunnel/traffic-forward/l2tpv3/current
                                    container current {
                                        description "Enter the current context";

                                        ///nokia-state/state/esa/vm/tunnel/statistics/ip-tunnel/traffic-forward/l2tpv3/current/start-time
                                        leaf start-time {
                                            type yang:date-and-time;
                                            description "The time when the sampling interval started.";
                                        }

                                        ///nokia-state/state/esa/vm/tunnel/statistics/ip-tunnel/traffic-forward/l2tpv3/current/sampling-duration
                                        leaf sampling-duration {
                                            type types-sros:time-duration;
                                            description "The duration of the corresponding sampling interval.";
                                        }

                                        ///nokia-state/state/esa/vm/tunnel/statistics/ip-tunnel/traffic-forward/l2tpv3/current/packets
                                        container packets {
                                            description "Enter the packets context";

                                            ///nokia-state/state/esa/vm/tunnel/statistics/ip-tunnel/traffic-forward/l2tpv3/current/packets/encapsulated
                                            leaf encapsulated {
                                                type yang:counter64;
                                                units "packets";
                                                description "Number of encaped L2TPv3 tunnel packets.";
                                            }

                                            ///nokia-state/state/esa/vm/tunnel/statistics/ip-tunnel/traffic-forward/l2tpv3/current/packets/decapsulated
                                            leaf decapsulated {
                                                type yang:counter64;
                                                units "packets";
                                                description "Number of decaped L2TPv3 tunnel packets.";
                                            }

                                            ///nokia-state/state/esa/vm/tunnel/statistics/ip-tunnel/traffic-forward/l2tpv3/current/packets/total
                                            leaf total {
                                                type yang:counter64;
                                                units "packets";
                                                description "Number of encaped and decaped L2TPv3 tunnel packets.";
                                            }

                                        } // container packets

                                        ///nokia-state/state/esa/vm/tunnel/statistics/ip-tunnel/traffic-forward/l2tpv3/current/bytes
                                        container bytes {
                                            description "Enter the bytes context";

                                            ///nokia-state/state/esa/vm/tunnel/statistics/ip-tunnel/traffic-forward/l2tpv3/current/bytes/encapsulated
                                            leaf encapsulated {
                                                type yang:counter64;
                                                units "kilobytes";
                                                description "Number of kilobytes in the encaped L2TPv3 tunnel packets.";
                                            }

                                            ///nokia-state/state/esa/vm/tunnel/statistics/ip-tunnel/traffic-forward/l2tpv3/current/bytes/decapsulated
                                            leaf decapsulated {
                                                type yang:counter64;
                                                units "kilobytes";
                                                description "Number of kilobytes in the decaped L2TPv3 tunnel packets.";
                                            }

                                            ///nokia-state/state/esa/vm/tunnel/statistics/ip-tunnel/traffic-forward/l2tpv3/current/bytes/total
                                            leaf total {
                                                type yang:counter64;
                                                units "kilobytes";
                                                description "Number of kilobytes in the encaped and decaped L2TPv3 tunnel packets.";
                                            }

                                        } // container bytes

                                    } // container current

                                } // container l2tpv3

                            } // container traffic-forward

                        } // container ip-tunnel

                        ///nokia-state/state/esa/vm/tunnel/statistics/ipsec
                        container ipsec {
                            description "Enter the ipsec context";

                            ///nokia-state/state/esa/vm/tunnel/statistics/ipsec/number-of-tunnels
                            container number-of-tunnels {
                                description "Enter the number-of-tunnels context";

                                ///nokia-state/state/esa/vm/tunnel/statistics/ipsec/number-of-tunnels/current
                                container current {
                                    description "Enter the current context";

                                    ///nokia-state/state/esa/vm/tunnel/statistics/ipsec/number-of-tunnels/current/static-lan-to-lan
                                    leaf static-lan-to-lan {
                                        type yang:counter64;
                                        description "Number of IPsec static LAN-to-LAN (SL2L) tunnels.";
                                    }

                                    ///nokia-state/state/esa/vm/tunnel/statistics/ipsec/number-of-tunnels/current/dynamic-lan-to-lan
                                    leaf dynamic-lan-to-lan {
                                        type yang:counter64;
                                        description "Number of IPsec dynamic LAN-to-LAN (DL2L) tunnels.";
                                    }

                                    ///nokia-state/state/esa/vm/tunnel/statistics/ipsec/number-of-tunnels/current/remote-access
                                    leaf remote-access {
                                        type yang:counter64;
                                        description "Number of IPsec remote access (RA) tunnels.";
                                    }

                                    ///nokia-state/state/esa/vm/tunnel/statistics/ipsec/number-of-tunnels/current/total
                                    leaf total {
                                        type yang:counter64;
                                        description "Total number of IPsec tunnels.";
                                    }

                                    ///nokia-state/state/esa/vm/tunnel/statistics/ipsec/number-of-tunnels/current/start-time
                                    leaf start-time {
                                        type yang:date-and-time;
                                        description "The time when the sampling interval started.";
                                    }

                                } // container current

                                ///nokia-state/state/esa/vm/tunnel/statistics/ipsec/number-of-tunnels/historical
                                list historical {
                                    key "index";
                                    description "Enter the historical list instance";

                                    ///nokia-state/state/esa/vm/tunnel/statistics/ipsec/number-of-tunnels/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/ipsec/number-of-tunnels/historical/static-lan-to-lan
                                    leaf static-lan-to-lan {
                                        type yang:counter64;
                                        description "Number of IPsec static LAN-to-LAN (SL2L) tunnels.";
                                    }

                                    ///nokia-state/state/esa/vm/tunnel/statistics/ipsec/number-of-tunnels/historical/dynamic-lan-to-lan
                                    leaf dynamic-lan-to-lan {
                                        type yang:counter64;
                                        description "Number of IPsec dynamic LAN-to-LAN (DL2L) tunnels.";
                                    }

                                    ///nokia-state/state/esa/vm/tunnel/statistics/ipsec/number-of-tunnels/historical/remote-access
                                    leaf remote-access {
                                        type yang:counter64;
                                        description "Number of IPsec remote access (RA) tunnels.";
                                    }

                                    ///nokia-state/state/esa/vm/tunnel/statistics/ipsec/number-of-tunnels/historical/total
                                    leaf total {
                                        type yang:counter64;
                                        description "Total number of IPsec tunnels.";
                                    }

                                    ///nokia-state/state/esa/vm/tunnel/statistics/ipsec/number-of-tunnels/historical/start-time
                                    leaf start-time {
                                        type yang:date-and-time;
                                        description "The time when the sampling interval started.";
                                    }

                                } // list historical

                            } // container number-of-tunnels

                            ///nokia-state/state/esa/vm/tunnel/statistics/ipsec/throughput
                            container throughput {
                                description "Enter the throughput context";

                                ///nokia-state/state/esa/vm/tunnel/statistics/ipsec/throughput/current
                                container current {
                                    description "Enter the current context";

                                    ///nokia-state/state/esa/vm/tunnel/statistics/ipsec/throughput/current/start-time
                                    leaf start-time {
                                        type yang:date-and-time;
                                        description "The time when the sampling interval started.";
                                    }

                                    ///nokia-state/state/esa/vm/tunnel/statistics/ipsec/throughput/current/sampling-duration
                                    leaf sampling-duration {
                                        type types-sros:time-duration;
                                        description "The duration of the corresponding sampling interval.";
                                    }

                                    ///nokia-state/state/esa/vm/tunnel/statistics/ipsec/throughput/current/packets
                                    container packets {
                                        description "Enter the packets context";

                                        ///nokia-state/state/esa/vm/tunnel/statistics/ipsec/throughput/current/packets/encrypted
                                        leaf encrypted {
                                            type yang:counter64;
                                            units "packets per second";
                                            description "Encrypted IPsec traffic throughput.";
                                        }

                                        ///nokia-state/state/esa/vm/tunnel/statistics/ipsec/throughput/current/packets/decrypted
                                        leaf decrypted {
                                            type yang:counter64;
                                            units "packets per second";
                                            description "Decrypted IPsec traffic throughput.";
                                        }

                                        ///nokia-state/state/esa/vm/tunnel/statistics/ipsec/throughput/current/packets/total
                                        leaf total {
                                            type yang:counter64;
                                            units "packets per second";
                                            description "Encrypted and decrypted IPsec traffic throughput.";
                                        }

                                    } // container packets

                                    ///nokia-state/state/esa/vm/tunnel/statistics/ipsec/throughput/current/bytes
                                    container bytes {
                                        description "Enter the bytes context";

                                        ///nokia-state/state/esa/vm/tunnel/statistics/ipsec/throughput/current/bytes/encrypted
                                        leaf encrypted {
                                            type yang:counter64;
                                            units "megabps";
                                            description "Encrypted IPsec traffic throughput.";
                                        }

                                        ///nokia-state/state/esa/vm/tunnel/statistics/ipsec/throughput/current/bytes/decrypted
                                        leaf decrypted {
                                            type yang:counter64;
                                            units "megabps";
                                            description "Decrypted IPsec traffic throughput.";
                                        }

                                        ///nokia-state/state/esa/vm/tunnel/statistics/ipsec/throughput/current/bytes/total
                                        leaf total {
                                            type yang:counter64;
                                            units "megabps";
                                            description "Encrypted and decrypted IPsec traffic throughput.";
                                        }

                                    } // container bytes

                                } // container current

                                ///nokia-state/state/esa/vm/tunnel/statistics/ipsec/throughput/historical
                                list historical {
                                    key "index";
                                    description "Enter the historical list instance";

                                    ///nokia-state/state/esa/vm/tunnel/statistics/ipsec/throughput/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/ipsec/throughput/historical/start-time
                                    leaf start-time {
                                        type yang:date-and-time;
                                        description "The time when the sampling interval started.";
                                    }

                                    ///nokia-state/state/esa/vm/tunnel/statistics/ipsec/throughput/historical/sampling-duration
                                    leaf sampling-duration {
                                        type types-sros:time-duration;
                                        description "The duration of the corresponding sampling interval.";
                                    }

                                    ///nokia-state/state/esa/vm/tunnel/statistics/ipsec/throughput/historical/packets
                                    container packets {
                                        description "Enter the packets context";

                                        ///nokia-state/state/esa/vm/tunnel/statistics/ipsec/throughput/historical/packets/encrypted
                                        leaf encrypted {
                                            type yang:counter64;
                                            units "packets per second";
                                            description "Encrypted IPsec traffic throughput.";
                                        }

                                        ///nokia-state/state/esa/vm/tunnel/statistics/ipsec/throughput/historical/packets/decrypted
                                        leaf decrypted {
                                            type yang:counter64;
                                            units "packets per second";
                                            description "Decrypted IPsec traffic throughput.";
                                        }

                                        ///nokia-state/state/esa/vm/tunnel/statistics/ipsec/throughput/historical/packets/total
                                        leaf total {
                                            type yang:counter64;
                                            units "packets per second";
                                            description "Encrypted and decrypted IPsec traffic throughput.";
                                        }

                                    } // container packets

                                    ///nokia-state/state/esa/vm/tunnel/statistics/ipsec/throughput/historical/bytes
                                    container bytes {
                                        description "Enter the bytes context";

                                        ///nokia-state/state/esa/vm/tunnel/statistics/ipsec/throughput/historical/bytes/encrypted
                                        leaf encrypted {
                                            type yang:counter64;
                                            units "megabps";
                                            description "Encrypted IPsec traffic throughput.";
                                        }

                                        ///nokia-state/state/esa/vm/tunnel/statistics/ipsec/throughput/historical/bytes/decrypted
                                        leaf decrypted {
                                            type yang:counter64;
                                            units "megabps";
                                            description "Decrypted IPsec traffic throughput.";
                                        }

                                        ///nokia-state/state/esa/vm/tunnel/statistics/ipsec/throughput/historical/bytes/total
                                        leaf total {
                                            type yang:counter64;
                                            units "megabps";
                                            description "Encrypted and decrypted IPsec traffic throughput.";
                                        }

                                    } // container bytes

                                } // list historical

                            } // container throughput

                            ///nokia-state/state/esa/vm/tunnel/statistics/ipsec/tunnel-setup-rate
                            container tunnel-setup-rate {
                                description "Enter the tunnel-setup-rate context";

                                ///nokia-state/state/esa/vm/tunnel/statistics/ipsec/tunnel-setup-rate/current
                                container current {
                                    description "Enter the current context";

                                    ///nokia-state/state/esa/vm/tunnel/statistics/ipsec/tunnel-setup-rate/current/static-lan-to-lan
                                    leaf static-lan-to-lan {
                                        type decimal64 {
                                            fraction-digits 2;
                                        }
                                        units "tunnels per second";
                                        description "Static LAN-to-LAN (SL2L) tunnel setup rate.";
                                    }

                                    ///nokia-state/state/esa/vm/tunnel/statistics/ipsec/tunnel-setup-rate/current/total
                                    leaf total {
                                        type decimal64 {
                                            fraction-digits 2;
                                        }
                                        units "tunnels per second";
                                        description "Total IPsec tunnel setup rate.";
                                    }

                                    ///nokia-state/state/esa/vm/tunnel/statistics/ipsec/tunnel-setup-rate/current/dynamic-lan-to-lan
                                    leaf dynamic-lan-to-lan {
                                        type decimal64 {
                                            fraction-digits 2;
                                        }
                                        units "tunnels per second";
                                        description "Dynamic LAN-to-LAN (DL2L) tunnel setup rate.";
                                    }

                                    ///nokia-state/state/esa/vm/tunnel/statistics/ipsec/tunnel-setup-rate/current/remote-access
                                    leaf remote-access {
                                        type decimal64 {
                                            fraction-digits 2;
                                        }
                                        units "tunnels per second";
                                        description "Remote access (RA) tunnel setup rate.";
                                    }

                                    ///nokia-state/state/esa/vm/tunnel/statistics/ipsec/tunnel-setup-rate/current/start-time
                                    leaf start-time {
                                        type yang:date-and-time;
                                        description "The time when the sampling interval started.";
                                    }

                                    ///nokia-state/state/esa/vm/tunnel/statistics/ipsec/tunnel-setup-rate/current/sampling-duration
                                    leaf sampling-duration {
                                        type types-sros:time-duration;
                                        description "The duration of the corresponding sampling interval.";
                                    }

                                } // container current

                                ///nokia-state/state/esa/vm/tunnel/statistics/ipsec/tunnel-setup-rate/historical
                                list historical {
                                    key "index";
                                    description "Enter the historical list instance";

                                    ///nokia-state/state/esa/vm/tunnel/statistics/ipsec/tunnel-setup-rate/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/ipsec/tunnel-setup-rate/historical/static-lan-to-lan
                                    leaf static-lan-to-lan {
                                        type decimal64 {
                                            fraction-digits 2;
                                        }
                                        units "tunnels per second";
                                        description "Static LAN-to-LAN (SL2L) tunnel setup rate.";
                                    }

                                    ///nokia-state/state/esa/vm/tunnel/statistics/ipsec/tunnel-setup-rate/historical/total
                                    leaf total {
                                        type decimal64 {
                                            fraction-digits 2;
                                        }
                                        units "tunnels per second";
                                        description "Total IPsec tunnel setup rate.";
                                    }

                                    ///nokia-state/state/esa/vm/tunnel/statistics/ipsec/tunnel-setup-rate/historical/dynamic-lan-to-lan
                                    leaf dynamic-lan-to-lan {
                                        type decimal64 {
                                            fraction-digits 2;
                                        }
                                        units "tunnels per second";
                                        description "Dynamic LAN-to-LAN (DL2L) tunnel setup rate.";
                                    }

                                    ///nokia-state/state/esa/vm/tunnel/statistics/ipsec/tunnel-setup-rate/historical/remote-access
                                    leaf remote-access {
                                        type decimal64 {
                                            fraction-digits 2;
                                        }
                                        units "tunnels per second";
                                        description "Remote access (RA) tunnel setup rate.";
                                    }

                                    ///nokia-state/state/esa/vm/tunnel/statistics/ipsec/tunnel-setup-rate/historical/start-time
                                    leaf start-time {
                                        type yang:date-and-time;
                                        description "The time when the sampling interval started.";
                                    }

                                    ///nokia-state/state/esa/vm/tunnel/statistics/ipsec/tunnel-setup-rate/historical/sampling-duration
                                    leaf sampling-duration {
                                        type types-sros:time-duration;
                                        description "The duration of the corresponding sampling interval.";
                                    }

                                } // list historical

                            } // container tunnel-setup-rate

                            ///nokia-state/state/esa/vm/tunnel/statistics/ipsec/traffic-forward
                            container traffic-forward {
                                description "Enter the traffic-forward context";

                                ///nokia-state/state/esa/vm/tunnel/statistics/ipsec/traffic-forward/current
                                container current {
                                    description "Enter the current context";

                                    ///nokia-state/state/esa/vm/tunnel/statistics/ipsec/traffic-forward/current/start-time
                                    leaf start-time {
                                        type yang:date-and-time;
                                        description "The time when the sampling interval started.";
                                    }

                                    ///nokia-state/state/esa/vm/tunnel/statistics/ipsec/traffic-forward/current/sampling-duration
                                    leaf sampling-duration {
                                        type types-sros:time-duration;
                                        description "The duration of the corresponding sampling interval.";
                                    }

                                    ///nokia-state/state/esa/vm/tunnel/statistics/ipsec/traffic-forward/current/packets
                                    container packets {
                                        description "Enter the packets context";

                                        ///nokia-state/state/esa/vm/tunnel/statistics/ipsec/traffic-forward/current/packets/encrypted
                                        leaf encrypted {
                                            type yang:counter64;
                                            units "packets";
                                            description "Number of encrypted IPsec packets.";
                                        }

                                        ///nokia-state/state/esa/vm/tunnel/statistics/ipsec/traffic-forward/current/packets/decrypted
                                        leaf decrypted {
                                            type yang:counter64;
                                            units "packets";
                                            description "Number of decrypted IPsec packets.";
                                        }

                                        ///nokia-state/state/esa/vm/tunnel/statistics/ipsec/traffic-forward/current/packets/total
                                        leaf total {
                                            type yang:counter64;
                                            units "packets";
                                            description "Number of encrypted and decrypted IPsec packets.";
                                        }

                                    } // container packets

                                    ///nokia-state/state/esa/vm/tunnel/statistics/ipsec/traffic-forward/current/bytes
                                    container bytes {
                                        description "Enter the bytes context";

                                        ///nokia-state/state/esa/vm/tunnel/statistics/ipsec/traffic-forward/current/bytes/encrypted
                                        leaf encrypted {
                                            type yang:counter64;
                                            units "kilobytes";
                                            description "Number of kilobytes in the encrypted IPsec packets.";
                                        }

                                        ///nokia-state/state/esa/vm/tunnel/statistics/ipsec/traffic-forward/current/bytes/decrypted
                                        leaf decrypted {
                                            type yang:counter64;
                                            units "kilobytes";
                                            description "Number of kilobytes in the decrypted IPsec packets.";
                                        }

                                        ///nokia-state/state/esa/vm/tunnel/statistics/ipsec/traffic-forward/current/bytes/total
                                        leaf total {
                                            type yang:counter64;
                                            units "kilobytes";
                                            description "Number of kilobytes in the encrypted and decrypted IPsec packets.";
                                        }

                                    } // container bytes

                                } // container current

                            } // container traffic-forward

                            ///nokia-state/state/esa/vm/tunnel/statistics/ipsec/ike-exchange-failure-rate
                            container ike-exchange-failure-rate {
                                description "Enter the ike-exchange-failure-rate context";

                                ///nokia-state/state/esa/vm/tunnel/statistics/ipsec/ike-exchange-failure-rate/current
                                container current {
                                    description "Enter the current context";

                                    ///nokia-state/state/esa/vm/tunnel/statistics/ipsec/ike-exchange-failure-rate/current/start-time
                                    leaf start-time {
                                        type yang:date-and-time;
                                        description "The time when the sampling interval started.";
                                    }

                                    ///nokia-state/state/esa/vm/tunnel/statistics/ipsec/ike-exchange-failure-rate/current/sampling-duration
                                    leaf sampling-duration {
                                        type types-sros:time-duration;
                                        description "The duration of the corresponding sampling interval.";
                                    }

                                    ///nokia-state/state/esa/vm/tunnel/statistics/ipsec/ike-exchange-failure-rate/current/auth-failure
                                    container auth-failure {
                                        description "Enter the auth-failure context";

                                        ///nokia-state/state/esa/vm/tunnel/statistics/ipsec/ike-exchange-failure-rate/current/auth-failure/count
                                        leaf count {
                                            type decimal64 {
                                                fraction-digits 2;
                                            }
                                            units "failures per second";
                                            description "IKE exchange failure rate - authentication.";
                                        }

                                        ///nokia-state/state/esa/vm/tunnel/statistics/ipsec/ike-exchange-failure-rate/current/auth-failure/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/auth-failure/first-failure-description
                                        leaf first-failure-description {
                                            type types-sros:long-description;
                                            description "The description of the place where the first IKE exchange failure happened.";
                                        }

                                        ///nokia-state/state/esa/vm/tunnel/statistics/ipsec/ike-exchange-failure-rate/current/auth-failure/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/auth-failure/last-failure-description
                                        leaf last-failure-description {
                                            type types-sros:long-description;
                                            description "The description of the place where the last IKE exchange failure happened.";
                                        }

                                    } // container auth-failure

                                    ///nokia-state/state/esa/vm/tunnel/statistics/ipsec/ike-exchange-failure-rate/current/non-proposal-chosen
                                    container non-proposal-chosen {
                                        description "Enter the non-proposal-chosen context";

                                        ///nokia-state/state/esa/vm/tunnel/statistics/ipsec/ike-exchange-failure-rate/current/non-proposal-chosen/count
                                        leaf count {
                                            type decimal64 {
                                                fraction-digits 2;
                                            }
                                            units "failures per second";
                                            description "IKE exchange failure rate - non-proposal chosen.";
                                        }

                                        ///nokia-state/state/esa/vm/tunnel/statistics/ipsec/ike-exchange-failure-rate/current/non-proposal-chosen/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/non-proposal-chosen/first-failure-description
                                        leaf first-failure-description {
                                            type types-sros:long-description;
                                            description "The description of the place where the first IKE exchange failure happened.";
                                        }

                                        ///nokia-state/state/esa/vm/tunnel/statistics/ipsec/ike-exchange-failure-rate/current/non-proposal-chosen/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/non-proposal-chosen/last-failure-description
                                        leaf last-failure-description {
                                            type types-sros:long-description;
                                            description "The description of the place where the last IKE exchange failure happened.";
                                        }

                                    } // container non-proposal-chosen

                                    ///nokia-state/state/esa/vm/tunnel/statistics/ipsec/ike-exchange-failure-rate/current/internal-address-assignment
                                    container internal-address-assignment {
                                        description "Enter the internal-address-assignment context";

                                        ///nokia-state/state/esa/vm/tunnel/statistics/ipsec/ike-exchange-failure-rate/current/internal-address-assignment/count
                                        leaf count {
                                            type decimal64 {
                                                fraction-digits 2;
                                            }
                                            units "failures per second";
                                            description "IKE exchange failure rate - address assignment.";
                                        }

                                        ///nokia-state/state/esa/vm/tunnel/statistics/ipsec/ike-exchange-failure-rate/current/internal-address-assignment/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/internal-address-assignment/first-failure-description
                                        leaf first-failure-description {
                                            type types-sros:long-description;
                                            description "The description of the place where the first IKE exchange failure happened.";
                                        }

                                        ///nokia-state/state/esa/vm/tunnel/statistics/ipsec/ike-exchange-failure-rate/current/internal-address-assignment/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/internal-address-assignment/last-failure-description
                                        leaf last-failure-description {
                                            type types-sros:long-description;
                                            description "The description of the place where the last IKE exchange failure happened.";
                                        }

                                    } // container internal-address-assignment

                                    ///nokia-state/state/esa/vm/tunnel/statistics/ipsec/ike-exchange-failure-rate/current/invalid-ts
                                    container invalid-ts {
                                        description "Enter the invalid-ts context";

                                        ///nokia-state/state/esa/vm/tunnel/statistics/ipsec/ike-exchange-failure-rate/current/invalid-ts/count
                                        leaf count {
                                            type decimal64 {
                                                fraction-digits 2;
                                            }
                                            units "failures per second";
                                            description "IKE exchange failure rate - invalid traffic selector.";
                                        }

                                        ///nokia-state/state/esa/vm/tunnel/statistics/ipsec/ike-exchange-failure-rate/current/invalid-ts/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/invalid-ts/first-failure-description
                                        leaf first-failure-description {
                                            type types-sros:long-description;
                                            description "The description of the place where the first IKE exchange failure happened.";
                                        }

                                        ///nokia-state/state/esa/vm/tunnel/statistics/ipsec/ike-exchange-failure-rate/current/invalid-ts/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/invalid-ts/last-failure-description
                                        leaf last-failure-description {
                                            type types-sros:long-description;
                                            description "The description of the place where the last IKE exchange failure happened.";
                                        }

                                    } // container invalid-ts

                                    ///nokia-state/state/esa/vm/tunnel/statistics/ipsec/ike-exchange-failure-rate/current/invalid-ke
                                    container invalid-ke {
                                        description "Enter the invalid-ke context";

                                        ///nokia-state/state/esa/vm/tunnel/statistics/ipsec/ike-exchange-failure-rate/current/invalid-ke/count
                                        leaf count {
                                            type decimal64 {
                                                fraction-digits 2;
                                            }
                                            units "failures per second";
                                            description "IKE exchange failure rate - invalid key exchange.";
                                        }

                                        ///nokia-state/state/esa/vm/tunnel/statistics/ipsec/ike-exchange-failure-rate/current/invalid-ke/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/invalid-ke/first-failure-description
                                        leaf first-failure-description {
                                            type types-sros:long-description;
                                            description "The description of the place where the first IKE exchange failure happened.";
                                        }

                                        ///nokia-state/state/esa/vm/tunnel/statistics/ipsec/ike-exchange-failure-rate/current/invalid-ke/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/invalid-ke/last-failure-description
                                        leaf last-failure-description {
                                            type types-sros:long-description;
                                            description "The description of the place where the last IKE exchange failure happened.";
                                        }

                                    } // container invalid-ke

                                    ///nokia-state/state/esa/vm/tunnel/statistics/ipsec/ike-exchange-failure-rate/current/dpd-timeout
                                    container dpd-timeout {
                                        description "Enter the dpd-timeout context";

                                        ///nokia-state/state/esa/vm/tunnel/statistics/ipsec/ike-exchange-failure-rate/current/dpd-timeout/count
                                        leaf count {
                                            type decimal64 {
                                                fraction-digits 2;
                                            }
                                            units "failures per second";
                                            description "IKE exchange failure rate - DPD timeout.";
                                        }

                                        ///nokia-state/state/esa/vm/tunnel/statistics/ipsec/ike-exchange-failure-rate/current/dpd-timeout/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/dpd-timeout/first-failure-description
                                        leaf first-failure-description {
                                            type types-sros:long-description;
                                            description "The description of the place where the first IKE exchange failure happened.";
                                        }

                                        ///nokia-state/state/esa/vm/tunnel/statistics/ipsec/ike-exchange-failure-rate/current/dpd-timeout/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/dpd-timeout/last-failure-description
                                        leaf last-failure-description {
                                            type types-sros:long-description;
                                            description "The description of the place where the last IKE exchange failure happened.";
                                        }

                                    } // container dpd-timeout

                                    ///nokia-state/state/esa/vm/tunnel/statistics/ipsec/ike-exchange-failure-rate/current/other
                                    container other {
                                        description "Enter the other context";

                                        ///nokia-state/state/esa/vm/tunnel/statistics/ipsec/ike-exchange-failure-rate/current/other/count
                                        leaf count {
                                            type decimal64 {
                                                fraction-digits 2;
                                            }
                                            units "failures per second";
                                            description "IKE exchange failure rate - other failure reasons.";
                                        }

                                        ///nokia-state/state/esa/vm/tunnel/statistics/ipsec/ike-exchange-failure-rate/current/other/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/current/other/first-failure-description
                                        leaf first-failure-description {
                                            type types-sros:long-description;
                                            description "The description of the place where the first IKE exchange failure happened.";
                                        }

                                        ///nokia-state/state/esa/vm/tunnel/statistics/ipsec/ike-exchange-failure-rate/current/other/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/current/other/last-failure-description
                                        leaf last-failure-description {
                                            type types-sros:long-description;
                                            description "The description of the place where the last IKE exchange failure happened.";
                                        }

                                    } // container other

                                } // container current

                                ///nokia-state/state/esa/vm/tunnel/statistics/ipsec/ike-exchange-failure-rate/historical
                                list historical {
                                    key "index";
                                    description "Enter the historical list instance";

                                    ///nokia-state/state/esa/vm/tunnel/statistics/ipsec/ike-exchange-failure-rate/historical/index
                                    leaf index {
                                        type uint32 {
                                            range "2..max";
                                        }
                                        description
                                            "The index of the finished sampling interval period for this statistic.
                                             It starts with '2' and is ordered by start time of intervals so that
                                             smaller index indicate more recent intervals.";
                                    }

                                    ///nokia-state/state/esa/vm/tunnel/statistics/ipsec/ike-exchange-failure-rate/historical/start-time
                                    leaf start-time {
                                        type yang:date-and-time;
                                        description "The time when the sampling interval started.";
                                    }

                                    ///nokia-state/state/esa/vm/tunnel/statistics/ipsec/ike-exchange-failure-rate/historical/sampling-duration
                                    leaf sampling-duration {
                                        type types-sros:time-duration;
                                        description "The duration of the corresponding sampling interval.";
                                    }

                                    ///nokia-state/state/esa/vm/tunnel/statistics/ipsec/ike-exchange-failure-rate/historical/auth-failure
                                    container auth-failure {
                                        description "Enter the auth-failure context";

                                        ///nokia-state/state/esa/vm/tunnel/statistics/ipsec/ike-exchange-failure-rate/historical/auth-failure/count
                                        leaf count {
                                            type decimal64 {
                                                fraction-digits 2;
                                            }
                                            units "failures per second";
                                            description "IKE exchange failure rate - authentication.";
                                        }

                                        ///nokia-state/state/esa/vm/tunnel/statistics/ipsec/ike-exchange-failure-rate/historical/auth-failure/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/auth-failure/first-failure-description
                                        leaf first-failure-description {
                                            type types-sros:long-description;
                                            description "The description of the place where the first IKE exchange failure happened.";
                                        }

                                        ///nokia-state/state/esa/vm/tunnel/statistics/ipsec/ike-exchange-failure-rate/historical/auth-failure/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/auth-failure/last-failure-description
                                        leaf last-failure-description {
                                            type types-sros:long-description;
                                            description "The description of the place where the last IKE exchange failure happened.";
                                        }

                                    } // container auth-failure

                                    ///nokia-state/state/esa/vm/tunnel/statistics/ipsec/ike-exchange-failure-rate/historical/non-proposal-chosen
                                    container non-proposal-chosen {
                                        description "Enter the non-proposal-chosen context";

                                        ///nokia-state/state/esa/vm/tunnel/statistics/ipsec/ike-exchange-failure-rate/historical/non-proposal-chosen/count
                                        leaf count {
                                            type decimal64 {
                                                fraction-digits 2;
                                            }
                                            units "failures per second";
                                            description "IKE exchange failure rate - non-proposal chosen.";
                                        }

                                        ///nokia-state/state/esa/vm/tunnel/statistics/ipsec/ike-exchange-failure-rate/historical/non-proposal-chosen/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/non-proposal-chosen/first-failure-description
                                        leaf first-failure-description {
                                            type types-sros:long-description;
                                            description "The description of the place where the first IKE exchange failure happened.";
                                        }

                                        ///nokia-state/state/esa/vm/tunnel/statistics/ipsec/ike-exchange-failure-rate/historical/non-proposal-chosen/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/non-proposal-chosen/last-failure-description
                                        leaf last-failure-description {
                                            type types-sros:long-description;
                                            description "The description of the place where the last IKE exchange failure happened.";
                                        }

                                    } // container non-proposal-chosen

                                    ///nokia-state/state/esa/vm/tunnel/statistics/ipsec/ike-exchange-failure-rate/historical/internal-address-assignment
                                    container internal-address-assignment {
                                        description "Enter the internal-address-assignment context";

                                        ///nokia-state/state/esa/vm/tunnel/statistics/ipsec/ike-exchange-failure-rate/historical/internal-address-assignment/count
                                        leaf count {
                                            type decimal64 {
                                                fraction-digits 2;
                                            }
                                            units "failures per second";
                                            description "IKE exchange failure rate - address assignment.";
                                        }

                                        ///nokia-state/state/esa/vm/tunnel/statistics/ipsec/ike-exchange-failure-rate/historical/internal-address-assignment/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/internal-address-assignment/first-failure-description
                                        leaf first-failure-description {
                                            type types-sros:long-description;
                                            description "The description of the place where the first IKE exchange failure happened.";
                                        }

                                        ///nokia-state/state/esa/vm/tunnel/statistics/ipsec/ike-exchange-failure-rate/historical/internal-address-assignment/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/internal-address-assignment/last-failure-description
                                        leaf last-failure-description {
                                            type types-sros:long-description;
                                            description "The description of the place where the last IKE exchange failure happened.";
                                        }

                                    } // container internal-address-assignment

                                    ///nokia-state/state/esa/vm/tunnel/statistics/ipsec/ike-exchange-failure-rate/historical/invalid-ts
                                    container invalid-ts {
                                        description "Enter the invalid-ts context";

                                        ///nokia-state/state/esa/vm/tunnel/statistics/ipsec/ike-exchange-failure-rate/historical/invalid-ts/count
                                        leaf count {
                                            type decimal64 {
                                                fraction-digits 2;
                                            }
                                            units "failures per second";
                                            description "IKE exchange failure rate - invalid traffic selector.";
                                        }

                                        ///nokia-state/state/esa/vm/tunnel/statistics/ipsec/ike-exchange-failure-rate/historical/invalid-ts/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/invalid-ts/first-failure-description
                                        leaf first-failure-description {
                                            type types-sros:long-description;
                                            description "The description of the place where the first IKE exchange failure happened.";
                                        }

                                        ///nokia-state/state/esa/vm/tunnel/statistics/ipsec/ike-exchange-failure-rate/historical/invalid-ts/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/invalid-ts/last-failure-description
                                        leaf last-failure-description {
                                            type types-sros:long-description;
                                            description "The description of the place where the last IKE exchange failure happened.";
                                        }

                                    } // container invalid-ts

                                    ///nokia-state/state/esa/vm/tunnel/statistics/ipsec/ike-exchange-failure-rate/historical/invalid-ke
                                    container invalid-ke {
                                        description "Enter the invalid-ke context";

                                        ///nokia-state/state/esa/vm/tunnel/statistics/ipsec/ike-exchange-failure-rate/historical/invalid-ke/count
                                        leaf count {
                                            type decimal64 {
                                                fraction-digits 2;
                                            }
                                            units "failures per second";
                                            description "IKE exchange failure rate - invalid key exchange.";
                                        }

                                        ///nokia-state/state/esa/vm/tunnel/statistics/ipsec/ike-exchange-failure-rate/historical/invalid-ke/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/invalid-ke/first-failure-description
                                        leaf first-failure-description {
                                            type types-sros:long-description;
                                            description "The description of the place where the first IKE exchange failure happened.";
                                        }

                                        ///nokia-state/state/esa/vm/tunnel/statistics/ipsec/ike-exchange-failure-rate/historical/invalid-ke/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/invalid-ke/last-failure-description
                                        leaf last-failure-description {
                                            type types-sros:long-description;
                                            description "The description of the place where the last IKE exchange failure happened.";
                                        }

                                    } // container invalid-ke

                                    ///nokia-state/state/esa/vm/tunnel/statistics/ipsec/ike-exchange-failure-rate/historical/dpd-timeout
                                    container dpd-timeout {
                                        description "Enter the dpd-timeout context";

                                        ///nokia-state/state/esa/vm/tunnel/statistics/ipsec/ike-exchange-failure-rate/historical/dpd-timeout/count
                                        leaf count {
                                            type decimal64 {
                                                fraction-digits 2;
                                            }
                                            units "failures per second";
                                            description "IKE exchange failure rate - DPD timeout.";
                                        }

                                        ///nokia-state/state/esa/vm/tunnel/statistics/ipsec/ike-exchange-failure-rate/historical/dpd-timeout/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/dpd-timeout/first-failure-description
                                        leaf first-failure-description {
                                            type types-sros:long-description;
                                            description "The description of the place where the first IKE exchange failure happened.";
                                        }

                                        ///nokia-state/state/esa/vm/tunnel/statistics/ipsec/ike-exchange-failure-rate/historical/dpd-timeout/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/dpd-timeout/last-failure-description
                                        leaf last-failure-description {
                                            type types-sros:long-description;
                                            description "The description of the place where the last IKE exchange failure happened.";
                                        }

                                    } // container dpd-timeout

                                    ///nokia-state/state/esa/vm/tunnel/statistics/ipsec/ike-exchange-failure-rate/historical/other
                                    container other {
                                        description "Enter the other context";

                                        ///nokia-state/state/esa/vm/tunnel/statistics/ipsec/ike-exchange-failure-rate/historical/other/count
                                        leaf count {
                                            type decimal64 {
                                                fraction-digits 2;
                                            }
                                            units "failures per second";
                                            description "IKE exchange failure rate - other failure reasons.";
                                        }

                                        ///nokia-state/state/esa/vm/tunnel/statistics/ipsec/ike-exchange-failure-rate/historical/other/first-failure
                                        leaf first-failure {
                                            type yang:date-and-time;
                                            description
                                                "The time when the first IKE exchange failure happened
                                                 in the corresponding sampling interval.";
                                        }

                                        ///nokia-state/state/esa/vm/tunnel/statistics/ipsec/ike-exchange-failure-rate/historical/other/first-failure-description
                                        leaf first-failure-description {
                                            type types-sros:long-description;
                                            description "The description of the place where the first IKE exchange failure happened.";
                                        }

                                        ///nokia-state/state/esa/vm/tunnel/statistics/ipsec/ike-exchange-failure-rate/historical/other/last-failure
                                        leaf last-failure {
                                            type yang:date-and-time;
                                            description
                                                "The time when the last IKE exchange failure happened
                                                 in the corresponding sampling interval.";
                                        }

                                        ///nokia-state/state/esa/vm/tunnel/statistics/ipsec/ike-exchange-failure-rate/historical/other/last-failure-description
                                        leaf last-failure-description {
                                            type types-sros:long-description;
                                            description "The description of the place where the last IKE exchange failure happened.";
                                        }

                                    } // container other

                                } // list historical

                            } // container ike-exchange-failure-rate

                            ///nokia-state/state/esa/vm/tunnel/statistics/ipsec/ikev2-msg-drop
                            container ikev2-msg-drop {
                                description "Enter the ikev2-msg-drop context";

                                ///nokia-state/state/esa/vm/tunnel/statistics/ipsec/ikev2-msg-drop/current
                                container current {
                                    description "Enter the current context";

                                    ///nokia-state/state/esa/vm/tunnel/statistics/ipsec/ikev2-msg-drop/current/ike-sa-init
                                    leaf ike-sa-init {
                                        type yang:counter64;
                                        description "Number of IKE-SA-INIT exchange packet drops.";
                                    }

                                    ///nokia-state/state/esa/vm/tunnel/statistics/ipsec/ikev2-msg-drop/current/ike-auth
                                    leaf ike-auth {
                                        type yang:counter64;
                                        description "Number of IKE-AUTH exchange packet drops.";
                                    }

                                    ///nokia-state/state/esa/vm/tunnel/statistics/ipsec/ikev2-msg-drop/current/create-child-and-info
                                    leaf create-child-and-info {
                                        type yang:counter64;
                                        description "Number of Create-CHILD and informational exchange packet drops.";
                                    }

                                    ///nokia-state/state/esa/vm/tunnel/statistics/ipsec/ikev2-msg-drop/current/start-time
                                    leaf start-time {
                                        type yang:date-and-time;
                                        description "The time when the sampling interval started.";
                                    }

                                    ///nokia-state/state/esa/vm/tunnel/statistics/ipsec/ikev2-msg-drop/current/sampling-duration
                                    leaf sampling-duration {
                                        type types-sros:time-duration;
                                        description "The duration of the corresponding sampling interval.";
                                    }

                                } // container current

                            } // container ikev2-msg-drop

                        } // container ipsec

                    } // container statistics

                } // container tunnel

                ///nokia-state/state/esa/vm/core-utilization
                list core-utilization {
                    key "vm-core-id";
                    description "Enter the core-utilization list instance";

                    ///nokia-state/state/esa/vm/core-utilization/vm-core-id
                    leaf vm-core-id {
                        type uint32 {
                            range "1..62";
                        }
                        description "The ID of the VM Core.";
                    }

                    ///nokia-state/state/esa/vm/core-utilization/virt-core-role-name
                    leaf virt-core-role-name {
                        type types-sros:named-item;
                        description "Indicates the esa-vm virtual core role.";
                    }

                    ///nokia-state/state/esa/vm/core-utilization/virt-core-curr-util
                    leaf virt-core-curr-util {
                        type uint32;
                        units "centipercent";
                        description
                            "Indicates the current 10-second utilization of this virtual
                             core on the esa-vm.";
                    }

                    ///nokia-state/state/esa/vm/core-utilization/virt-core-avg-util
                    leaf virt-core-avg-util {
                        type uint32;
                        units "centipercent";
                        description
                            "Indicates the average 15-minute utilization of this virtual
                             core on the esa-vm.";
                    }

                    ///nokia-state/state/esa/vm/core-utilization/virt-core-peak-util
                    leaf virt-core-peak-util {
                        type uint32;
                        units "centipercent";
                        description
                            "Indicates the all-time peak 10-second utilization of
                             this virtual core on the esa-vm.";
                    }

                } // list core-utilization

            } // list vm

            ///nokia-state/state/esa/cell-topology
            list cell-topology {
                key "cell-id";
                description "Enter the cell-topology list instance";

                ///nokia-state/state/esa/cell-topology/cell-id
                leaf cell-id {
                    type uint32 {
                        range "0..7";
                    }
                    description "The ID of the cell.";
                }

                ///nokia-state/state/esa/cell-topology/socket
                leaf socket {
                    type uint32;
                    description "Indicates the socket number that the ESA NUMA cell resides on.";
                }

                ///nokia-state/state/esa/cell-topology/cores-available
                leaf cores-available {
                    type yang:gauge32;
                    description "Indicates the total number of cores on the ESA NUMA cell.";
                }

                ///nokia-state/state/esa/cell-topology/cores-allocated
                leaf cores-allocated {
                    type yang:gauge32;
                    description "Indicates the total number of allocated cores on the ESA NUMA cell.";
                }

                ///nokia-state/state/esa/cell-topology/memory-available
                leaf memory-available {
                    type yang:gauge32;
                    units "gigabytes";
                    description
                        "Indicates the total amount of available memory (in GigaBytes)
                         on the ESA NUMA cell.";
                }

                ///nokia-state/state/esa/cell-topology/memory-allocated
                leaf memory-allocated {
                    type yang:gauge32;
                    units "gigabytes";
                    description
                        "Indicates the total amount of allocated memory (in GigaBytes)
                         on the ESA NUMA cell.";
                }

            } // list cell-topology

        } // list esa

    } // grouping state-esa

}
