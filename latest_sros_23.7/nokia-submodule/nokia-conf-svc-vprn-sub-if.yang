submodule nokia-conf-svc-vprn-sub-if {

    yang-version "1.1";

    belongs-to nokia-conf { prefix "conf"; }

    import nokia-sros-yang-extensions     { prefix "sros-ext"; }
    import nokia-types-eth-cfm            { prefix "types-eth-cfm"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }

    include nokia-conf-aa-group;
    include nokia-conf-aaa;
    include nokia-conf-application-assurance;
    include nokia-conf-eth-cfm;
    include nokia-conf-filter;
    include nokia-conf-filter-dhcp;
    include nokia-conf-groups;
    include nokia-conf-log;
    include nokia-conf-policy-options;
    include nokia-conf-port;
    include nokia-conf-port-eth-access;
    include nokia-conf-port-ethernet;
    include nokia-conf-pxc;
    include nokia-conf-python;
    include nokia-conf-qos;
    include nokia-conf-routing-options;
    include nokia-conf-service;
    include nokia-conf-submgt-local-user-db;
    include nokia-conf-submgt-vrgw;
    include nokia-conf-subscriber-mgmt;
    include nokia-conf-svc-epipe;
    include nokia-conf-svc-vprn;
    include nokia-conf-svc-vprn-dhcp-server;
    include nokia-conf-svc-vprn-grp-if-wlangw;
    include nokia-conf-svc-vprn-sub-if-wlangw;
    include nokia-conf-system;
    include nokia-conf-system-security;
    include nokia-conf-vrrp;

    sros-ext:sros-major-release "rel23";
    organization "Nokia";
    contact
        "Nokia SR OS Support
         Web: <http://www.nokia.com>";
    description
        "Nokia YANG Data model to configure vprn service subscriber interfaces on SR OS based routers.

         Copyright 2016 Nokia. All rights reserved. Reproduction of this document
         is authorized on the condition that the foregoing copyright notice is included.

         This nokia-conf-svc-vprn-sub-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-07";

    grouping conf-svc-vprn-sub-if-subscriber-interface {
        ///nokia-conf/configure/service/vprn/subscriber-interface
        list subscriber-interface {
            key "interface-name";
            description "Enter the subscriber-interface list instance";

            ///nokia-conf/configure/service/vprn/subscriber-interface/interface-name
            leaf interface-name {
                type types-sros:interface-name;
                description "Subscriber interface name";
            }

            ///nokia-conf/configure/service/vprn/subscriber-interface/admin-state
            leaf admin-state {
                type types-sros:admin-state;
                default "enable";
                description "Administrative state of the subscriber interface";
            }

            ///nokia-conf/configure/service/vprn/subscriber-interface/description
            leaf description {
                type types-sros:very-long-description;
                description "Text description";
            }

            ///nokia-conf/configure/service/vprn/subscriber-interface/fwd-service
            leaf fwd-service {
                type leafref {
                    path "../../../vprn/service-name";
                }
                sros-ext:immutable;
                description "Configure the forwarding service.";
            }

            ///nokia-conf/configure/service/vprn/subscriber-interface/fwd-subscriber-interface
            leaf fwd-subscriber-interface {
                type leafref {
                    path "../../../vprn[service-name=current()/../fwd-service]/subscriber-interface/interface-name";
                }
                sros-ext:immutable;
                description "Forwarding subscriber interface name";
            }

            ///nokia-conf/configure/service/vprn/subscriber-interface/wan-mode
            leaf wan-mode {
                type enumeration {
                    enum mode64                         { value 1; }
                    enum mode128                        { value 2; }
                }
                sros-ext:immutable;
                default "mode64";
                description "Mode of operation for hosts with /128 WAN IPv6 address";
            }

            ///nokia-conf/configure/service/vprn/subscriber-interface/private-retail-subnets
            leaf private-retail-subnets {
                when "../fwd-service" {
                    description "fwd-service must be set";
                }
                type boolean;
                sros-ext:immutable;
                default "false";
                description "Export subnets to the forwarding service";
            }

            ///nokia-conf/configure/service/vprn/subscriber-interface/apply-groups
            leaf-list apply-groups {
                type leafref {
                    path "../../../../groups/group/name";
                }
                max-elements 8;
                ordered-by user;
                description "Apply a configuration group at this level";
            }

            ///nokia-conf/configure/service/vprn/subscriber-interface/apply-groups-exclude
            leaf-list apply-groups-exclude {
                type leafref {
                    path "../../../../groups/group/name";
                }
                max-elements 8;
                ordered-by user;
                description "Exclude a configuration group at this level";
            }

            ///nokia-conf/configure/service/vprn/subscriber-interface/ipv4
            container ipv4 {
                description "Enter the ipv4 context";

                ///nokia-conf/configure/service/vprn/subscriber-interface/ipv4/allow-unmatching-subnets
                leaf allow-unmatching-subnets {
                    type boolean;
                    default "false";
                    description "Allow subscriber hosts without a matching subnet";
                }

                ///nokia-conf/configure/service/vprn/subscriber-interface/ipv4/export-host-routes
                leaf export-host-routes {
                    when "../../fwd-service" {
                        description "fwd-service must be set";
                    }
                    type boolean;
                    default "false";
                    description "Allow export of subscriber management host routes";
                }

                ///nokia-conf/configure/service/vprn/subscriber-interface/ipv4/default-dns
                leaf-list default-dns {
                    type types-sros:ipv4-unicast-address;
                    max-elements 2;
                    ordered-by user;
                    description "Default DNS server addresses";
                }

                ///nokia-conf/configure/service/vprn/subscriber-interface/ipv4/address
                list address {
                    key "ipv4-address";
                    description "Enter the address list instance";

                    ///nokia-conf/configure/service/vprn/subscriber-interface/ipv4/address/ipv4-address
                    leaf ipv4-address {
                        type types-sros:ipv4-unicast-address;
                        description "IP address associated with the subscriber subnet";
                    }

                    ///nokia-conf/configure/service/vprn/subscriber-interface/ipv4/address/prefix-length
                    leaf prefix-length {
                        type uint32 {
                            range "0..32";
                        }
                        mandatory true;
                        description "IPv4 address prefix length";
                    }

                    ///nokia-conf/configure/service/vprn/subscriber-interface/ipv4/address/gateway
                    leaf gateway {
                        type types-sros:ipv4-unicast-address;
                        description "Gateway IP address within the subnet for SRRP routing";
                    }

                    ///nokia-conf/configure/service/vprn/subscriber-interface/ipv4/address/track-srrp
                    leaf track-srrp {
                        type uint32 {
                            range "1..4294967295";
                        }
                        description "SRRP instance whose state is tracked on this IP address";
                    }

                    ///nokia-conf/configure/service/vprn/subscriber-interface/ipv4/address/populate-host-routes
                    leaf populate-host-routes {
                        type boolean;
                        default "false";
                        description "Populate subscriber host routes in local FIB";
                    }

                    ///nokia-conf/configure/service/vprn/subscriber-interface/ipv4/address/holdup-time
                    leaf holdup-time {
                        type uint32 {
                            range "100..5000";
                        }
                        units "milliseconds";
                        description "Wait time before accepting new state attribute";
                    }

                    ///nokia-conf/configure/service/vprn/subscriber-interface/ipv4/address/apply-groups
                    leaf-list apply-groups {
                        type leafref {
                            path "../../../../../../groups/group/name";
                        }
                        max-elements 8;
                        ordered-by user;
                        description "Apply a configuration group at this level";
                    }

                    ///nokia-conf/configure/service/vprn/subscriber-interface/ipv4/address/apply-groups-exclude
                    leaf-list apply-groups-exclude {
                        type leafref {
                            path "../../../../../../groups/group/name";
                        }
                        max-elements 8;
                        ordered-by user;
                        description "Exclude a configuration group at this level";
                    }

                } // list address

                ///nokia-conf/configure/service/vprn/subscriber-interface/ipv4/arp-host
                container arp-host {
                    when "../../fwd-service" {
                        description "fwd-service must be set";
                    }
                    description "Enter the arp-host context";

                    ///nokia-conf/configure/service/vprn/subscriber-interface/ipv4/arp-host/admin-state
                    leaf admin-state {
                        type types-sros:admin-state;
                        description "Administrative state of ARP hosts";
                    }

                    ///nokia-conf/configure/service/vprn/subscriber-interface/ipv4/arp-host/host-limit
                    leaf host-limit {
                        type uint32 {
                            range "1..524287";
                        }
                        description "Maximum number of ARP hosts";
                    }

                    ///nokia-conf/configure/service/vprn/subscriber-interface/ipv4/arp-host/apply-groups
                    leaf-list apply-groups {
                        type leafref {
                            path "../../../../../../groups/group/name";
                        }
                        max-elements 8;
                        ordered-by user;
                        description "Apply a configuration group at this level";
                    }

                    ///nokia-conf/configure/service/vprn/subscriber-interface/ipv4/arp-host/apply-groups-exclude
                    leaf-list apply-groups-exclude {
                        type leafref {
                            path "../../../../../../groups/group/name";
                        }
                        max-elements 8;
                        ordered-by user;
                        description "Exclude a configuration group at this level";
                    }

                } // container arp-host

                ///nokia-conf/configure/service/vprn/subscriber-interface/ipv4/unnumbered
                container unnumbered {
                    description "Enter the unnumbered context";

                    ///nokia-conf/configure/service/vprn/subscriber-interface/ipv4/unnumbered/source
                    choice source {
                        ///nokia-conf/configure/service/vprn/subscriber-interface/ipv4/unnumbered/source/ip-address
                        case ip-address {

                            ///nokia-conf/configure/service/vprn/subscriber-interface/ipv4/unnumbered/source/ip-address/ip-address
                            leaf ip-address {
                                type types-sros:ipv4-unicast-address;
                                description "IP address for the subscriber interface";
                            }

                        }
                        ///nokia-conf/configure/service/vprn/subscriber-interface/ipv4/unnumbered/source/ip-int-name
                        case ip-int-name {

                            ///nokia-conf/configure/service/vprn/subscriber-interface/ipv4/unnumbered/source/ip-int-name/ip-int-name
                            leaf ip-int-name {
                                type types-sros:interface-name;
                                description "Interface name from which an IPv4 addressed is borrowed";
                            }

                        }
                    }
                } // container unnumbered

                ///nokia-conf/configure/service/vprn/subscriber-interface/ipv4/bfd
                container bfd {
                    description "Enter the bfd context";

                    ///nokia-conf/configure/service/vprn/subscriber-interface/ipv4/bfd/admin-state
                    leaf admin-state {
                        type types-sros:admin-state;
                        default "disable";
                        description "Administrative state of BFD sessions";
                    }

                    ///nokia-conf/configure/service/vprn/subscriber-interface/ipv4/bfd/transmit-interval
                    leaf transmit-interval {
                        type uint32 {
                            range "10..100000";
                        }
                        units "milliseconds";
                        default "100";
                        description "BFD transmit interval over this interface";
                    }

                    ///nokia-conf/configure/service/vprn/subscriber-interface/ipv4/bfd/receive
                    leaf receive {
                        type uint32 {
                            range "10..100000";
                        }
                        units "milliseconds";
                        default "100";
                        description "BFD receive interval over this interface";
                    }

                    ///nokia-conf/configure/service/vprn/subscriber-interface/ipv4/bfd/multiplier
                    leaf multiplier {
                        type uint32 {
                            range "1..20";
                        }
                        default "3";
                        description "Number of consecutive BFD messages missed from the peer";
                    }

                    ///nokia-conf/configure/service/vprn/subscriber-interface/ipv4/bfd/echo-receive
                    leaf echo-receive {
                        type uint32 {
                            range "100..100000";
                        }
                        units "milliseconds";
                        description "Minimum echo interval over this interface";
                    }

                    ///nokia-conf/configure/service/vprn/subscriber-interface/ipv4/bfd/type
                    leaf type {
                        type enumeration {
                            enum cpm-np                         { value 1; }
                            enum auto                           { value 2; }
                            enum fp                             { value 3; }
                        }
                        default "auto";
                        description "Local termination point for the BFD session";
                    }

                } // container bfd

                ///nokia-conf/configure/service/vprn/subscriber-interface/ipv4/dhcp
                container dhcp {
                    description "Enable the dhcp context";

                    ///nokia-conf/configure/service/vprn/subscriber-interface/ipv4/dhcp/admin-state
                    leaf admin-state {
                        when "../../../fwd-service" {
                            description "fwd-service must be set";
                        }
                        type types-sros:admin-state;
                        description "Administrative state of DHCP";
                    }

                    ///nokia-conf/configure/service/vprn/subscriber-interface/ipv4/dhcp/description
                    leaf description {
                        when "../../../fwd-service" {
                            description "fwd-service must be set";
                        }
                        type types-sros:description;
                        description "Text description";
                    }

                    ///nokia-conf/configure/service/vprn/subscriber-interface/ipv4/dhcp/python-policy
                    leaf python-policy {
                        when "../../../fwd-service" {
                            description "fwd-service must be set";
                        }
                        type leafref {
                            path "../../../../../../python/python-policy/name";
                        }
                        description "Python policy";
                    }

                    ///nokia-conf/configure/service/vprn/subscriber-interface/ipv4/dhcp/server
                    leaf-list server {
                        when "../../../fwd-service" {
                            description "fwd-service must be set";
                        }
                        type types-sros:ipv4-unicast-address;
                        max-elements 8;
                        ordered-by user;
                        description "DHCP server IP addresses";
                    }

                    ///nokia-conf/configure/service/vprn/subscriber-interface/ipv4/dhcp/gi-address
                    leaf gi-address {
                        type types-sros:ipv4-unicast-address;
                        description "GI address for the DHCP relay";
                    }

                    ///nokia-conf/configure/service/vprn/subscriber-interface/ipv4/dhcp/release-include-gi-address
                    leaf release-include-gi-address {
                        when "../../../fwd-service" {
                            description "fwd-service must be set";
                        }
                        type boolean;
                        default "false";
                        description "Include the GI address in DHCP relay messages";
                    }

                    ///nokia-conf/configure/service/vprn/subscriber-interface/ipv4/dhcp/src-ip-addr
                    leaf src-ip-addr {
                        type enumeration {
                            enum auto                           { value 0; }
                            enum gi-address                     { value 1; }
                        }
                        default "auto";
                        description "Type of source address to use for DHCP relay";
                    }

                    ///nokia-conf/configure/service/vprn/subscriber-interface/ipv4/dhcp/virtual-subnet
                    leaf virtual-subnet {
                        when "not(../../../fwd-service)" {
                            description "fwd-service must be unset";
                        }
                        type boolean;
                        default "false";
                        description "Enable a virtual subnet for DHCPv4 hosts";
                    }

                    ///nokia-conf/configure/service/vprn/subscriber-interface/ipv4/dhcp/apply-groups
                    leaf-list apply-groups {
                        type leafref {
                            path "../../../../../../groups/group/name";
                        }
                        max-elements 8;
                        ordered-by user;
                        description "Apply a configuration group at this level";
                    }

                    ///nokia-conf/configure/service/vprn/subscriber-interface/ipv4/dhcp/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/ipv4/dhcp/proxy-server
                    container proxy-server {
                        when "../../../fwd-service" {
                            description "fwd-service must be set";
                        }
                        description "Enter the proxy-server context";

                        ///nokia-conf/configure/service/vprn/subscriber-interface/ipv4/dhcp/proxy-server/admin-state
                        leaf admin-state {
                            type types-sros:admin-state;
                            default "disable";
                            description "Administrative state of the DHCP proxy server";
                        }

                        ///nokia-conf/configure/service/vprn/subscriber-interface/ipv4/dhcp/proxy-server/emulated-server
                        leaf emulated-server {
                            type types-sros:ipv4-unicast-address;
                            description "IP address used as DHCP server address in SAP context";
                        }

                        ///nokia-conf/configure/service/vprn/subscriber-interface/ipv4/dhcp/proxy-server/lease-time
                        container lease-time {
                            description "Enter the lease-time context";

                            ///nokia-conf/configure/service/vprn/subscriber-interface/ipv4/dhcp/proxy-server/lease-time/value
                            leaf value {
                                type types-sros:time-duration {
                                    range "300..315446399";
                                }
                                units "seconds";
                                description "DHCP lease time";
                            }

                            ///nokia-conf/configure/service/vprn/subscriber-interface/ipv4/dhcp/proxy-server/lease-time/radius-override
                            leaf radius-override {
                                type boolean;
                                default "false";
                                description "Use lease time information provided by RADIUS server";
                            }

                        } // container lease-time

                    } // container proxy-server

                    ///nokia-conf/configure/service/vprn/subscriber-interface/ipv4/dhcp/option-82
                    container option-82 {
                        when "../../../fwd-service" {
                            description "fwd-service must be set";
                        }
                        description "Enter the option-82 context";

                        ///nokia-conf/configure/service/vprn/subscriber-interface/ipv4/dhcp/option-82/vendor-specific-option
                        container vendor-specific-option {
                            description "Enter the vendor-specific-option context";

                            ///nokia-conf/configure/service/vprn/subscriber-interface/ipv4/dhcp/option-82/vendor-specific-option/system-id
                            leaf system-id {
                                type boolean;
                                default "false";
                                description "Send the system ID in the VSO";
                            }

                            ///nokia-conf/configure/service/vprn/subscriber-interface/ipv4/dhcp/option-82/vendor-specific-option/client-mac-address
                            leaf client-mac-address {
                                type boolean;
                                default "false";
                                description "Send the MAC address in the VSO";
                            }

                            ///nokia-conf/configure/service/vprn/subscriber-interface/ipv4/dhcp/option-82/vendor-specific-option/service-id
                            leaf service-id {
                                type boolean;
                                default "false";
                                description "Send the service ID in the Vendor Specific Option";
                            }

                            ///nokia-conf/configure/service/vprn/subscriber-interface/ipv4/dhcp/option-82/vendor-specific-option/sap-id
                            leaf sap-id {
                                type boolean;
                                default "false";
                                description "Send SAP ID in the sub-option of the DHCP relay packet";
                            }

                            ///nokia-conf/configure/service/vprn/subscriber-interface/ipv4/dhcp/option-82/vendor-specific-option/string
                            leaf string {
                                type types-sros:string-not-all-spaces {
                                    length "1..32";
                                }
                                description "User-defined ASCII string for the VSO";
                            }

                        } // container vendor-specific-option

                    } // container option-82

                    ///nokia-conf/configure/service/vprn/subscriber-interface/ipv4/dhcp/lease-populate
                    container lease-populate {
                        when "../../../fwd-service" {
                            description "fwd-service must be set";
                        }
                        description "Enter the lease-populate context";

                        ///nokia-conf/configure/service/vprn/subscriber-interface/ipv4/dhcp/lease-populate/max-leases
                        leaf max-leases {
                            type uint32 {
                                range "0..511999";
                            }
                            description "Maximum number of DHCPv4 leases";
                        }

                    } // container lease-populate

                    ///nokia-conf/configure/service/vprn/subscriber-interface/ipv4/dhcp/client-applications
                    container client-applications {
                        when "../../../fwd-service" {
                            description "fwd-service must be set";
                        }
                        description "Enter the client-applications context";

                        ///nokia-conf/configure/service/vprn/subscriber-interface/ipv4/dhcp/client-applications/dhcp
                        leaf dhcp {
                            type boolean;
                            default "true";
                            description "Enable IPoE clients to use DHCP relay or proxy server";
                        }

                        ///nokia-conf/configure/service/vprn/subscriber-interface/ipv4/dhcp/client-applications/ppp
                        leaf ppp {
                            type boolean;
                            default "false";
                            description "Enable PPPoE clients to use DHCP relay or proxy server";
                        }

                    } // container client-applications

                    ///nokia-conf/configure/service/vprn/subscriber-interface/ipv4/dhcp/relay-proxy
                    container relay-proxy {
                        when "../../../fwd-service" {
                            description "fwd-service must be set";
                        }
                        presence "Enable the relay-proxy context";
                        description "Enable the relay-proxy context";

                        ///nokia-conf/configure/service/vprn/subscriber-interface/ipv4/dhcp/relay-proxy/release-update-src-ip
                        leaf release-update-src-ip {
                            type boolean;
                            default "false";
                            description "Update the source IP address of a DHCP RELEASE message";
                        }

                        ///nokia-conf/configure/service/vprn/subscriber-interface/ipv4/dhcp/relay-proxy/siaddr-override
                        leaf siaddr-override {
                            type types-sros:ipv4-unicast-address;
                            description "DHCP server IP address for address hiding function";
                        }

                    } // container relay-proxy

                    ///nokia-conf/configure/service/vprn/subscriber-interface/ipv4/dhcp/offer-selection
                    container offer-selection {
                        description "Enter the offer-selection context";

                        ///nokia-conf/configure/service/vprn/subscriber-interface/ipv4/dhcp/offer-selection/discover-delay
                        leaf discover-delay {
                            type int32 {
                                range "1..100";
                            }
                            units "deciseconds";
                            description "Delay before sending DHCP Discover messages";
                        }

                        ///nokia-conf/configure/service/vprn/subscriber-interface/ipv4/dhcp/offer-selection/mode
                        choice mode {
                            ///nokia-conf/configure/service/vprn/subscriber-interface/ipv4/dhcp/offer-selection/mode/mode-client-mac
                            case mode-client-mac {

                                ///nokia-conf/configure/service/vprn/subscriber-interface/ipv4/dhcp/offer-selection/mode/mode-client-mac/client-mac
                                container client-mac {
                                    description "Enter the client-mac context";

                                    ///nokia-conf/configure/service/vprn/subscriber-interface/ipv4/dhcp/offer-selection/mode/mode-client-mac/client-mac/mac-address
                                    leaf mac-address {
                                        type enumeration {
                                            enum odd                            { value 1; }
                                            enum even                           { value 2; }
                                        }
                                        description "Designated client MAC addresses for Offer selection";
                                    }

                                    ///nokia-conf/configure/service/vprn/subscriber-interface/ipv4/dhcp/offer-selection/mode/mode-client-mac/client-mac/discover-delay
                                    leaf discover-delay {
                                        type int32 {
                                            range "1..100";
                                        }
                                        units "deciseconds";
                                        description "Delay before sending DHCP Discover messages";
                                    }

                                } // container client-mac

                            }
                            ///nokia-conf/configure/service/vprn/subscriber-interface/ipv4/dhcp/offer-selection/mode/mode-server
                            case mode-server {

                                ///nokia-conf/configure/service/vprn/subscriber-interface/ipv4/dhcp/offer-selection/mode/mode-server/server
                                list server {
                                    key "ipv4-address";
                                    max-elements 8;
                                    description "Enter the server list instance";

                                    ///nokia-conf/configure/service/vprn/subscriber-interface/ipv4/dhcp/offer-selection/mode/mode-server/server/ipv4-address
                                    leaf ipv4-address {
                                        type types-sros:ipv4-unicast-address;
                                        description "IP address of the DHCP server";
                                    }

                                    ///nokia-conf/configure/service/vprn/subscriber-interface/ipv4/dhcp/offer-selection/mode/mode-server/server/discover-delay
                                    leaf discover-delay {
                                        type int32 {
                                            range "1..100";
                                        }
                                        units "deciseconds";
                                        description "Delay before sending DHCP Discover messages";
                                    }

                                    ///nokia-conf/configure/service/vprn/subscriber-interface/ipv4/dhcp/offer-selection/mode/mode-server/server/apply-groups
                                    leaf-list apply-groups {
                                        type leafref {
                                            path "../../../../../../../../groups/group/name";
                                        }
                                        max-elements 8;
                                        ordered-by user;
                                        description "Apply a configuration group at this level";
                                    }

                                    ///nokia-conf/configure/service/vprn/subscriber-interface/ipv4/dhcp/offer-selection/mode/mode-server/server/apply-groups-exclude
                                    leaf-list apply-groups-exclude {
                                        type leafref {
                                            path "../../../../../../../../groups/group/name";
                                        }
                                        max-elements 8;
                                        ordered-by user;
                                        description "Exclude a configuration group at this level";
                                    }

                                } // list server

                            }
                        }
                    } // container offer-selection

                } // container dhcp

            } // container ipv4

            ///nokia-conf/configure/service/vprn/subscriber-interface/ipv6
            container ipv6 {
                presence "Enable the ipv6 context";
                description "Enable the ipv6 context";

                ///nokia-conf/configure/service/vprn/subscriber-interface/ipv6/allow-multiple-wan-addresses
                leaf allow-multiple-wan-addresses {
                    when "../../fwd-service" {
                        description "fwd-service must be set";
                    }
                    type boolean;
                    default "false";
                    description "Allow multiple WAN addresses";
                }

                ///nokia-conf/configure/service/vprn/subscriber-interface/ipv6/ipoe-bridged-mode
                leaf ipoe-bridged-mode {
                    when "../../fwd-service" {
                        description "fwd-service must be set";
                    }
                    type boolean;
                    default "false";
                    description "Enable IPv6 IPoE bridged mode";
                }

                ///nokia-conf/configure/service/vprn/subscriber-interface/ipv6/allow-unmatching-prefixes
                leaf allow-unmatching-prefixes {
                    type boolean;
                    default "false";
                    description "Allow subscriber hosts without a matching prefix";
                }

                ///nokia-conf/configure/service/vprn/subscriber-interface/ipv6/delegated-prefix-length
                leaf delegated-prefix-length {
                    when "not(../../fwd-service)" {
                        description "fwd-service must be unset";
                    }
                    type union {
                        type uint32 {
                            range "48..64";
                        }
                        type enumeration {
                            enum variable                       { value 0; }
                        }
                    }
                    default "64";
                    description "IPv6 delegated prefix length";
                }

                ///nokia-conf/configure/service/vprn/subscriber-interface/ipv6/default-dns
                leaf-list default-dns {
                    type types-sros:ipv6-unicast-address;
                    max-elements 2;
                    ordered-by user;
                    description "Default DNS server addresses";
                }

                ///nokia-conf/configure/service/vprn/subscriber-interface/ipv6/address
                list address {
                    key "ipv6-address";
                    description "Enter the address list instance";

                    ///nokia-conf/configure/service/vprn/subscriber-interface/ipv6/address/ipv6-address
                    leaf ipv6-address {
                        type types-sros:ipv6-address;
                        description "IPv6 address for the subscriber interface";
                    }

                    ///nokia-conf/configure/service/vprn/subscriber-interface/ipv6/address/prefix-length
                    leaf prefix-length {
                        type uint32 {
                            range "0..128";
                        }
                        mandatory true;
                        description "IPv6 address prefix length";
                    }

                    ///nokia-conf/configure/service/vprn/subscriber-interface/ipv6/address/host-type
                    leaf host-type {
                        type enumeration {
                            enum pd {
                                value 0;
                                description "IPv6 ESM hosts for DHCPv6 prefix-delegation";
                            }
                            enum wan {
                                value 1;
                                description "ESM hosts for DHCPv6 addresses or by WAN interface";
                            }
                            enum pd-wan {
                                value 2;
                                description "Both prefix-delegation and ESM hosts";
                            }
                        }
                        sros-ext:immutable;
                        default "pd";
                        description "Host type for subscriber interface prefixes";
                    }

                    ///nokia-conf/configure/service/vprn/subscriber-interface/ipv6/address/apply-groups
                    leaf-list apply-groups {
                        type leafref {
                            path "../../../../../../groups/group/name";
                        }
                        max-elements 8;
                        ordered-by user;
                        description "Apply a configuration group at this level";
                    }

                    ///nokia-conf/configure/service/vprn/subscriber-interface/ipv6/address/apply-groups-exclude
                    leaf-list apply-groups-exclude {
                        type leafref {
                            path "../../../../../../groups/group/name";
                        }
                        max-elements 8;
                        ordered-by user;
                        description "Exclude a configuration group at this level";
                    }

                } // list address

                ///nokia-conf/configure/service/vprn/subscriber-interface/ipv6/prefix
                list prefix {
                    key "ipv6-prefix";
                    description "Enter the prefix list instance";

                    ///nokia-conf/configure/service/vprn/subscriber-interface/ipv6/prefix/ipv6-prefix
                    leaf ipv6-prefix {
                        type types-sros:ipv6-prefix;
                        description "IPv6 address for a router interface";
                    }

                    ///nokia-conf/configure/service/vprn/subscriber-interface/ipv6/prefix/track-srrp
                    leaf track-srrp {
                        type uint32 {
                            range "1..4294967295";
                        }
                        description "SRRP instance whose state is tracked on this IP address";
                    }

                    ///nokia-conf/configure/service/vprn/subscriber-interface/ipv6/prefix/holdup-time
                    leaf holdup-time {
                        type uint32 {
                            range "100..5000";
                        }
                        units "milliseconds";
                        description "Time to wait before route accepts new state attribute";
                    }

                    ///nokia-conf/configure/service/vprn/subscriber-interface/ipv6/prefix/host-type
                    leaf host-type {
                        type enumeration {
                            enum pd {
                                value 0;
                                description "IPv6 ESM hosts for DHCPv6 prefix-delegation";
                            }
                            enum wan {
                                value 1;
                                description "ESM hosts for DHCPv6 addresses or by WAN interface";
                            }
                            enum pd-wan {
                                value 2;
                                description "Both prefix-delegation and ESM hosts";
                            }
                        }
                        sros-ext:immutable;
                        default "pd";
                        description "Host type for subscriber interface prefixes";
                    }

                    ///nokia-conf/configure/service/vprn/subscriber-interface/ipv6/prefix/apply-groups
                    leaf-list apply-groups {
                        type leafref {
                            path "../../../../../../groups/group/name";
                        }
                        max-elements 8;
                        ordered-by user;
                        description "Apply a configuration group at this level";
                    }

                    ///nokia-conf/configure/service/vprn/subscriber-interface/ipv6/prefix/apply-groups-exclude
                    leaf-list apply-groups-exclude {
                        type leafref {
                            path "../../../../../../groups/group/name";
                        }
                        max-elements 8;
                        ordered-by user;
                        description "Exclude a configuration group at this level";
                    }

                } // list prefix

                ///nokia-conf/configure/service/vprn/subscriber-interface/ipv6/link-local-address
                container link-local-address {
                    description "Enter the link-local-address context";

                    ///nokia-conf/configure/service/vprn/subscriber-interface/ipv6/link-local-address/address
                    leaf address {
                        type types-sros:ipv6-address;
                        description "IPv6 link local address";
                    }

                } // container link-local-address

                ///nokia-conf/configure/service/vprn/subscriber-interface/ipv6/bfd
                container bfd {
                    description "Enter the bfd context";

                    ///nokia-conf/configure/service/vprn/subscriber-interface/ipv6/bfd/admin-state
                    leaf admin-state {
                        type types-sros:admin-state;
                        default "disable";
                        description "Administrative state of BFD sessions";
                    }

                    ///nokia-conf/configure/service/vprn/subscriber-interface/ipv6/bfd/transmit-interval
                    leaf transmit-interval {
                        type uint32 {
                            range "10..100000";
                        }
                        units "milliseconds";
                        default "100";
                        description "BFD transmit interval over this interface";
                    }

                    ///nokia-conf/configure/service/vprn/subscriber-interface/ipv6/bfd/receive
                    leaf receive {
                        type uint32 {
                            range "10..100000";
                        }
                        units "milliseconds";
                        default "100";
                        description "BFD receive interval over this interface";
                    }

                    ///nokia-conf/configure/service/vprn/subscriber-interface/ipv6/bfd/multiplier
                    leaf multiplier {
                        type uint32 {
                            range "1..20";
                        }
                        default "3";
                        description "Number of consecutive BFD messages missed from the peer";
                    }

                    ///nokia-conf/configure/service/vprn/subscriber-interface/ipv6/bfd/echo-receive
                    leaf echo-receive {
                        type uint32 {
                            range "100..100000";
                        }
                        units "milliseconds";
                        description "Minimum echo interval over this interface";
                    }

                    ///nokia-conf/configure/service/vprn/subscriber-interface/ipv6/bfd/type
                    leaf type {
                        type enumeration {
                            enum cpm-np                         { value 1; }
                            enum auto                           { value 2; }
                            enum fp                             { value 3; }
                        }
                        default "auto";
                        description "Local termination point for the BFD session";
                    }

                } // container bfd

                ///nokia-conf/configure/service/vprn/subscriber-interface/ipv6/dhcp6
                container dhcp6 {
                    when "../../fwd-service" {
                        description "fwd-service must be set";
                    }
                    description "Enter the dhcp6 context";

                    ///nokia-conf/configure/service/vprn/subscriber-interface/ipv6/dhcp6/override-slaac
                    leaf override-slaac {
                        type boolean;
                        default "false";
                        description "Allow WAN address offered by DHCP to overwrite the WAN address acquired from SLAAC";
                    }

                    ///nokia-conf/configure/service/vprn/subscriber-interface/ipv6/dhcp6/python-policy
                    leaf python-policy {
                        type leafref {
                            path "../../../../../../python/python-policy/name";
                        }
                        description "Python policy";
                    }

                    ///nokia-conf/configure/service/vprn/subscriber-interface/ipv6/dhcp6/apply-groups
                    leaf-list apply-groups {
                        type leafref {
                            path "../../../../../../groups/group/name";
                        }
                        max-elements 8;
                        ordered-by user;
                        description "Apply a configuration group at this level";
                    }

                    ///nokia-conf/configure/service/vprn/subscriber-interface/ipv6/dhcp6/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/ipv6/dhcp6/pd-managed-route
                    container pd-managed-route {
                        presence "Enable the pd-managed-route context";
                        description "Enable the pd-managed-route context";

                        ///nokia-conf/configure/service/vprn/subscriber-interface/ipv6/dhcp6/pd-managed-route/next-hop
                        leaf next-hop {
                            type types-services:dhcp6-pd-managed-route-nh;
                            default "ipv6";
                            description "Next hop type";
                        }

                    } // container pd-managed-route

                    ///nokia-conf/configure/service/vprn/subscriber-interface/ipv6/dhcp6/relay
                    container relay {
                        description "Enter the relay context";

                        ///nokia-conf/configure/service/vprn/subscriber-interface/ipv6/dhcp6/relay/admin-state
                        leaf admin-state {
                            type types-sros:admin-state;
                            default "disable";
                            description "Administrative state of DHCPv6 Relay";
                        }

                        ///nokia-conf/configure/service/vprn/subscriber-interface/ipv6/dhcp6/relay/description
                        leaf description {
                            type types-sros:description;
                            description "Text description";
                        }

                        ///nokia-conf/configure/service/vprn/subscriber-interface/ipv6/dhcp6/relay/source-address
                        leaf source-address {
                            type types-sros:ipv6-unicast-address;
                            description "Source IPv6 address for the DHCPv6 relay messages";
                        }

                        ///nokia-conf/configure/service/vprn/subscriber-interface/ipv6/dhcp6/relay/link-address
                        leaf link-address {
                            type types-sros:ipv6-address;
                            description "Link address for the DHCPv6 relay messages";
                        }

                        ///nokia-conf/configure/service/vprn/subscriber-interface/ipv6/dhcp6/relay/server
                        leaf-list server {
                            type types-sros:ipv6-address-with-zone;
                            max-elements 8;
                            ordered-by user;
                            description "DHCP6 server(s) to which the DHCP6 requests are forwarded";
                        }

                        ///nokia-conf/configure/service/vprn/subscriber-interface/ipv6/dhcp6/relay/client-applications
                        container client-applications {
                            description "Enter the client-applications context";

                            ///nokia-conf/configure/service/vprn/subscriber-interface/ipv6/dhcp6/relay/client-applications/dhcp
                            leaf dhcp {
                                type boolean;
                                default "true";
                                description "Enable IPoE clients to use DHCP relay or proxy server";
                            }

                            ///nokia-conf/configure/service/vprn/subscriber-interface/ipv6/dhcp6/relay/client-applications/ppp
                            leaf ppp {
                                type boolean;
                                default "false";
                                description "Allow PPPoE clients to use DHCP relay functionality";
                            }

                        } // container client-applications

                        ///nokia-conf/configure/service/vprn/subscriber-interface/ipv6/dhcp6/relay/advertise-selection
                        container advertise-selection {
                            description "Enter the advertise-selection context";

                            ///nokia-conf/configure/service/vprn/subscriber-interface/ipv6/dhcp6/relay/advertise-selection/solicit-delay
                            leaf solicit-delay {
                                type int32 {
                                    range "1..100";
                                }
                                units "deciseconds";
                                description "Delay before sending DHCPv6 Solicit messages";
                            }

                            ///nokia-conf/configure/service/vprn/subscriber-interface/ipv6/dhcp6/relay/advertise-selection/mode
                            choice mode {
                                ///nokia-conf/configure/service/vprn/subscriber-interface/ipv6/dhcp6/relay/advertise-selection/mode/mode-client-mac
                                case mode-client-mac {

                                    ///nokia-conf/configure/service/vprn/subscriber-interface/ipv6/dhcp6/relay/advertise-selection/mode/mode-client-mac/client-mac
                                    container client-mac {
                                        description "Enter the client-mac context";

                                        ///nokia-conf/configure/service/vprn/subscriber-interface/ipv6/dhcp6/relay/advertise-selection/mode/mode-client-mac/client-mac/mac-address
                                        leaf mac-address {
                                            type enumeration {
                                                enum odd                            { value 1; }
                                                enum even                           { value 2; }
                                            }
                                            description "Designated client MAC addresses for Advertise selection";
                                        }

                                        ///nokia-conf/configure/service/vprn/subscriber-interface/ipv6/dhcp6/relay/advertise-selection/mode/mode-client-mac/client-mac/solicit-delay
                                        leaf solicit-delay {
                                            type int32 {
                                                range "1..100";
                                            }
                                            units "deciseconds";
                                            description "Delay before sending DHCPv6 Solicit messages";
                                        }

                                        ///nokia-conf/configure/service/vprn/subscriber-interface/ipv6/dhcp6/relay/advertise-selection/mode/mode-client-mac/client-mac/preference-option
                                        container preference-option {
                                            description "Enter the preference-option context";

                                            ///nokia-conf/configure/service/vprn/subscriber-interface/ipv6/dhcp6/relay/advertise-selection/mode/mode-client-mac/client-mac/preference-option/value
                                            leaf value {
                                                type int32 {
                                                    range "0..255";
                                                }
                                                description "Preference option value for DHCPv6 Advertise messages";
                                            }

                                        } // container preference-option

                                    } // container client-mac

                                }
                                ///nokia-conf/configure/service/vprn/subscriber-interface/ipv6/dhcp6/relay/advertise-selection/mode/mode-server
                                case mode-server {

                                    ///nokia-conf/configure/service/vprn/subscriber-interface/ipv6/dhcp6/relay/advertise-selection/mode/mode-server/server
                                    list server {
                                        key "ipv6-address";
                                        max-elements 8;
                                        description "Enter the server list instance";

                                        ///nokia-conf/configure/service/vprn/subscriber-interface/ipv6/dhcp6/relay/advertise-selection/mode/mode-server/server/ipv6-address
                                        leaf ipv6-address {
                                            type types-sros:ipv6-address;
                                            description "IP address of the DHCPv6 server";
                                        }

                                        ///nokia-conf/configure/service/vprn/subscriber-interface/ipv6/dhcp6/relay/advertise-selection/mode/mode-server/server/solicit-delay
                                        leaf solicit-delay {
                                            type int32 {
                                                range "1..100";
                                            }
                                            units "deciseconds";
                                            description "Delay before sending DHCPv6 Solicit messages";
                                        }

                                        ///nokia-conf/configure/service/vprn/subscriber-interface/ipv6/dhcp6/relay/advertise-selection/mode/mode-server/server/apply-groups
                                        leaf-list apply-groups {
                                            type leafref {
                                                path "../../../../../../../../../groups/group/name";
                                            }
                                            max-elements 8;
                                            ordered-by user;
                                            description "Apply a configuration group at this level";
                                        }

                                        ///nokia-conf/configure/service/vprn/subscriber-interface/ipv6/dhcp6/relay/advertise-selection/mode/mode-server/server/apply-groups-exclude
                                        leaf-list apply-groups-exclude {
                                            type leafref {
                                                path "../../../../../../../../../groups/group/name";
                                            }
                                            max-elements 8;
                                            ordered-by user;
                                            description "Exclude a configuration group at this level";
                                        }

                                        ///nokia-conf/configure/service/vprn/subscriber-interface/ipv6/dhcp6/relay/advertise-selection/mode/mode-server/server/preference-option
                                        container preference-option {
                                            description "Enter the preference-option context";

                                            ///nokia-conf/configure/service/vprn/subscriber-interface/ipv6/dhcp6/relay/advertise-selection/mode/mode-server/server/preference-option/value
                                            leaf value {
                                                type int32 {
                                                    range "0..255";
                                                }
                                                description "Preference option value for DHCPv6 Advertise messages";
                                            }

                                        } // container preference-option

                                    } // list server

                                }
                            }
                            ///nokia-conf/configure/service/vprn/subscriber-interface/ipv6/dhcp6/relay/advertise-selection/preference-option
                            container preference-option {
                                description "Enter the preference-option context";

                                ///nokia-conf/configure/service/vprn/subscriber-interface/ipv6/dhcp6/relay/advertise-selection/preference-option/value
                                leaf value {
                                    type int32 {
                                        range "0..255";
                                    }
                                    description "Preference option value for DHCPv6 Advertise messages";
                                }

                            } // container preference-option

                        } // container advertise-selection

                        ///nokia-conf/configure/service/vprn/subscriber-interface/ipv6/dhcp6/relay/lease-split
                        container lease-split {
                            description "Enter the lease-split context";

                            ///nokia-conf/configure/service/vprn/subscriber-interface/ipv6/dhcp6/relay/lease-split/admin-state
                            leaf admin-state {
                                type types-sros:admin-state;
                                default "disable";
                                description "Administrative state of DHCPv6 lease split";
                            }

                            ///nokia-conf/configure/service/vprn/subscriber-interface/ipv6/dhcp6/relay/lease-split/valid-lifetime
                            leaf valid-lifetime {
                                type types-submgt:dhcp6-prefix-lifetime-new;
                                default "3600";
                                description "DHCPv6 lease split valid lifetime (short lease time)";
                            }

                        } // container lease-split

                    } // container relay

                    ///nokia-conf/configure/service/vprn/subscriber-interface/ipv6/dhcp6/proxy-server
                    container proxy-server {
                        description "Enter the proxy-server context";

                        ///nokia-conf/configure/service/vprn/subscriber-interface/ipv6/dhcp6/proxy-server/admin-state
                        leaf admin-state {
                            type types-sros:admin-state;
                            default "disable";
                            description "Administrative state of the DHCPv6 proxy server";
                        }

                        ///nokia-conf/configure/service/vprn/subscriber-interface/ipv6/dhcp6/proxy-server/preferred-lifetime
                        leaf preferred-lifetime {
                            type types-submgt:dhcp6-prefix-lifetime;
                            default "3600";
                            description "Time for prefix to remain preferred on this interface";
                        }

                        ///nokia-conf/configure/service/vprn/subscriber-interface/ipv6/dhcp6/proxy-server/valid-lifetime
                        leaf valid-lifetime {
                            type types-submgt:dhcp6-prefix-lifetime;
                            default "86400";
                            description "Time for prefix to remain valid on this interface";
                        }

                        ///nokia-conf/configure/service/vprn/subscriber-interface/ipv6/dhcp6/proxy-server/renew-timer
                        leaf renew-timer {
                            type types-submgt:dhcp6-renew-timer;
                            description "Renew timer (T1)";
                        }

                        ///nokia-conf/configure/service/vprn/subscriber-interface/ipv6/dhcp6/proxy-server/rebind-timer
                        leaf rebind-timer {
                            type types-submgt:dhcp6-rebind-timer;
                            description "Rebind timer (T2) for this interface";
                        }

                        ///nokia-conf/configure/service/vprn/subscriber-interface/ipv6/dhcp6/proxy-server/client-applications
                        container client-applications {
                            description "Enter the client-applications context";

                            ///nokia-conf/configure/service/vprn/subscriber-interface/ipv6/dhcp6/proxy-server/client-applications/dhcp
                            leaf dhcp {
                                type boolean;
                                default "true";
                                description "Enable IPoE clients to use DHCP relay or proxy server";
                            }

                            ///nokia-conf/configure/service/vprn/subscriber-interface/ipv6/dhcp6/proxy-server/client-applications/ppp
                            leaf ppp {
                                type boolean;
                                default "false";
                                description "Allow PPPoE clients to use DHCP relay functionality";
                            }

                        } // container client-applications

                        ///nokia-conf/configure/service/vprn/subscriber-interface/ipv6/dhcp6/proxy-server/server-id
                        container server-id {
                            description "Enter the server-id context";

                            ///nokia-conf/configure/service/vprn/subscriber-interface/ipv6/dhcp6/proxy-server/server-id/apply-groups
                            leaf-list apply-groups {
                                type leafref {
                                    path "../../../../../../../../groups/group/name";
                                }
                                max-elements 8;
                                ordered-by user;
                                description "Apply a configuration group at this level";
                            }

                            ///nokia-conf/configure/service/vprn/subscriber-interface/ipv6/dhcp6/proxy-server/server-id/apply-groups-exclude
                            leaf-list apply-groups-exclude {
                                type leafref {
                                    path "../../../../../../../../groups/group/name";
                                }
                                max-elements 8;
                                ordered-by user;
                                description "Exclude a configuration group at this level";
                            }

                            ///nokia-conf/configure/service/vprn/subscriber-interface/ipv6/dhcp6/proxy-server/server-id/server-id
                            choice server-id {
                                default "duid-ll";
                                ///nokia-conf/configure/service/vprn/subscriber-interface/ipv6/dhcp6/proxy-server/server-id/server-id/duid-ll
                                case duid-ll {

                                    ///nokia-conf/configure/service/vprn/subscriber-interface/ipv6/dhcp6/proxy-server/server-id/server-id/duid-ll/duid-ll
                                    leaf duid-ll {
                                        type empty;
                                        description "Use link-layer address (DUID-LL) as DUID";
                                    }

                                }
                                ///nokia-conf/configure/service/vprn/subscriber-interface/ipv6/dhcp6/proxy-server/server-id/server-id/duid-en-hex
                                case duid-en-hex {

                                    ///nokia-conf/configure/service/vprn/subscriber-interface/ipv6/dhcp6/proxy-server/server-id/server-id/duid-en-hex/duid-en-hex
                                    leaf duid-en-hex {
                                        type string {
                                            length "1..118";
                                        }
                                        description "DUID system ID in hexadecimal format";
                                    }

                                }
                                ///nokia-conf/configure/service/vprn/subscriber-interface/ipv6/dhcp6/proxy-server/server-id/server-id/duid-en-ascii
                                case duid-en-ascii {

                                    ///nokia-conf/configure/service/vprn/subscriber-interface/ipv6/dhcp6/proxy-server/server-id/server-id/duid-en-ascii/duid-en-ascii
                                    leaf duid-en-ascii {
                                        type types-sros:string-not-all-spaces {
                                            length "1..58";
                                        }
                                        description "Vendor-assigned ID based on Enterprise Number (DUID-EN)";
                                    }

                                }
                            }
                        } // container server-id

                    } // container proxy-server

                } // container dhcp6

                ///nokia-conf/configure/service/vprn/subscriber-interface/ipv6/router-advertisements
                container router-advertisements {
                    when "../../fwd-service" {
                        description "fwd-service must be set";
                    }
                    description "Enter the router-advertisements context";

                    ///nokia-conf/configure/service/vprn/subscriber-interface/ipv6/router-advertisements/admin-state
                    leaf admin-state {
                        type types-sros:admin-state;
                        default "disable";
                        description "Administrative state of router advertisements";
                    }

                    ///nokia-conf/configure/service/vprn/subscriber-interface/ipv6/router-advertisements/max-advertisement-interval
                    leaf max-advertisement-interval {
                        type types-sros:time-duration {
                            range "900..1800";
                        }
                        units "seconds";
                        default "1800";
                        description "Maximum advertisement interval";
                    }

                    ///nokia-conf/configure/service/vprn/subscriber-interface/ipv6/router-advertisements/min-advertisement-interval
                    leaf min-advertisement-interval {
                        type types-sros:time-duration {
                            range "900..1350";
                        }
                        units "seconds";
                        default "900";
                        description "Minimum advertisement interval";
                    }

                    ///nokia-conf/configure/service/vprn/subscriber-interface/ipv6/router-advertisements/force-mcast
                    leaf force-mcast {
                        type enumeration {
                            enum ip                             { value 1; }
                            enum ip-mac                         { value 2; }
                        }
                        description "Protocol with forced multicast";
                    }

                    ///nokia-conf/configure/service/vprn/subscriber-interface/ipv6/router-advertisements/apply-groups
                    leaf-list apply-groups {
                        type leafref {
                            path "../../../../../../groups/group/name";
                        }
                        max-elements 8;
                        ordered-by user;
                        description "Apply a configuration group at this level";
                    }

                    ///nokia-conf/configure/service/vprn/subscriber-interface/ipv6/router-advertisements/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/ipv6/router-advertisements/options
                    container options {
                        description "Enter the options context";

                        ///nokia-conf/configure/service/vprn/subscriber-interface/ipv6/router-advertisements/options/current-hop-limit
                        leaf current-hop-limit {
                            type uint32 {
                                range "0..255";
                            }
                            default "64";
                            description "Hop limit to be advertised";
                        }

                        ///nokia-conf/configure/service/vprn/subscriber-interface/ipv6/router-advertisements/options/managed-configuration
                        leaf managed-configuration {
                            type boolean;
                            default "false";
                            description "Managed address configuration flag";
                        }

                        ///nokia-conf/configure/service/vprn/subscriber-interface/ipv6/router-advertisements/options/mtu
                        leaf mtu {
                            type union {
                                type uint32 {
                                    range "1280..9212";
                                }
                                type enumeration {
                                    enum not-included                   { value 0; }
                                }
                            }
                            units "bytes";
                            default "not-included";
                            description "Advertised MTU value";
                        }

                        ///nokia-conf/configure/service/vprn/subscriber-interface/ipv6/router-advertisements/options/other-stateful-configuration
                        leaf other-stateful-configuration {
                            type boolean;
                            default "false";
                            description "Other stateful configuration flag";
                        }

                        ///nokia-conf/configure/service/vprn/subscriber-interface/ipv6/router-advertisements/options/reachable-time
                        leaf reachable-time {
                            type types-sros:time-duration {
                                range "0..3600000";
                            }
                            units "milliseconds";
                            default "0";
                            description "Reachable time for advertisements";
                        }

                        ///nokia-conf/configure/service/vprn/subscriber-interface/ipv6/router-advertisements/options/retransmit-timer
                        leaf retransmit-timer {
                            type uint32 {
                                range "0..1800000";
                            }
                            units "seconds";
                            default "0";
                            description "Retransmit time in router advertisements from interface";
                        }

                        ///nokia-conf/configure/service/vprn/subscriber-interface/ipv6/router-advertisements/options/router-lifetime
                        leaf router-lifetime {
                            type union {
                                type types-sros:time-duration {
                                    range "2700..9000";
                                }
                                type enumeration {
                                    enum no-default-router              { value 0; }
                                }
                            }
                            units "seconds";
                            default "4500";
                            description "Router lifetime";
                        }

                        ///nokia-conf/configure/service/vprn/subscriber-interface/ipv6/router-advertisements/options/dns
                        container dns {
                            description "Enter the dns context";

                            ///nokia-conf/configure/service/vprn/subscriber-interface/ipv6/router-advertisements/options/dns/include-rdnss
                            leaf include-rdnss {
                                type boolean;
                                default "false";
                                description "Include the RDNSS server option 25";
                            }

                            ///nokia-conf/configure/service/vprn/subscriber-interface/ipv6/router-advertisements/options/dns/rdnss-lifetime
                            leaf rdnss-lifetime {
                                type union {
                                    type types-sros:time-duration {
                                        range "900..3600";
                                    }
                                    type enumeration {
                                        enum infinite                       { value -1; }
                                    }
                                }
                                units "seconds";
                                default "3600";
                                description "Maximum time for the RDNSS address to remain valid";
                            }

                        } // container dns

                    } // container options

                    ///nokia-conf/configure/service/vprn/subscriber-interface/ipv6/router-advertisements/prefix-options
                    container prefix-options {
                        description "Enter the prefix-options context";

                        ///nokia-conf/configure/service/vprn/subscriber-interface/ipv6/router-advertisements/prefix-options/autonomous
                        leaf autonomous {
                            type boolean;
                            default "false";
                            description "Value of the autonomous flag";
                        }

                        ///nokia-conf/configure/service/vprn/subscriber-interface/ipv6/router-advertisements/prefix-options/on-link
                        leaf on-link {
                            type boolean;
                            default "true";
                            description "Assign the prefix to an interface on the specified link";
                        }

                        ///nokia-conf/configure/service/vprn/subscriber-interface/ipv6/router-advertisements/prefix-options/preferred-lifetime
                        leaf preferred-lifetime {
                            type types-submgt:router-advertisement-prefix-options-lifetime;
                            units "seconds";
                            default "3600";
                            description "Time for a prefix to remain preferred";
                        }

                        ///nokia-conf/configure/service/vprn/subscriber-interface/ipv6/router-advertisements/prefix-options/valid-lifetime
                        leaf valid-lifetime {
                            type types-submgt:router-advertisement-prefix-options-lifetime;
                            units "seconds";
                            default "86400";
                            description "Time for a prefix to remain valid";
                        }

                    } // container prefix-options

                } // container router-advertisements

                ///nokia-conf/configure/service/vprn/subscriber-interface/ipv6/router-solicit
                container router-solicit {
                    when "../../fwd-service" {
                        description "fwd-service must be set";
                    }
                    description "Enable the router-solicit context";

                    ///nokia-conf/configure/service/vprn/subscriber-interface/ipv6/router-solicit/inactivity-timer
                    leaf inactivity-timer {
                        type union {
                            type types-sros:time-duration {
                                range "1..31536000";
                            }
                            type enumeration {
                                enum infinite                       { value -1; }
                            }
                        }
                        units "seconds";
                        default "300";
                        description "Time before an inactive host is removed";
                    }

                    ///nokia-conf/configure/service/vprn/subscriber-interface/ipv6/router-solicit/apply-groups
                    leaf-list apply-groups {
                        type leafref {
                            path "../../../../../../groups/group/name";
                        }
                        max-elements 8;
                        ordered-by user;
                        description "Apply a configuration group at this level";
                    }

                    ///nokia-conf/configure/service/vprn/subscriber-interface/ipv6/router-solicit/apply-groups-exclude
                    leaf-list apply-groups-exclude {
                        type leafref {
                            path "../../../../../../groups/group/name";
                        }
                        max-elements 8;
                        ordered-by user;
                        description "Exclude a configuration group at this level";
                    }

                } // container router-solicit

            } // container ipv6

            ///nokia-conf/configure/service/vprn/subscriber-interface/hold-time
            container hold-time {
                description "Enter the hold-time context";

                ///nokia-conf/configure/service/vprn/subscriber-interface/hold-time/ipv4
                container ipv4 {
                    description "Enter the ipv4 context";

                    ///nokia-conf/configure/service/vprn/subscriber-interface/hold-time/ipv4/up
                    container up {
                        description "Enter the up context";

                        ///nokia-conf/configure/service/vprn/subscriber-interface/hold-time/ipv4/up/seconds
                        leaf seconds {
                            type types-router:hold-time-seconds;
                            units "seconds";
                            description "Up hold time for the IP interface";
                        }

                    } // container up

                    ///nokia-conf/configure/service/vprn/subscriber-interface/hold-time/ipv4/down
                    container down {
                        description "Enter the down context";

                        ///nokia-conf/configure/service/vprn/subscriber-interface/hold-time/ipv4/down/seconds
                        leaf seconds {
                            type types-router:hold-time-seconds;
                            units "seconds";
                            description "Down hold time for the IP interface";
                        }

                        ///nokia-conf/configure/service/vprn/subscriber-interface/hold-time/ipv4/down/init-only
                        leaf init-only {
                            type boolean;
                            default "false";
                            description "Apply delay only at interface configuration or reboot";
                        }

                    } // container down

                } // container ipv4

                ///nokia-conf/configure/service/vprn/subscriber-interface/hold-time/ipv6
                container ipv6 {
                    description "Enter the ipv6 context";

                    ///nokia-conf/configure/service/vprn/subscriber-interface/hold-time/ipv6/up
                    container up {
                        description "Enter the up context";

                        ///nokia-conf/configure/service/vprn/subscriber-interface/hold-time/ipv6/up/seconds
                        leaf seconds {
                            type types-router:hold-time-seconds;
                            units "seconds";
                            description "Up hold time for the IP interface";
                        }

                    } // container up

                    ///nokia-conf/configure/service/vprn/subscriber-interface/hold-time/ipv6/down
                    container down {
                        description "Enter the down context";

                        ///nokia-conf/configure/service/vprn/subscriber-interface/hold-time/ipv6/down/seconds
                        leaf seconds {
                            type types-router:hold-time-seconds;
                            units "seconds";
                            description "Down hold time for the IP interface";
                        }

                        ///nokia-conf/configure/service/vprn/subscriber-interface/hold-time/ipv6/down/init-only
                        leaf init-only {
                            type boolean;
                            default "false";
                            description "Apply delay only at interface configuration or reboot";
                        }

                    } // container down

                } // container ipv6

            } // container hold-time

            ///nokia-conf/configure/service/vprn/subscriber-interface/ipoe-linking
            container ipoe-linking {
                when "../fwd-service" {
                    description "fwd-service must be set";
                }
                description "Enter the ipoe-linking context";

                ///nokia-conf/configure/service/vprn/subscriber-interface/ipoe-linking/gratuitous-router-advertisement
                leaf gratuitous-router-advertisement {
                    type boolean;
                    default "false";
                    description "Send unsolicited router advertisement after DHCP setup";
                }

                ///nokia-conf/configure/service/vprn/subscriber-interface/ipoe-linking/apply-groups
                leaf-list apply-groups {
                    type leafref {
                        path "../../../../../groups/group/name";
                    }
                    max-elements 8;
                    ordered-by user;
                    description "Apply a configuration group at this level";
                }

                ///nokia-conf/configure/service/vprn/subscriber-interface/ipoe-linking/apply-groups-exclude
                leaf-list apply-groups-exclude {
                    type leafref {
                        path "../../../../../groups/group/name";
                    }
                    max-elements 8;
                    ordered-by user;
                    description "Exclude a configuration group at this level";
                }

            } // container ipoe-linking

            ///nokia-conf/configure/service/vprn/subscriber-interface/ipoe-session
            container ipoe-session {
                when "../fwd-service" {
                    description "fwd-service must be set";
                }
                description "Enable the ipoe-session context";

                ///nokia-conf/configure/service/vprn/subscriber-interface/ipoe-session/session-limit
                leaf session-limit {
                    type uint32 {
                        range "1..500000";
                    }
                    description "Maximum number of sessions on this group interface";
                }

                ///nokia-conf/configure/service/vprn/subscriber-interface/ipoe-session/apply-groups
                leaf-list apply-groups {
                    type leafref {
                        path "../../../../../groups/group/name";
                    }
                    max-elements 8;
                    ordered-by user;
                    description "Apply a configuration group at this level";
                }

                ///nokia-conf/configure/service/vprn/subscriber-interface/ipoe-session/apply-groups-exclude
                leaf-list apply-groups-exclude {
                    type leafref {
                        path "../../../../../groups/group/name";
                    }
                    max-elements 8;
                    ordered-by user;
                    description "Exclude a configuration group at this level";
                }

            } // container ipoe-session

            ///nokia-conf/configure/service/vprn/subscriber-interface/pppoe
            container pppoe {
                when "../fwd-service" {
                    description "fwd-service must be set";
                }
                description "Enable the pppoe context";

                ///nokia-conf/configure/service/vprn/subscriber-interface/pppoe/description
                leaf description {
                    type types-sros:description;
                    description "Text description";
                }

                ///nokia-conf/configure/service/vprn/subscriber-interface/pppoe/session-limit
                leaf session-limit {
                    type uint32 {
                        range "1..333823";
                    }
                    default "1";
                    description "Maximum PPPoE sessions";
                }

                ///nokia-conf/configure/service/vprn/subscriber-interface/pppoe/apply-groups
                leaf-list apply-groups {
                    type leafref {
                        path "../../../../../groups/group/name";
                    }
                    max-elements 8;
                    ordered-by user;
                    description "Apply a configuration group at this level";
                }

                ///nokia-conf/configure/service/vprn/subscriber-interface/pppoe/apply-groups-exclude
                leaf-list apply-groups-exclude {
                    type leafref {
                        path "../../../../../groups/group/name";
                    }
                    max-elements 8;
                    ordered-by user;
                    description "Exclude a configuration group at this level";
                }

            } // container pppoe

            ///nokia-conf/configure/service/vprn/subscriber-interface/local-address-assignment
            container local-address-assignment {
                when "../fwd-service" {
                    description "fwd-service must be set";
                }
                description "Enter the local-address-assignment context";

                ///nokia-conf/configure/service/vprn/subscriber-interface/local-address-assignment/admin-state
                leaf admin-state {
                    type types-sros:admin-state;
                    default "disable";
                    description "Administrative state of Local Address Assignment";
                }

                ///nokia-conf/configure/service/vprn/subscriber-interface/local-address-assignment/apply-groups
                leaf-list apply-groups {
                    type leafref {
                        path "../../../../../groups/group/name";
                    }
                    max-elements 8;
                    ordered-by user;
                    description "Apply a configuration group at this level";
                }

                ///nokia-conf/configure/service/vprn/subscriber-interface/local-address-assignment/apply-groups-exclude
                leaf-list apply-groups-exclude {
                    type leafref {
                        path "../../../../../groups/group/name";
                    }
                    max-elements 8;
                    ordered-by user;
                    description "Exclude a configuration group at this level";
                }

                ///nokia-conf/configure/service/vprn/subscriber-interface/local-address-assignment/ipv4
                container ipv4 {
                    description "Enter the ipv4 context";

                    ///nokia-conf/configure/service/vprn/subscriber-interface/local-address-assignment/ipv4/server
                    leaf server {
                        type leafref {
                            path "../../../../dhcp-server/dhcpv4/name";
                        }
                        description "Local DHCPv4 server for local pools management";
                    }

                    ///nokia-conf/configure/service/vprn/subscriber-interface/local-address-assignment/ipv4/default-pool
                    leaf-list default-pool {
                        type types-sros:named-item;
                        max-elements 2;
                        ordered-by user;
                        description "Default pools";
                    }

                    ///nokia-conf/configure/service/vprn/subscriber-interface/local-address-assignment/ipv4/client-applications
                    container client-applications {
                        description "Enter the client-applications context";

                        ///nokia-conf/configure/service/vprn/subscriber-interface/local-address-assignment/ipv4/client-applications/ppp
                        leaf ppp {
                            type boolean;
                            default "false";
                            description "Request local addresses for PPP IPCP hosts";
                        }

                    } // container client-applications

                } // container ipv4

                ///nokia-conf/configure/service/vprn/subscriber-interface/local-address-assignment/ipv6
                container ipv6 {
                    description "Enter the ipv6 context";

                    ///nokia-conf/configure/service/vprn/subscriber-interface/local-address-assignment/ipv6/server
                    leaf server {
                        type leafref {
                            path "../../../../dhcp-server/dhcpv6/name";
                        }
                        description "Local DHCPv6 server for local pools management";
                    }

                    ///nokia-conf/configure/service/vprn/subscriber-interface/local-address-assignment/ipv6/client-applications
                    container client-applications {
                        description "Enter the client-applications context";

                        ///nokia-conf/configure/service/vprn/subscriber-interface/local-address-assignment/ipv6/client-applications/ppp-slaac
                        leaf ppp-slaac {
                            type boolean;
                            default "false";
                            description "Request local addresses for PPP SLAAC hosts";
                        }

                        ///nokia-conf/configure/service/vprn/subscriber-interface/local-address-assignment/ipv6/client-applications/ipoe-wan
                        leaf ipoe-wan {
                            type boolean;
                            default "false";
                            description "Request local addresses for IPoE IA NA hosts";
                        }

                        ///nokia-conf/configure/service/vprn/subscriber-interface/local-address-assignment/ipv6/client-applications/ipoe-slaac
                        leaf ipoe-slaac {
                            type boolean;
                            default "false";
                            description "Request local addresses for IPoE SLAAC hosts";
                        }

                    } // container client-applications

                } // container ipv6

            } // container local-address-assignment

            ///nokia-conf/configure/service/vprn/subscriber-interface/group-interface
            list group-interface {
                when "not(../fwd-service)" {
                    description "fwd-service must be unset";
                }
                key "group-interface-name";
                description "Enter the group-interface list instance";

                ///nokia-conf/configure/service/vprn/subscriber-interface/group-interface/group-interface-name
                leaf group-interface-name {
                    type types-sros:interface-name;
                    description "Group interface name";
                }

                ///nokia-conf/configure/service/vprn/subscriber-interface/group-interface/admin-state
                leaf admin-state {
                    type types-sros:admin-state;
                    default "enable";
                    description "Administrative state of the interface";
                }

                ///nokia-conf/configure/service/vprn/subscriber-interface/group-interface/description
                leaf description {
                    type types-sros:very-long-description;
                    description "Text description";
                }

                ///nokia-conf/configure/service/vprn/subscriber-interface/group-interface/type
                leaf type {
                    type types-services:group-interface-type;
                    sros-ext:immutable;
                    default "plain";
                    description "Group interface type";
                }

                ///nokia-conf/configure/service/vprn/subscriber-interface/group-interface/radius-auth-policy
                leaf radius-auth-policy {
                    type leafref {
                        path "../../../../../subscriber-mgmt/radius-authentication-policy/name";
                    }
                    description "RADIUS authentication policy";
                }

                ///nokia-conf/configure/service/vprn/subscriber-interface/group-interface/gx-policy
                leaf gx-policy {
                    when "../type = 'plain' or ../type = 'lns' or ../type = 'wlan-gw' or ../type = 'gtp'" {
                        description "invalid group interface type";
                    }
                    type leafref {
                        path "../../../../../subscriber-mgmt/diameter-gx-policy/name";
                    }
                    description "Diameter application policy";
                }

                ///nokia-conf/configure/service/vprn/subscriber-interface/group-interface/nasreq-auth-policy
                leaf nasreq-auth-policy {
                    when "../type = 'plain'" {
                        description "group interface type must be 'plain'";
                    }
                    type leafref {
                        path "../../../../../subscriber-mgmt/diameter-nasreq-policy/name";
                    }
                    description "Diameter NASREQ application policy to use for authentication";
                }

                ///nokia-conf/configure/service/vprn/subscriber-interface/group-interface/ingress-stats
                leaf ingress-stats {
                    type boolean;
                    default "false";
                    description "Collect ingress interface statistics";
                }

                ///nokia-conf/configure/service/vprn/subscriber-interface/group-interface/ip-mtu
                leaf ip-mtu {
                    when "not(../type = 'bonding')" {
                        description "group interface type must not be 'bonding'";
                    }
                    type types-router:ip-mtu-ext;
                    units "bytes";
                    description "Interface IP MTU";
                }

                ///nokia-conf/configure/service/vprn/subscriber-interface/group-interface/mac
                leaf mac {
                    when "not(../type = 'wlan-gw') and not(../type = 'gtp') and not(../type = 'bonding')" {
                        description "invalid group interface type";
                    }
                    type types-sros:mac-unicast-address;
                    description "MAC address for the interface";
                }

                ///nokia-conf/configure/service/vprn/subscriber-interface/group-interface/oper-up-while-empty
                leaf oper-up-while-empty {
                    when "../type = 'plain' or ../type = 'lns'" {
                        description "invalid group interface type";
                    }
                    type boolean;
                    default "false";
                    description "Enable this group interface without any active SAPs";
                }

                ///nokia-conf/configure/service/vprn/subscriber-interface/group-interface/redundant-interface
                leaf redundant-interface {
                    when "../type = 'plain' or ../type = 'lns'" {
                        description "invalid group interface type";
                    }
                    type leafref {
                        path "../../../redundant-interface/interface-name";
                    }
                    description "Redundant interface";
                }

                ///nokia-conf/configure/service/vprn/subscriber-interface/group-interface/shcv-policy
                leaf shcv-policy {
                    when "../type = 'plain' or ../type = 'lns' or ../type = 'wlan-gw'" {
                        description "invalid group interface type";
                    }
                    type leafref {
                        path "../../../../../subscriber-mgmt/shcv-policy/name";
                    }
                    description "SHCV policy for IPv4 and IPv6 subscriber hosts";
                }

                ///nokia-conf/configure/service/vprn/subscriber-interface/group-interface/shcv-policy-ipv4
                leaf shcv-policy-ipv4 {
                    when "../type = 'plain' or ../type = 'lns' or ../type = 'wlan-gw'" {
                        description "invalid group interface type";
                    }
                    type leafref {
                        path "../../../../../subscriber-mgmt/shcv-policy/name";
                    }
                    description "SHCV for IPv4 subscriber hosts";
                }

                ///nokia-conf/configure/service/vprn/subscriber-interface/group-interface/shcv-policy-ipv6
                leaf shcv-policy-ipv6 {
                    when "../type = 'plain' or ../type = 'lns' or ../type = 'wlan-gw'" {
                        description "invalid group interface type";
                    }
                    type leafref {
                        path "../../../../../subscriber-mgmt/shcv-policy/name";
                    }
                    description "SHCV for IPv6 subscriber hosts";
                }

                ///nokia-conf/configure/service/vprn/subscriber-interface/group-interface/suppress-aa-sub
                leaf suppress-aa-sub {
                    type boolean;
                    default "false";
                    description "Enable application assurance suppression for ESM subscribers";
                }

                ///nokia-conf/configure/service/vprn/subscriber-interface/group-interface/tos-marking-state
                leaf tos-marking-state {
                    type types-router:tos-marking-state;
                    default "trusted";
                    description "TOS marking state";
                }

                ///nokia-conf/configure/service/vprn/subscriber-interface/group-interface/apply-groups
                leaf-list apply-groups {
                    type leafref {
                        path "../../../../../groups/group/name";
                    }
                    max-elements 8;
                    ordered-by user;
                    description "Apply a configuration group at this level";
                }

                ///nokia-conf/configure/service/vprn/subscriber-interface/group-interface/apply-groups-exclude
                leaf-list apply-groups-exclude {
                    type leafref {
                        path "../../../../../groups/group/name";
                    }
                    max-elements 8;
                    ordered-by user;
                    description "Exclude a configuration group at this level";
                }

                ///nokia-conf/configure/service/vprn/subscriber-interface/group-interface/ingress
                container ingress {
                    description "Enter the ingress context";

                    ///nokia-conf/configure/service/vprn/subscriber-interface/group-interface/ingress/policy-accounting
                    leaf policy-accounting {
                        type leafref {
                            path "../../../../../../routing-options/policy-accounting/policy-acct-template/name";
                        }
                        description "Ingress policy accounting template name";
                    }

                } // container ingress

                ///nokia-conf/configure/service/vprn/subscriber-interface/group-interface/dynamic-routes-track-srrp
                container dynamic-routes-track-srrp {
                    when "../type = 'plain' or ../type = 'lns'" {
                        description "invalid group interface type";
                    }
                    presence "Enable the dynamic-routes-track-srrp context";
                    description "Enable the dynamic-routes-track-srrp context";

                    ///nokia-conf/configure/service/vprn/subscriber-interface/group-interface/dynamic-routes-track-srrp/hold-time
                    leaf hold-time {
                        type uint32 {
                            range "1..50";
                        }
                        units "deciseconds";
                        description "Time before route state updated after SRRP transition";
                    }

                } // container dynamic-routes-track-srrp

                ///nokia-conf/configure/service/vprn/subscriber-interface/group-interface/ipv4
                container ipv4 {
                    description "Enter the ipv4 context";

                    ///nokia-conf/configure/service/vprn/subscriber-interface/group-interface/ipv4/qos-route-lookup
                    leaf qos-route-lookup {
                        type types-router:qos-route-lookup-grp-if;
                        description "QoS route lookup";
                    }

                    ///nokia-conf/configure/service/vprn/subscriber-interface/group-interface/ipv4/ignore-df-bit
                    leaf ignore-df-bit {
                        when "../../type = 'wlan-gw'" {
                            description "group interface type must be 'wlan-gw'";
                        }
                        type boolean;
                        default "false";
                        description "Ignore DF bit in the IPv4 header when fragmenting";
                    }

                    ///nokia-conf/configure/service/vprn/subscriber-interface/group-interface/ipv4/icmp
                    container icmp {
                        description "Enter the icmp context";

                        ///nokia-conf/configure/service/vprn/subscriber-interface/group-interface/ipv4/icmp/mask-reply
                        leaf mask-reply {
                            type boolean;
                            default "true";
                            description "Allow responses to ICMP mask requests on the interface";
                        }

                        ///nokia-conf/configure/service/vprn/subscriber-interface/group-interface/ipv4/icmp/redirects
                        container redirects {
                            description "Enter the redirects context";

                            ///nokia-conf/configure/service/vprn/subscriber-interface/group-interface/ipv4/icmp/redirects/admin-state
                            leaf admin-state {
                                type types-sros:admin-state;
                                default "enable";
                                description "Administrative state of sending ICMP redirect messages";
                            }

                            ///nokia-conf/configure/service/vprn/subscriber-interface/group-interface/ipv4/icmp/redirects/number
                            leaf number {
                                type uint16 {
                                    range "10..1000";
                                }
                                default "100";
                                description "Maximum number of ICMP redirect messages to send";
                            }

                            ///nokia-conf/configure/service/vprn/subscriber-interface/group-interface/ipv4/icmp/redirects/seconds
                            leaf seconds {
                                type uint16 {
                                    range "1..60";
                                }
                                units "seconds";
                                default "10";
                                description "Time used to limit the number of ICMP redirect messages";
                            }

                        } // container redirects

                        ///nokia-conf/configure/service/vprn/subscriber-interface/group-interface/ipv4/icmp/ttl-expired
                        container ttl-expired {
                            description "Enter the ttl-expired context";

                            ///nokia-conf/configure/service/vprn/subscriber-interface/group-interface/ipv4/icmp/ttl-expired/admin-state
                            leaf admin-state {
                                type types-sros:admin-state;
                                default "enable";
                                description "Administrative state of sending TTL expired messages";
                            }

                            ///nokia-conf/configure/service/vprn/subscriber-interface/group-interface/ipv4/icmp/ttl-expired/number
                            leaf number {
                                type uint16 {
                                    range "10..2000";
                                }
                                default "100";
                                description "Maximum number of TTL expired messages to send";
                            }

                            ///nokia-conf/configure/service/vprn/subscriber-interface/group-interface/ipv4/icmp/ttl-expired/seconds
                            leaf seconds {
                                type uint16 {
                                    range "1..60";
                                }
                                units "seconds";
                                default "10";
                                description "Time used to limit the number of TTL expired messages";
                            }

                            ///nokia-conf/configure/service/vprn/subscriber-interface/group-interface/ipv4/icmp/ttl-expired/use-matching-address
                            leaf use-matching-address {
                                type boolean;
                                default "false";
                                description "Use the subscriber interface address as source address";
                            }

                        } // container ttl-expired

                        ///nokia-conf/configure/service/vprn/subscriber-interface/group-interface/ipv4/icmp/unreachables
                        container unreachables {
                            description "Enter the unreachables context";

                            ///nokia-conf/configure/service/vprn/subscriber-interface/group-interface/ipv4/icmp/unreachables/admin-state
                            leaf admin-state {
                                type types-sros:admin-state;
                                default "enable";
                                description "Administrative state of sending unreachable messages";
                            }

                            ///nokia-conf/configure/service/vprn/subscriber-interface/group-interface/ipv4/icmp/unreachables/number
                            leaf number {
                                type uint16 {
                                    range "10..2000";
                                }
                                default "100";
                                description "Maximum number of unreachable messages to send";
                            }

                            ///nokia-conf/configure/service/vprn/subscriber-interface/group-interface/ipv4/icmp/unreachables/seconds
                            leaf seconds {
                                type uint16 {
                                    range "1..60";
                                }
                                units "seconds";
                                default "10";
                                description "Time to limit the number of ICMP unreachable messages";
                            }

                        } // container unreachables

                        ///nokia-conf/configure/service/vprn/subscriber-interface/group-interface/ipv4/icmp/param-problem
                        container param-problem {
                            description "Enter the param-problem context";

                            ///nokia-conf/configure/service/vprn/subscriber-interface/group-interface/ipv4/icmp/param-problem/admin-state
                            leaf admin-state {
                                type types-sros:admin-state;
                                default "enable";
                                description "Administrative state of sent Parameter Problem messages";
                            }

                            ///nokia-conf/configure/service/vprn/subscriber-interface/group-interface/ipv4/icmp/param-problem/number
                            leaf number {
                                type uint32 {
                                    range "10..1000";
                                }
                                default "100";
                                description "Maximum number of Parameter Problem messages to send";
                            }

                            ///nokia-conf/configure/service/vprn/subscriber-interface/group-interface/ipv4/icmp/param-problem/seconds
                            leaf seconds {
                                type uint32 {
                                    range "1..60";
                                }
                                units "seconds";
                                default "10";
                                description "Time used to limit number of Parameter Problem messages";
                            }

                        } // container param-problem

                    } // container icmp

                    ///nokia-conf/configure/service/vprn/subscriber-interface/group-interface/ipv4/urpf-check
                    container urpf-check {
                        when "not(../../type = 'bonding')" {
                            description "group interface type must not be 'bonding'";
                        }
                        presence "Enable the urpf-check context";
                        description "Enable the urpf-check context";

                        ///nokia-conf/configure/service/vprn/subscriber-interface/group-interface/ipv4/urpf-check/mode
                        leaf mode {
                            type types-router:urpf-check-mode;
                            default "strict";
                            description "Unicast RPF check mode";
                        }

                    } // container urpf-check

                    ///nokia-conf/configure/service/vprn/subscriber-interface/group-interface/ipv4/arp-host
                    container arp-host {
                        when "../../type = 'plain' or ../../type = 'lns'" {
                            description "invalid group interface type";
                        }
                        description "Enable the arp-host context";

                        ///nokia-conf/configure/service/vprn/subscriber-interface/group-interface/ipv4/arp-host/admin-state
                        leaf admin-state {
                            type types-sros:admin-state;
                            description "Administrative state of ARP hosts";
                        }

                        ///nokia-conf/configure/service/vprn/subscriber-interface/group-interface/ipv4/arp-host/host-limit
                        leaf host-limit {
                            type uint32 {
                                range "1..524287";
                            }
                            description "Maximum number of ARP hosts";
                        }

                        ///nokia-conf/configure/service/vprn/subscriber-interface/group-interface/ipv4/arp-host/sap-host-limit
                        leaf sap-host-limit {
                            type uint32 {
                                range "1..131071";
                            }
                            default "1";
                            description "Maximum number of ARP hosts per SAP";
                        }

                        ///nokia-conf/configure/service/vprn/subscriber-interface/group-interface/ipv4/arp-host/min-auth-interval
                        leaf min-auth-interval {
                            type types-sros:time-duration {
                                range "1..6000";
                            }
                            units "minutes";
                            default "15";
                            description "Minimum authentication interval";
                        }

                        ///nokia-conf/configure/service/vprn/subscriber-interface/group-interface/ipv4/arp-host/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv4/arp-host/apply-groups-exclude
                        leaf-list apply-groups-exclude {
                            type leafref {
                                path "../../../../../../../groups/group/name";
                            }
                            max-elements 8;
                            ordered-by user;
                            description "Exclude a configuration group at this level";
                        }

                    } // container arp-host

                    ///nokia-conf/configure/service/vprn/subscriber-interface/group-interface/ipv4/neighbor-discovery
                    container neighbor-discovery {
                        when "../../type = 'plain' or ../../type = 'lns' or ../../type = 'wlan-gw'" {
                            description "invalid group interface type";
                        }
                        description "Enter the neighbor-discovery context";

                        ///nokia-conf/configure/service/vprn/subscriber-interface/group-interface/ipv4/neighbor-discovery/local-proxy-arp
                        leaf local-proxy-arp {
                            type boolean;
                            description "Enable local proxy ARP on interface";
                        }

                        ///nokia-conf/configure/service/vprn/subscriber-interface/group-interface/ipv4/neighbor-discovery/remote-proxy-arp
                        leaf remote-proxy-arp {
                            type boolean;
                            default "false";
                            description "Enable remote proxy ARP on the interface";
                        }

                        ///nokia-conf/configure/service/vprn/subscriber-interface/group-interface/ipv4/neighbor-discovery/proxy-arp-policy
                        leaf-list proxy-arp-policy {
                            type leafref {
                                path "../../../../../../../policy-options/policy-statement/name";
                            }
                            max-elements 5;
                            ordered-by user;
                            description "Proxy ARP policy name";
                        }

                        ///nokia-conf/configure/service/vprn/subscriber-interface/group-interface/ipv4/neighbor-discovery/populate
                        leaf populate {
                            when "../../../type = 'plain' or ../../../type = 'lns'" {
                                description "invalid group interface type";
                            }
                            type boolean;
                            description "Allow population of static and dynamic hosts";
                        }

                        ///nokia-conf/configure/service/vprn/subscriber-interface/group-interface/ipv4/neighbor-discovery/timeout
                        leaf timeout {
                            when "../../../type = 'plain' or ../../../type = 'lns'" {
                                description "invalid group interface type";
                            }
                            type uint32 {
                                range "0..65535";
                            }
                            units "seconds";
                            default "14400";
                            description "Timeout for an ARP entry learned on the interface";
                        }

                    } // container neighbor-discovery

                    ///nokia-conf/configure/service/vprn/subscriber-interface/group-interface/ipv4/bfd
                    container bfd {
                        description "Enter the bfd context";

                        ///nokia-conf/configure/service/vprn/subscriber-interface/group-interface/ipv4/bfd/admin-state
                        leaf admin-state {
                            type types-sros:admin-state;
                            default "disable";
                            description "Administrative state of BFD sessions";
                        }

                        ///nokia-conf/configure/service/vprn/subscriber-interface/group-interface/ipv4/bfd/transmit-interval
                        leaf transmit-interval {
                            type uint32 {
                                range "10..100000";
                            }
                            units "milliseconds";
                            default "100";
                            description "BFD transmit interval over this interface";
                        }

                        ///nokia-conf/configure/service/vprn/subscriber-interface/group-interface/ipv4/bfd/receive
                        leaf receive {
                            type uint32 {
                                range "10..100000";
                            }
                            units "milliseconds";
                            default "100";
                            description "BFD receive interval over this interface";
                        }

                        ///nokia-conf/configure/service/vprn/subscriber-interface/group-interface/ipv4/bfd/multiplier
                        leaf multiplier {
                            type uint32 {
                                range "1..20";
                            }
                            default "3";
                            description "Number of consecutive BFD messages missed from the peer";
                        }

                        ///nokia-conf/configure/service/vprn/subscriber-interface/group-interface/ipv4/bfd/echo-receive
                        leaf echo-receive {
                            type uint32 {
                                range "100..100000";
                            }
                            units "milliseconds";
                            description "Minimum echo interval over this interface";
                        }

                        ///nokia-conf/configure/service/vprn/subscriber-interface/group-interface/ipv4/bfd/type
                        leaf type {
                            type enumeration {
                                enum cpm-np                         { value 1; }
                                enum auto                           { value 2; }
                                enum fp                             { value 3; }
                            }
                            default "auto";
                            description "Local termination point for the BFD session";
                        }

                    } // container bfd

                    ///nokia-conf/configure/service/vprn/subscriber-interface/group-interface/ipv4/dhcp
                    container dhcp {
                        when "../../type = 'plain' or ../../type = 'lns' or ../../type = 'wlan-gw' or ../../type = 'gtp'" {
                            description "invalid group interface type";
                        }
                        description "Enable the dhcp context";

                        ///nokia-conf/configure/service/vprn/subscriber-interface/group-interface/ipv4/dhcp/admin-state
                        leaf admin-state {
                            type types-sros:admin-state;
                            description "Administrative state of DHCP";
                        }

                        ///nokia-conf/configure/service/vprn/subscriber-interface/group-interface/ipv4/dhcp/description
                        leaf description {
                            type types-sros:description;
                            description "Text description";
                        }

                        ///nokia-conf/configure/service/vprn/subscriber-interface/group-interface/ipv4/dhcp/filter
                        leaf filter {
                            type leafref {
                                path "../../../../../../../filter/dhcp-filter/filter-id";
                            }
                            description "DHCP filter ID for the group interface";
                        }

                        ///nokia-conf/configure/service/vprn/subscriber-interface/group-interface/ipv4/dhcp/python-policy
                        leaf python-policy {
                            type leafref {
                                path "../../../../../../../python/python-policy/name";
                            }
                            description "Python policy name";
                        }

                        ///nokia-conf/configure/service/vprn/subscriber-interface/group-interface/ipv4/dhcp/server
                        leaf-list server {
                            type types-sros:ipv4-unicast-address;
                            max-elements 8;
                            ordered-by user;
                            description "IP addresses for DHCP server requests";
                        }

                        ///nokia-conf/configure/service/vprn/subscriber-interface/group-interface/ipv4/dhcp/trusted
                        leaf trusted {
                            type boolean;
                            default "false";
                            description "Relay untrusted packets";
                        }

                        ///nokia-conf/configure/service/vprn/subscriber-interface/group-interface/ipv4/dhcp/gi-address
                        leaf gi-address {
                            type types-sros:ipv4-unicast-address;
                            description "GI address for the DHCP relay";
                        }

                        ///nokia-conf/configure/service/vprn/subscriber-interface/group-interface/ipv4/dhcp/release-include-gi-address
                        leaf release-include-gi-address {
                            type boolean;
                            default "false";
                            description "Include gateway IP address in DHCP Release messages";
                        }

                        ///nokia-conf/configure/service/vprn/subscriber-interface/group-interface/ipv4/dhcp/src-ip-addr
                        leaf src-ip-addr {
                            type enumeration {
                                enum auto                           { value 0; }
                                enum gi-address                     { value 1; }
                            }
                            default "auto";
                            description "Type of source address to use for DHCP relay";
                        }

                        ///nokia-conf/configure/service/vprn/subscriber-interface/group-interface/ipv4/dhcp/match-circuit-id
                        leaf match-circuit-id {
                            when "not(../../../type = 'gtp')" {
                                description "group interface type must not be 'gtp'";
                            }
                            type boolean;
                            default "false";
                            description "Enable Option 82 circuit ID on relayed DHCP packets";
                        }

                        ///nokia-conf/configure/service/vprn/subscriber-interface/group-interface/ipv4/dhcp/user-db
                        leaf user-db {
                            when "not(../../../type = 'gtp')" {
                                description "group interface type must not be 'gtp'";
                            }
                            type leafref {
                                path "../../../../../../../subscriber-mgmt/local-user-db/name";
                            }
                            sros-ext:auto-restart-to-modify;
                            description "Local user database for authentication";
                        }

                        ///nokia-conf/configure/service/vprn/subscriber-interface/group-interface/ipv4/dhcp/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv4/dhcp/apply-groups-exclude
                        leaf-list apply-groups-exclude {
                            type leafref {
                                path "../../../../../../../groups/group/name";
                            }
                            max-elements 8;
                            ordered-by user;
                            description "Exclude a configuration group at this level";
                        }

                        ///nokia-conf/configure/service/vprn/subscriber-interface/group-interface/ipv4/dhcp/proxy-server
                        container proxy-server {
                            description "Enter the proxy-server context";

                            ///nokia-conf/configure/service/vprn/subscriber-interface/group-interface/ipv4/dhcp/proxy-server/admin-state
                            leaf admin-state {
                                type types-sros:admin-state;
                                default "disable";
                                description "Administrative state of the DHCP proxy server";
                            }

                            ///nokia-conf/configure/service/vprn/subscriber-interface/group-interface/ipv4/dhcp/proxy-server/emulated-server
                            leaf emulated-server {
                                type types-sros:ipv4-unicast-address;
                                description "IP address used as DHCP server address in SAP context";
                            }

                            ///nokia-conf/configure/service/vprn/subscriber-interface/group-interface/ipv4/dhcp/proxy-server/lease-time
                            container lease-time {
                                description "Enter the lease-time context";

                                ///nokia-conf/configure/service/vprn/subscriber-interface/group-interface/ipv4/dhcp/proxy-server/lease-time/value
                                leaf value {
                                    type types-sros:time-duration {
                                        range "300..315446399";
                                    }
                                    units "seconds";
                                    description "DHCP lease time";
                                }

                                ///nokia-conf/configure/service/vprn/subscriber-interface/group-interface/ipv4/dhcp/proxy-server/lease-time/radius-override
                                leaf radius-override {
                                    type boolean;
                                    default "false";
                                    description "Use lease time information provided by RADIUS server";
                                }

                            } // container lease-time

                        } // container proxy-server

                        ///nokia-conf/configure/service/vprn/subscriber-interface/group-interface/ipv4/dhcp/option-82
                        container option-82 {
                            description "Enter the option-82 context";

                            ///nokia-conf/configure/service/vprn/subscriber-interface/group-interface/ipv4/dhcp/option-82/action
                            leaf action {
                                type enumeration {
                                    enum replace                        { value 1; }
                                    enum drop                           { value 2; }
                                    enum keep                           { value 3; }
                                }
                                default "keep";
                                description "Action to take with received DHCP Option 82";
                            }

                            ///nokia-conf/configure/service/vprn/subscriber-interface/group-interface/ipv4/dhcp/option-82/circuit-id
                            container circuit-id {
                                description "Enter the circuit-id context";

                                ///nokia-conf/configure/service/vprn/subscriber-interface/group-interface/ipv4/dhcp/option-82/circuit-id/circuit-id
                                choice circuit-id {
                                    default "ascii-tuple";
                                    ///nokia-conf/configure/service/vprn/subscriber-interface/group-interface/ipv4/dhcp/option-82/circuit-id/circuit-id/none
                                    case none {

                                        ///nokia-conf/configure/service/vprn/subscriber-interface/group-interface/ipv4/dhcp/option-82/circuit-id/circuit-id/none/none
                                        leaf none {
                                            type empty;
                                            description "Do not include the circuit ID";
                                        }

                                    }
                                    ///nokia-conf/configure/service/vprn/subscriber-interface/group-interface/ipv4/dhcp/option-82/circuit-id/circuit-id/ifindex
                                    case ifindex {

                                        ///nokia-conf/configure/service/vprn/subscriber-interface/group-interface/ipv4/dhcp/option-82/circuit-id/circuit-id/ifindex/ifindex
                                        leaf ifindex {
                                            type empty;
                                            description "Use the interface index for the circuit ID";
                                        }

                                    }
                                    ///nokia-conf/configure/service/vprn/subscriber-interface/group-interface/ipv4/dhcp/option-82/circuit-id/circuit-id/ascii-tuple
                                    case ascii-tuple {

                                        ///nokia-conf/configure/service/vprn/subscriber-interface/group-interface/ipv4/dhcp/option-82/circuit-id/circuit-id/ascii-tuple/ascii-tuple
                                        leaf ascii-tuple {
                                            type empty;
                                            description "Use the ASCII-encoded tuple for the circuit ID";
                                        }

                                    }
                                    ///nokia-conf/configure/service/vprn/subscriber-interface/group-interface/ipv4/dhcp/option-82/circuit-id/circuit-id/sap-id
                                    case sap-id {

                                        ///nokia-conf/configure/service/vprn/subscriber-interface/group-interface/ipv4/dhcp/option-82/circuit-id/circuit-id/sap-id/sap-id
                                        leaf sap-id {
                                            type empty;
                                            description "Use the SAP ID";
                                        }

                                    }
                                    ///nokia-conf/configure/service/vprn/subscriber-interface/group-interface/ipv4/dhcp/option-82/circuit-id/circuit-id/vlan-ascii-tuple
                                    case vlan-ascii-tuple {

                                        ///nokia-conf/configure/service/vprn/subscriber-interface/group-interface/ipv4/dhcp/option-82/circuit-id/circuit-id/vlan-ascii-tuple/vlan-ascii-tuple
                                        leaf vlan-ascii-tuple {
                                            type empty;
                                            description "Include the VLAN ID and dot1p bits in the ASCII tuple";
                                        }

                                    }
                                }
                            } // container circuit-id

                            ///nokia-conf/configure/service/vprn/subscriber-interface/group-interface/ipv4/dhcp/option-82/remote-id
                            container remote-id {
                                description "Enter the remote-id context";

                                ///nokia-conf/configure/service/vprn/subscriber-interface/group-interface/ipv4/dhcp/option-82/remote-id/remote-id
                                choice remote-id {
                                    default "none";
                                    ///nokia-conf/configure/service/vprn/subscriber-interface/group-interface/ipv4/dhcp/option-82/remote-id/remote-id/none
                                    case none {

                                        ///nokia-conf/configure/service/vprn/subscriber-interface/group-interface/ipv4/dhcp/option-82/remote-id/remote-id/none/none
                                        leaf none {
                                            type empty;
                                            description "Do not include the remote ID";
                                        }

                                    }
                                    ///nokia-conf/configure/service/vprn/subscriber-interface/group-interface/ipv4/dhcp/option-82/remote-id/remote-id/mac
                                    case mac {

                                        ///nokia-conf/configure/service/vprn/subscriber-interface/group-interface/ipv4/dhcp/option-82/remote-id/remote-id/mac/mac
                                        leaf mac {
                                            type empty;
                                            description "Use the MAC address for the remote ID";
                                        }

                                    }
                                    ///nokia-conf/configure/service/vprn/subscriber-interface/group-interface/ipv4/dhcp/option-82/remote-id/remote-id/ascii-string
                                    case ascii-string {

                                        ///nokia-conf/configure/service/vprn/subscriber-interface/group-interface/ipv4/dhcp/option-82/remote-id/remote-id/ascii-string/ascii-string
                                        leaf ascii-string {
                                            type types-sros:string-not-all-spaces {
                                                length "1..32";
                                            }
                                            description "User-defined ASCII string for the remote ID";
                                        }

                                    }
                                }
                            } // container remote-id

                            ///nokia-conf/configure/service/vprn/subscriber-interface/group-interface/ipv4/dhcp/option-82/vendor-specific-option
                            container vendor-specific-option {
                                description "Enter the vendor-specific-option context";

                                ///nokia-conf/configure/service/vprn/subscriber-interface/group-interface/ipv4/dhcp/option-82/vendor-specific-option/system-id
                                leaf system-id {
                                    type boolean;
                                    default "false";
                                    description "Send the system ID in the VSO";
                                }

                                ///nokia-conf/configure/service/vprn/subscriber-interface/group-interface/ipv4/dhcp/option-82/vendor-specific-option/client-mac-address
                                leaf client-mac-address {
                                    type boolean;
                                    default "false";
                                    description "Send the MAC address in the VSO";
                                }

                                ///nokia-conf/configure/service/vprn/subscriber-interface/group-interface/ipv4/dhcp/option-82/vendor-specific-option/pool-name
                                leaf pool-name {
                                    type boolean;
                                    default "false";
                                    description "Send the pool name in the VSO";
                                }

                                ///nokia-conf/configure/service/vprn/subscriber-interface/group-interface/ipv4/dhcp/option-82/vendor-specific-option/service-id
                                leaf service-id {
                                    type boolean;
                                    default "false";
                                    description "Send the service ID in the Vendor Specific Option";
                                }

                                ///nokia-conf/configure/service/vprn/subscriber-interface/group-interface/ipv4/dhcp/option-82/vendor-specific-option/sap-id
                                leaf sap-id {
                                    type boolean;
                                    default "false";
                                    description "Send SAP ID in the sub-option of the DHCP relay packet";
                                }

                                ///nokia-conf/configure/service/vprn/subscriber-interface/group-interface/ipv4/dhcp/option-82/vendor-specific-option/string
                                leaf string {
                                    type types-sros:string-not-all-spaces {
                                        length "1..32";
                                    }
                                    description "User-defined ASCII string for the VSO";
                                }

                            } // container vendor-specific-option

                        } // container option-82

                        ///nokia-conf/configure/service/vprn/subscriber-interface/group-interface/ipv4/dhcp/lease-populate
                        container lease-populate {
                            description "Enter the lease-populate context";

                            ///nokia-conf/configure/service/vprn/subscriber-interface/group-interface/ipv4/dhcp/lease-populate/max-leases
                            leaf max-leases {
                                type uint32 {
                                    range "1..511999";
                                }
                                description "Maximum number of DHCPv4 leases";
                            }

                            ///nokia-conf/configure/service/vprn/subscriber-interface/group-interface/ipv4/dhcp/lease-populate/l2-header
                            container l2-header {
                                when "../../../../type = 'plain' or ../../../../type = 'lns'" {
                                    description "invalid group interface type";
                                }
                                presence "Enable the l2-header context";
                                description "Enable the l2-header context";

                                ///nokia-conf/configure/service/vprn/subscriber-interface/group-interface/ipv4/dhcp/lease-populate/l2-header/mac
                                leaf mac {
                                    type types-sros:mac-unicast-address;
                                    description "IEEE address used in anti-spoofing entries for the SAP";
                                }

                            } // container l2-header

                        } // container lease-populate

                        ///nokia-conf/configure/service/vprn/subscriber-interface/group-interface/ipv4/dhcp/client-applications
                        container client-applications {
                            when "../../../type = 'plain' or ../../../type = 'lns' or ../../../type = 'bonding'" {
                                description "invalid group interface type";
                            }
                            description "Enter the client-applications context";

                            ///nokia-conf/configure/service/vprn/subscriber-interface/group-interface/ipv4/dhcp/client-applications/dhcp
                            leaf dhcp {
                                type boolean;
                                default "true";
                                description "Enable IPoE clients to use DHCP relay or proxy server";
                            }

                            ///nokia-conf/configure/service/vprn/subscriber-interface/group-interface/ipv4/dhcp/client-applications/ppp
                            leaf ppp {
                                type boolean;
                                default "false";
                                description "Enable PPPoE clients to use DHCP relay or proxy server";
                            }

                        } // container client-applications

                        ///nokia-conf/configure/service/vprn/subscriber-interface/group-interface/ipv4/dhcp/relay-proxy
                        container relay-proxy {
                            when "not(../../../type = 'gtp')" {
                                description "group interface type must not be 'gtp'";
                            }
                            presence "Enable the relay-proxy context";
                            description "Enable the relay-proxy context";

                            ///nokia-conf/configure/service/vprn/subscriber-interface/group-interface/ipv4/dhcp/relay-proxy/release-update-src-ip
                            leaf release-update-src-ip {
                                type boolean;
                                default "false";
                                description "Update the source IP address of a DHCP RELEASE message";
                            }

                            ///nokia-conf/configure/service/vprn/subscriber-interface/group-interface/ipv4/dhcp/relay-proxy/siaddr-override
                            leaf siaddr-override {
                                type types-sros:ipv4-unicast-address;
                                description "DHCP server IP address for address hiding function";
                            }

                        } // container relay-proxy

                        ///nokia-conf/configure/service/vprn/subscriber-interface/group-interface/ipv4/dhcp/offer-selection
                        container offer-selection {
                            description "Enter the offer-selection context";

                            ///nokia-conf/configure/service/vprn/subscriber-interface/group-interface/ipv4/dhcp/offer-selection/discover-delay
                            leaf discover-delay {
                                type int32 {
                                    range "1..100";
                                }
                                units "deciseconds";
                                description "Delay before sending DHCP Discover messages";
                            }

                            ///nokia-conf/configure/service/vprn/subscriber-interface/group-interface/ipv4/dhcp/offer-selection/mode
                            choice mode {
                                ///nokia-conf/configure/service/vprn/subscriber-interface/group-interface/ipv4/dhcp/offer-selection/mode/mode-client-mac
                                case mode-client-mac {

                                    ///nokia-conf/configure/service/vprn/subscriber-interface/group-interface/ipv4/dhcp/offer-selection/mode/mode-client-mac/client-mac
                                    container client-mac {
                                        description "Enter the client-mac context";

                                        ///nokia-conf/configure/service/vprn/subscriber-interface/group-interface/ipv4/dhcp/offer-selection/mode/mode-client-mac/client-mac/mac-address
                                        leaf mac-address {
                                            type enumeration {
                                                enum odd                            { value 1; }
                                                enum even                           { value 2; }
                                            }
                                            description "Designated client MAC addresses for Offer selection";
                                        }

                                        ///nokia-conf/configure/service/vprn/subscriber-interface/group-interface/ipv4/dhcp/offer-selection/mode/mode-client-mac/client-mac/discover-delay
                                        leaf discover-delay {
                                            type int32 {
                                                range "1..100";
                                            }
                                            units "deciseconds";
                                            description "Delay before sending DHCP Discover messages";
                                        }

                                    } // container client-mac

                                }
                                ///nokia-conf/configure/service/vprn/subscriber-interface/group-interface/ipv4/dhcp/offer-selection/mode/mode-server
                                case mode-server {

                                    ///nokia-conf/configure/service/vprn/subscriber-interface/group-interface/ipv4/dhcp/offer-selection/mode/mode-server/server
                                    list server {
                                        key "ipv4-address";
                                        max-elements 8;
                                        description "Enter the server list instance";

                                        ///nokia-conf/configure/service/vprn/subscriber-interface/group-interface/ipv4/dhcp/offer-selection/mode/mode-server/server/ipv4-address
                                        leaf ipv4-address {
                                            type types-sros:ipv4-unicast-address;
                                            description "IP address of the DHCP server";
                                        }

                                        ///nokia-conf/configure/service/vprn/subscriber-interface/group-interface/ipv4/dhcp/offer-selection/mode/mode-server/server/discover-delay
                                        leaf discover-delay {
                                            type int32 {
                                                range "1..100";
                                            }
                                            units "deciseconds";
                                            description "Delay before sending DHCP Discover messages";
                                        }

                                        ///nokia-conf/configure/service/vprn/subscriber-interface/group-interface/ipv4/dhcp/offer-selection/mode/mode-server/server/apply-groups
                                        leaf-list apply-groups {
                                            type leafref {
                                                path "../../../../../../../../../groups/group/name";
                                            }
                                            max-elements 8;
                                            ordered-by user;
                                            description "Apply a configuration group at this level";
                                        }

                                        ///nokia-conf/configure/service/vprn/subscriber-interface/group-interface/ipv4/dhcp/offer-selection/mode/mode-server/server/apply-groups-exclude
                                        leaf-list apply-groups-exclude {
                                            type leafref {
                                                path "../../../../../../../../../groups/group/name";
                                            }
                                            max-elements 8;
                                            ordered-by user;
                                            description "Exclude a configuration group at this level";
                                        }

                                    } // list server

                                }
                            }
                        } // container offer-selection

                    } // container dhcp

                } // container ipv4

                ///nokia-conf/configure/service/vprn/subscriber-interface/group-interface/ipv6
                container ipv6 {
                    presence "Enable the ipv6 context";
                    description "Enable the ipv6 context";

                    ///nokia-conf/configure/service/vprn/subscriber-interface/group-interface/ipv6/allow-multiple-wan-addresses
                    leaf allow-multiple-wan-addresses {
                        when "../../type = 'plain' or ../../type = 'lns' or ../../type = 'wlan-gw' or ../../type = 'gtp'" {
                            description "invalid group interface type";
                        }
                        type boolean;
                        default "false";
                        description "Allow multiple WAN addresses";
                    }

                    ///nokia-conf/configure/service/vprn/subscriber-interface/group-interface/ipv6/ipoe-bridged-mode
                    leaf ipoe-bridged-mode {
                        when "../../type = 'plain' or ../../type = 'lns'" {
                            description "invalid group interface type";
                        }
                        type boolean;
                        default "false";
                        description "Enable IPv6 IPoE bridged mode";
                    }

                    ///nokia-conf/configure/service/vprn/subscriber-interface/group-interface/ipv6/qos-route-lookup
                    leaf qos-route-lookup {
                        type types-router:qos-route-lookup-grp-if;
                        description "QoS route lookup";
                    }

                    ///nokia-conf/configure/service/vprn/subscriber-interface/group-interface/ipv6/auto-reply
                    container auto-reply {
                        when "../../type = 'plain' or ../../type = 'lns' or ../../type = 'wlan-gw'" {
                            description "invalid group interface type";
                        }
                        description "Enter the auto-reply context";

                        ///nokia-conf/configure/service/vprn/subscriber-interface/group-interface/ipv6/auto-reply/neighbor-solicitation
                        leaf neighbor-solicitation {
                            type boolean;
                            default "false";
                            description "Enable auto-reply for NS";
                        }

                        ///nokia-conf/configure/service/vprn/subscriber-interface/group-interface/ipv6/auto-reply/router-solicitation
                        leaf router-solicitation {
                            type boolean;
                            default "false";
                            description "Enable auto-reply for RS";
                        }

                    } // container auto-reply

                    ///nokia-conf/configure/service/vprn/subscriber-interface/group-interface/ipv6/urpf-check
                    container urpf-check {
                        when "not(../../type = 'bonding')" {
                            description "group interface type must not be 'bonding'";
                        }
                        presence "Enable the urpf-check context";
                        description "Enable the urpf-check context";

                        ///nokia-conf/configure/service/vprn/subscriber-interface/group-interface/ipv6/urpf-check/mode
                        leaf mode {
                            type types-router:urpf-check-mode;
                            default "strict";
                            description "Unicast RPF check mode";
                        }

                    } // container urpf-check

                    ///nokia-conf/configure/service/vprn/subscriber-interface/group-interface/ipv6/bfd
                    container bfd {
                        description "Enter the bfd context";

                        ///nokia-conf/configure/service/vprn/subscriber-interface/group-interface/ipv6/bfd/admin-state
                        leaf admin-state {
                            type types-sros:admin-state;
                            default "disable";
                            description "Administrative state of BFD sessions";
                        }

                        ///nokia-conf/configure/service/vprn/subscriber-interface/group-interface/ipv6/bfd/transmit-interval
                        leaf transmit-interval {
                            type uint32 {
                                range "10..100000";
                            }
                            units "milliseconds";
                            default "100";
                            description "BFD transmit interval over this interface";
                        }

                        ///nokia-conf/configure/service/vprn/subscriber-interface/group-interface/ipv6/bfd/receive
                        leaf receive {
                            type uint32 {
                                range "10..100000";
                            }
                            units "milliseconds";
                            default "100";
                            description "BFD receive interval over this interface";
                        }

                        ///nokia-conf/configure/service/vprn/subscriber-interface/group-interface/ipv6/bfd/multiplier
                        leaf multiplier {
                            type uint32 {
                                range "1..20";
                            }
                            default "3";
                            description "Number of consecutive BFD messages missed from the peer";
                        }

                        ///nokia-conf/configure/service/vprn/subscriber-interface/group-interface/ipv6/bfd/echo-receive
                        leaf echo-receive {
                            type uint32 {
                                range "100..100000";
                            }
                            units "milliseconds";
                            description "Minimum echo interval over this interface";
                        }

                        ///nokia-conf/configure/service/vprn/subscriber-interface/group-interface/ipv6/bfd/type
                        leaf type {
                            type enumeration {
                                enum cpm-np                         { value 1; }
                                enum auto                           { value 2; }
                                enum fp                             { value 3; }
                            }
                            default "auto";
                            description "Local termination point for the BFD session";
                        }

                    } // container bfd

                    ///nokia-conf/configure/service/vprn/subscriber-interface/group-interface/ipv6/dhcp6
                    container dhcp6 {
                        when "../../type = 'plain' or ../../type = 'lns' or ../../type = 'wlan-gw' or ../../type = 'gtp'" {
                            description "invalid group interface type";
                        }
                        description "Enter the dhcp6 context";

                        ///nokia-conf/configure/service/vprn/subscriber-interface/group-interface/ipv6/dhcp6/filter
                        leaf filter {
                            type leafref {
                                path "../../../../../../../filter/dhcp6-filter/filter-id";
                            }
                            description "DHCPv6 filter";
                        }

                        ///nokia-conf/configure/service/vprn/subscriber-interface/group-interface/ipv6/dhcp6/override-slaac
                        leaf override-slaac {
                            type boolean;
                            default "false";
                            description "Allow WAN address offered by DHCP to overwrite the WAN address acquired from SLAAC";
                        }

                        ///nokia-conf/configure/service/vprn/subscriber-interface/group-interface/ipv6/dhcp6/python-policy
                        leaf python-policy {
                            type leafref {
                                path "../../../../../../../python/python-policy/name";
                            }
                            description "Python policy";
                        }

                        ///nokia-conf/configure/service/vprn/subscriber-interface/group-interface/ipv6/dhcp6/user-db
                        leaf user-db {
                            when "not(../../../type = 'gtp')" {
                                description "group interface type must not be 'gtp'";
                            }
                            type leafref {
                                path "../../../../../../../subscriber-mgmt/local-user-db/name";
                            }
                            description "Local user database used for authentication";
                        }

                        ///nokia-conf/configure/service/vprn/subscriber-interface/group-interface/ipv6/dhcp6/user-ident
                        leaf user-ident {
                            type types-services:dhcp6-user-ident;
                            default "mac";
                            description "DHCP6 user identification for this interface";
                        }

                        ///nokia-conf/configure/service/vprn/subscriber-interface/group-interface/ipv6/dhcp6/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv6/dhcp6/apply-groups-exclude
                        leaf-list apply-groups-exclude {
                            type leafref {
                                path "../../../../../../../groups/group/name";
                            }
                            max-elements 8;
                            ordered-by user;
                            description "Exclude a configuration group at this level";
                        }

                        ///nokia-conf/configure/service/vprn/subscriber-interface/group-interface/ipv6/dhcp6/pd-managed-route
                        container pd-managed-route {
                            presence "Enable the pd-managed-route context";
                            description "Enable the pd-managed-route context";

                            ///nokia-conf/configure/service/vprn/subscriber-interface/group-interface/ipv6/dhcp6/pd-managed-route/next-hop
                            leaf next-hop {
                                type types-services:dhcp6-pd-managed-route-nh;
                                default "ipv6";
                                description "Next hop type";
                            }

                        } // container pd-managed-route

                        ///nokia-conf/configure/service/vprn/subscriber-interface/group-interface/ipv6/dhcp6/snooping
                        container snooping {
                            description "Enter the snooping context";

                            ///nokia-conf/configure/service/vprn/subscriber-interface/group-interface/ipv6/dhcp6/snooping/admin-state
                            leaf admin-state {
                                when "not(../../../../type = 'gtp')" {
                                    description "group interface type must not be 'gtp'";
                                }
                                type types-sros:admin-state;
                                default "disable";
                                description "Administrative state of DHCPv6 snooping";
                            }

                        } // container snooping

                        ///nokia-conf/configure/service/vprn/subscriber-interface/group-interface/ipv6/dhcp6/relay
                        container relay {
                            description "Enter the relay context";

                            ///nokia-conf/configure/service/vprn/subscriber-interface/group-interface/ipv6/dhcp6/relay/admin-state
                            leaf admin-state {
                                type types-sros:admin-state;
                                default "disable";
                                description "Administrative state of DHCPv6 Relay";
                            }

                            ///nokia-conf/configure/service/vprn/subscriber-interface/group-interface/ipv6/dhcp6/relay/description
                            leaf description {
                                type types-sros:description;
                                description "Text description";
                            }

                            ///nokia-conf/configure/service/vprn/subscriber-interface/group-interface/ipv6/dhcp6/relay/source-address
                            leaf source-address {
                                type types-sros:ipv6-unicast-address;
                                description "Source IPv6 address for the DHCPv6 relay messages";
                            }

                            ///nokia-conf/configure/service/vprn/subscriber-interface/group-interface/ipv6/dhcp6/relay/link-address
                            leaf link-address {
                                type types-sros:ipv6-address;
                                description "Link address for the DHCPv6 relay messages";
                            }

                            ///nokia-conf/configure/service/vprn/subscriber-interface/group-interface/ipv6/dhcp6/relay/server
                            leaf-list server {
                                type types-sros:ipv6-address-with-zone;
                                max-elements 8;
                                ordered-by user;
                                description "DHCP6 server(s) to which the DHCP6 requests are forwarded";
                            }

                            ///nokia-conf/configure/service/vprn/subscriber-interface/group-interface/ipv6/dhcp6/relay/client-applications
                            container client-applications {
                                when "not(../../../../type = 'gtp')" {
                                    description "group interface type must not be 'gtp'";
                                }
                                description "Enter the client-applications context";

                                ///nokia-conf/configure/service/vprn/subscriber-interface/group-interface/ipv6/dhcp6/relay/client-applications/dhcp
                                leaf dhcp {
                                    type boolean;
                                    default "true";
                                    description "Enable IPoE clients to use DHCP relay or proxy server";
                                }

                                ///nokia-conf/configure/service/vprn/subscriber-interface/group-interface/ipv6/dhcp6/relay/client-applications/ppp
                                leaf ppp {
                                    when "not(../../../../../type = 'wlan-gw')" {
                                        description "group interface type must not be 'wlan-gw'";
                                    }
                                    type boolean;
                                    default "false";
                                    description "Allow the PPP application to use DHCP relay functionality";
                                }

                            } // container client-applications

                            ///nokia-conf/configure/service/vprn/subscriber-interface/group-interface/ipv6/dhcp6/relay/advertise-selection
                            container advertise-selection {
                                description "Enter the advertise-selection context";

                                ///nokia-conf/configure/service/vprn/subscriber-interface/group-interface/ipv6/dhcp6/relay/advertise-selection/solicit-delay
                                leaf solicit-delay {
                                    type int32 {
                                        range "1..100";
                                    }
                                    units "deciseconds";
                                    description "Delay before sending DHCPv6 Solicit messages";
                                }

                                ///nokia-conf/configure/service/vprn/subscriber-interface/group-interface/ipv6/dhcp6/relay/advertise-selection/mode
                                choice mode {
                                    ///nokia-conf/configure/service/vprn/subscriber-interface/group-interface/ipv6/dhcp6/relay/advertise-selection/mode/mode-client-mac
                                    case mode-client-mac {

                                        ///nokia-conf/configure/service/vprn/subscriber-interface/group-interface/ipv6/dhcp6/relay/advertise-selection/mode/mode-client-mac/client-mac
                                        container client-mac {
                                            description "Enter the client-mac context";

                                            ///nokia-conf/configure/service/vprn/subscriber-interface/group-interface/ipv6/dhcp6/relay/advertise-selection/mode/mode-client-mac/client-mac/mac-address
                                            leaf mac-address {
                                                type enumeration {
                                                    enum odd                            { value 1; }
                                                    enum even                           { value 2; }
                                                }
                                                description "Designated client MAC addresses for Advertise selection";
                                            }

                                            ///nokia-conf/configure/service/vprn/subscriber-interface/group-interface/ipv6/dhcp6/relay/advertise-selection/mode/mode-client-mac/client-mac/solicit-delay
                                            leaf solicit-delay {
                                                type int32 {
                                                    range "1..100";
                                                }
                                                units "deciseconds";
                                                description "Delay before sending DHCPv6 Solicit messages";
                                            }

                                            ///nokia-conf/configure/service/vprn/subscriber-interface/group-interface/ipv6/dhcp6/relay/advertise-selection/mode/mode-client-mac/client-mac/preference-option
                                            container preference-option {
                                                description "Enter the preference-option context";

                                                ///nokia-conf/configure/service/vprn/subscriber-interface/group-interface/ipv6/dhcp6/relay/advertise-selection/mode/mode-client-mac/client-mac/preference-option/value
                                                leaf value {
                                                    type int32 {
                                                        range "0..255";
                                                    }
                                                    description "Preference option value for DHCPv6 Advertise messages";
                                                }

                                            } // container preference-option

                                        } // container client-mac

                                    }
                                    ///nokia-conf/configure/service/vprn/subscriber-interface/group-interface/ipv6/dhcp6/relay/advertise-selection/mode/mode-server
                                    case mode-server {

                                        ///nokia-conf/configure/service/vprn/subscriber-interface/group-interface/ipv6/dhcp6/relay/advertise-selection/mode/mode-server/server
                                        list server {
                                            key "ipv6-address";
                                            max-elements 8;
                                            description "Enter the server list instance";

                                            ///nokia-conf/configure/service/vprn/subscriber-interface/group-interface/ipv6/dhcp6/relay/advertise-selection/mode/mode-server/server/ipv6-address
                                            leaf ipv6-address {
                                                type types-sros:ipv6-address;
                                                description "IP address of the DHCPv6 server";
                                            }

                                            ///nokia-conf/configure/service/vprn/subscriber-interface/group-interface/ipv6/dhcp6/relay/advertise-selection/mode/mode-server/server/solicit-delay
                                            leaf solicit-delay {
                                                type int32 {
                                                    range "1..100";
                                                }
                                                units "deciseconds";
                                                description "Delay before sending DHCPv6 Solicit messages";
                                            }

                                            ///nokia-conf/configure/service/vprn/subscriber-interface/group-interface/ipv6/dhcp6/relay/advertise-selection/mode/mode-server/server/apply-groups
                                            leaf-list apply-groups {
                                                type leafref {
                                                    path "../../../../../../../../../../groups/group/name";
                                                }
                                                max-elements 8;
                                                ordered-by user;
                                                description "Apply a configuration group at this level";
                                            }

                                            ///nokia-conf/configure/service/vprn/subscriber-interface/group-interface/ipv6/dhcp6/relay/advertise-selection/mode/mode-server/server/apply-groups-exclude
                                            leaf-list apply-groups-exclude {
                                                type leafref {
                                                    path "../../../../../../../../../../groups/group/name";
                                                }
                                                max-elements 8;
                                                ordered-by user;
                                                description "Exclude a configuration group at this level";
                                            }

                                            ///nokia-conf/configure/service/vprn/subscriber-interface/group-interface/ipv6/dhcp6/relay/advertise-selection/mode/mode-server/server/preference-option
                                            container preference-option {
                                                description "Enter the preference-option context";

                                                ///nokia-conf/configure/service/vprn/subscriber-interface/group-interface/ipv6/dhcp6/relay/advertise-selection/mode/mode-server/server/preference-option/value
                                                leaf value {
                                                    type int32 {
                                                        range "0..255";
                                                    }
                                                    description "Preference option value for DHCPv6 Advertise messages";
                                                }

                                            } // container preference-option

                                        } // list server

                                    }
                                }
                                ///nokia-conf/configure/service/vprn/subscriber-interface/group-interface/ipv6/dhcp6/relay/advertise-selection/preference-option
                                container preference-option {
                                    description "Enter the preference-option context";

                                    ///nokia-conf/configure/service/vprn/subscriber-interface/group-interface/ipv6/dhcp6/relay/advertise-selection/preference-option/value
                                    leaf value {
                                        type int32 {
                                            range "0..255";
                                        }
                                        description "Preference option value for DHCPv6 Advertise messages";
                                    }

                                } // container preference-option

                            } // container advertise-selection

                            ///nokia-conf/configure/service/vprn/subscriber-interface/group-interface/ipv6/dhcp6/relay/lease-split
                            container lease-split {
                                description "Enter the lease-split context";

                                ///nokia-conf/configure/service/vprn/subscriber-interface/group-interface/ipv6/dhcp6/relay/lease-split/admin-state
                                leaf admin-state {
                                    type types-sros:admin-state;
                                    default "disable";
                                    description "Administrative state of DHCPv6 lease split";
                                }

                                ///nokia-conf/configure/service/vprn/subscriber-interface/group-interface/ipv6/dhcp6/relay/lease-split/valid-lifetime
                                leaf valid-lifetime {
                                    type types-submgt:dhcp6-prefix-lifetime-new;
                                    default "3600";
                                    description "DHCPv6 lease split valid lifetime (short lease time)";
                                }

                            } // container lease-split

                        } // container relay

                        ///nokia-conf/configure/service/vprn/subscriber-interface/group-interface/ipv6/dhcp6/proxy-server
                        container proxy-server {
                            description "Enter the proxy-server context";

                            ///nokia-conf/configure/service/vprn/subscriber-interface/group-interface/ipv6/dhcp6/proxy-server/admin-state
                            leaf admin-state {
                                type types-sros:admin-state;
                                default "disable";
                                description "Administrative state of the DHCPv6 proxy server";
                            }

                            ///nokia-conf/configure/service/vprn/subscriber-interface/group-interface/ipv6/dhcp6/proxy-server/preferred-lifetime
                            leaf preferred-lifetime {
                                type types-submgt:dhcp6-prefix-lifetime;
                                default "3600";
                                description "Time for prefix to remain preferred on this interface";
                            }

                            ///nokia-conf/configure/service/vprn/subscriber-interface/group-interface/ipv6/dhcp6/proxy-server/valid-lifetime
                            leaf valid-lifetime {
                                type types-submgt:dhcp6-prefix-lifetime;
                                default "86400";
                                description "Time for prefix to remain valid on this interface";
                            }

                            ///nokia-conf/configure/service/vprn/subscriber-interface/group-interface/ipv6/dhcp6/proxy-server/renew-timer
                            leaf renew-timer {
                                type types-submgt:dhcp6-renew-timer;
                                description "Renew timer (T1)";
                            }

                            ///nokia-conf/configure/service/vprn/subscriber-interface/group-interface/ipv6/dhcp6/proxy-server/rebind-timer
                            leaf rebind-timer {
                                type types-submgt:dhcp6-rebind-timer;
                                description "Rebind timer (T2) for this interface";
                            }

                            ///nokia-conf/configure/service/vprn/subscriber-interface/group-interface/ipv6/dhcp6/proxy-server/client-applications
                            container client-applications {
                                when "not(../../../../type = 'gtp')" {
                                    description "group interface type must not be 'gtp'";
                                }
                                description "Enter the client-applications context";

                                ///nokia-conf/configure/service/vprn/subscriber-interface/group-interface/ipv6/dhcp6/proxy-server/client-applications/dhcp
                                leaf dhcp {
                                    type boolean;
                                    default "true";
                                    description "Enable IPoE clients to use DHCP relay or proxy server";
                                }

                                ///nokia-conf/configure/service/vprn/subscriber-interface/group-interface/ipv6/dhcp6/proxy-server/client-applications/ppp
                                leaf ppp {
                                    when "not(../../../../../type = 'wlan-gw')" {
                                        description "group interface type must not be 'wlan-gw'";
                                    }
                                    type boolean;
                                    default "false";
                                    description "Allow PPPoE clients to use DHCP relay functionality";
                                }

                            } // container client-applications

                            ///nokia-conf/configure/service/vprn/subscriber-interface/group-interface/ipv6/dhcp6/proxy-server/server-id
                            container server-id {
                                description "Enable the server-id context";

                                ///nokia-conf/configure/service/vprn/subscriber-interface/group-interface/ipv6/dhcp6/proxy-server/server-id/apply-groups
                                leaf-list apply-groups {
                                    type leafref {
                                        path "../../../../../../../../../groups/group/name";
                                    }
                                    max-elements 8;
                                    ordered-by user;
                                    description "Apply a configuration group at this level";
                                }

                                ///nokia-conf/configure/service/vprn/subscriber-interface/group-interface/ipv6/dhcp6/proxy-server/server-id/apply-groups-exclude
                                leaf-list apply-groups-exclude {
                                    type leafref {
                                        path "../../../../../../../../../groups/group/name";
                                    }
                                    max-elements 8;
                                    ordered-by user;
                                    description "Exclude a configuration group at this level";
                                }

                                ///nokia-conf/configure/service/vprn/subscriber-interface/group-interface/ipv6/dhcp6/proxy-server/server-id/server-id
                                choice server-id {
                                    default "duid-ll";
                                    ///nokia-conf/configure/service/vprn/subscriber-interface/group-interface/ipv6/dhcp6/proxy-server/server-id/server-id/duid-ll
                                    case duid-ll {

                                        ///nokia-conf/configure/service/vprn/subscriber-interface/group-interface/ipv6/dhcp6/proxy-server/server-id/server-id/duid-ll/duid-ll
                                        leaf duid-ll {
                                            type empty;
                                            description "Use link-layer address (DUID-LL) as DUID";
                                        }

                                    }
                                    ///nokia-conf/configure/service/vprn/subscriber-interface/group-interface/ipv6/dhcp6/proxy-server/server-id/server-id/duid-en-hex
                                    case duid-en-hex {

                                        ///nokia-conf/configure/service/vprn/subscriber-interface/group-interface/ipv6/dhcp6/proxy-server/server-id/server-id/duid-en-hex/duid-en-hex
                                        leaf duid-en-hex {
                                            type string {
                                                length "1..118";
                                            }
                                            description "DUID system ID in hexadecimal format";
                                        }

                                    }
                                    ///nokia-conf/configure/service/vprn/subscriber-interface/group-interface/ipv6/dhcp6/proxy-server/server-id/server-id/duid-en-ascii
                                    case duid-en-ascii {

                                        ///nokia-conf/configure/service/vprn/subscriber-interface/group-interface/ipv6/dhcp6/proxy-server/server-id/server-id/duid-en-ascii/duid-en-ascii
                                        leaf duid-en-ascii {
                                            type types-sros:string-not-all-spaces {
                                                length "1..58";
                                            }
                                            description "Vendor-assigned ID based on Enterprise Number (DUID-EN)";
                                        }

                                    }
                                }
                            } // container server-id

                        } // container proxy-server

                        ///nokia-conf/configure/service/vprn/subscriber-interface/group-interface/ipv6/dhcp6/option
                        container option {
                            description "Enable the option context";

                            ///nokia-conf/configure/service/vprn/subscriber-interface/group-interface/ipv6/dhcp6/option/remote-id
                            leaf remote-id {
                                type boolean;
                                default "false";
                                description "Send remote ID option in the DHCPv6 relay packet";
                            }

                            ///nokia-conf/configure/service/vprn/subscriber-interface/group-interface/ipv6/dhcp6/option/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/ipv6/dhcp6/option/apply-groups-exclude
                            leaf-list apply-groups-exclude {
                                type leafref {
                                    path "../../../../../../../../groups/group/name";
                                }
                                max-elements 8;
                                ordered-by user;
                                description "Exclude a configuration group at this level";
                            }

                            ///nokia-conf/configure/service/vprn/subscriber-interface/group-interface/ipv6/dhcp6/option/interface-id
                            container interface-id {
                                description "Enter the interface-id context";

                                ///nokia-conf/configure/service/vprn/subscriber-interface/group-interface/ipv6/dhcp6/option/interface-id/interface-id
                                choice interface-id {
                                    ///nokia-conf/configure/service/vprn/subscriber-interface/group-interface/ipv6/dhcp6/option/interface-id/interface-id/ascii-tuple
                                    case ascii-tuple {

                                        ///nokia-conf/configure/service/vprn/subscriber-interface/group-interface/ipv6/dhcp6/option/interface-id/interface-id/ascii-tuple/ascii-tuple
                                        leaf ascii-tuple {
                                            type empty;
                                            description "Use ASCII-encoded concatenated tuple";
                                        }

                                    }
                                    ///nokia-conf/configure/service/vprn/subscriber-interface/group-interface/ipv6/dhcp6/option/interface-id/interface-id/sap-id
                                    case sap-id {

                                        ///nokia-conf/configure/service/vprn/subscriber-interface/group-interface/ipv6/dhcp6/option/interface-id/interface-id/sap-id/sap-id
                                        leaf sap-id {
                                            type empty;
                                            description "Use SAP ID in interface ID option in relay packet";
                                        }

                                    }
                                    ///nokia-conf/configure/service/vprn/subscriber-interface/group-interface/ipv6/dhcp6/option/interface-id/interface-id/if-index
                                    case if-index {

                                        ///nokia-conf/configure/service/vprn/subscriber-interface/group-interface/ipv6/dhcp6/option/interface-id/interface-id/if-index/if-index
                                        leaf if-index {
                                            type empty;
                                            description "Use interface index in the DHCPv6 relay packet";
                                        }

                                    }
                                    ///nokia-conf/configure/service/vprn/subscriber-interface/group-interface/ipv6/dhcp6/option/interface-id/interface-id/string
                                    case string {

                                        ///nokia-conf/configure/service/vprn/subscriber-interface/group-interface/ipv6/dhcp6/option/interface-id/interface-id/string/string
                                        leaf string {
                                            type types-sros:string-not-all-spaces {
                                                length "1..80";
                                            }
                                            description "String for interface ID option in DHCPv6 relay packet";
                                        }

                                    }
                                }
                            } // container interface-id

                        } // container option

                    } // container dhcp6

                    ///nokia-conf/configure/service/vprn/subscriber-interface/group-interface/ipv6/neighbor-discovery
                    container neighbor-discovery {
                        when "../../type = 'plain' or ../../type = 'lns' or ../../type = 'wlan-gw'" {
                            description "invalid group interface type";
                        }
                        description "Enter the neighbor-discovery context";

                        ///nokia-conf/configure/service/vprn/subscriber-interface/group-interface/ipv6/neighbor-discovery/dad-snooping
                        leaf dad-snooping {
                            type boolean;
                            default "false";
                            description "Populate table via duplicate address detection packets";
                        }

                        ///nokia-conf/configure/service/vprn/subscriber-interface/group-interface/ipv6/neighbor-discovery/neighbor-limit
                        leaf neighbor-limit {
                            type int32 {
                                range "1..8";
                            }
                            default "1";
                            description "Maximum neighbor entries learned per SLAAC host";
                        }

                        ///nokia-conf/configure/service/vprn/subscriber-interface/group-interface/ipv6/neighbor-discovery/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv6/neighbor-discovery/apply-groups-exclude
                        leaf-list apply-groups-exclude {
                            type leafref {
                                path "../../../../../../../groups/group/name";
                            }
                            max-elements 8;
                            ordered-by user;
                            description "Exclude a configuration group at this level";
                        }

                    } // container neighbor-discovery

                    ///nokia-conf/configure/service/vprn/subscriber-interface/group-interface/ipv6/router-advertisements
                    container router-advertisements {
                        when "../../type = 'plain' or ../../type = 'lns' or ../../type = 'wlan-gw' or ../../type = 'gtp'" {
                            description "invalid group interface type";
                        }
                        description "Enter the router-advertisements context";

                        ///nokia-conf/configure/service/vprn/subscriber-interface/group-interface/ipv6/router-advertisements/admin-state
                        leaf admin-state {
                            type types-sros:admin-state;
                            default "disable";
                            description "Administrative state of router advertisements";
                        }

                        ///nokia-conf/configure/service/vprn/subscriber-interface/group-interface/ipv6/router-advertisements/max-advertisement-interval
                        leaf max-advertisement-interval {
                            type types-sros:time-duration {
                                range "900..1800";
                            }
                            units "seconds";
                            default "1800";
                            description "Maximum advertisement interval";
                        }

                        ///nokia-conf/configure/service/vprn/subscriber-interface/group-interface/ipv6/router-advertisements/min-advertisement-interval
                        leaf min-advertisement-interval {
                            type types-sros:time-duration {
                                range "900..1350";
                            }
                            units "seconds";
                            default "900";
                            description "Minimum advertisement interval";
                        }

                        ///nokia-conf/configure/service/vprn/subscriber-interface/group-interface/ipv6/router-advertisements/force-mcast
                        leaf force-mcast {
                            type enumeration {
                                enum ip                             { value 1; }
                                enum ip-mac                         { value 2; }
                            }
                            description "Protocol with forced multicast";
                        }

                        ///nokia-conf/configure/service/vprn/subscriber-interface/group-interface/ipv6/router-advertisements/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv6/router-advertisements/apply-groups-exclude
                        leaf-list apply-groups-exclude {
                            type leafref {
                                path "../../../../../../../groups/group/name";
                            }
                            max-elements 8;
                            ordered-by user;
                            description "Exclude a configuration group at this level";
                        }

                        ///nokia-conf/configure/service/vprn/subscriber-interface/group-interface/ipv6/router-advertisements/options
                        container options {
                            description "Enter the options context";

                            ///nokia-conf/configure/service/vprn/subscriber-interface/group-interface/ipv6/router-advertisements/options/current-hop-limit
                            leaf current-hop-limit {
                                type uint32 {
                                    range "0..255";
                                }
                                default "64";
                                description "Hop limit to be advertised";
                            }

                            ///nokia-conf/configure/service/vprn/subscriber-interface/group-interface/ipv6/router-advertisements/options/managed-configuration
                            leaf managed-configuration {
                                type boolean;
                                default "false";
                                description "Managed address configuration flag";
                            }

                            ///nokia-conf/configure/service/vprn/subscriber-interface/group-interface/ipv6/router-advertisements/options/mtu
                            leaf mtu {
                                type union {
                                    type uint32 {
                                        range "1280..9212";
                                    }
                                    type enumeration {
                                        enum not-included                   { value 0; }
                                    }
                                }
                                units "bytes";
                                default "not-included";
                                description "Advertised MTU value";
                            }

                            ///nokia-conf/configure/service/vprn/subscriber-interface/group-interface/ipv6/router-advertisements/options/other-stateful-configuration
                            leaf other-stateful-configuration {
                                type boolean;
                                default "false";
                                description "Other stateful configuration flag";
                            }

                            ///nokia-conf/configure/service/vprn/subscriber-interface/group-interface/ipv6/router-advertisements/options/reachable-time
                            leaf reachable-time {
                                type types-sros:time-duration {
                                    range "0..3600000";
                                }
                                units "milliseconds";
                                default "0";
                                description "Reachable time for advertisements";
                            }

                            ///nokia-conf/configure/service/vprn/subscriber-interface/group-interface/ipv6/router-advertisements/options/retransmit-timer
                            leaf retransmit-timer {
                                type uint32 {
                                    range "0..1800000";
                                }
                                units "seconds";
                                default "0";
                                description "Retransmit time in router advertisements from interface";
                            }

                            ///nokia-conf/configure/service/vprn/subscriber-interface/group-interface/ipv6/router-advertisements/options/router-lifetime
                            leaf router-lifetime {
                                type union {
                                    type types-sros:time-duration {
                                        range "2700..9000";
                                    }
                                    type enumeration {
                                        enum no-default-router              { value 0; }
                                    }
                                }
                                units "seconds";
                                default "4500";
                                description "Router lifetime";
                            }

                            ///nokia-conf/configure/service/vprn/subscriber-interface/group-interface/ipv6/router-advertisements/options/dns
                            container dns {
                                description "Enter the dns context";

                                ///nokia-conf/configure/service/vprn/subscriber-interface/group-interface/ipv6/router-advertisements/options/dns/include-rdnss
                                leaf include-rdnss {
                                    type boolean;
                                    default "false";
                                    description "Include the RDNSS server option 25";
                                }

                                ///nokia-conf/configure/service/vprn/subscriber-interface/group-interface/ipv6/router-advertisements/options/dns/rdnss-lifetime
                                leaf rdnss-lifetime {
                                    type union {
                                        type types-sros:time-duration {
                                            range "900..3600";
                                        }
                                        type enumeration {
                                            enum infinite                       { value -1; }
                                        }
                                    }
                                    units "seconds";
                                    default "3600";
                                    description "Maximum time for the RDNSS address to remain valid";
                                }

                            } // container dns

                        } // container options

                        ///nokia-conf/configure/service/vprn/subscriber-interface/group-interface/ipv6/router-advertisements/prefix-options
                        container prefix-options {
                            description "Enter the prefix-options context";

                            ///nokia-conf/configure/service/vprn/subscriber-interface/group-interface/ipv6/router-advertisements/prefix-options/autonomous
                            leaf autonomous {
                                type boolean;
                                default "false";
                                description "Value of the autonomous flag";
                            }

                            ///nokia-conf/configure/service/vprn/subscriber-interface/group-interface/ipv6/router-advertisements/prefix-options/on-link
                            leaf on-link {
                                type boolean;
                                default "true";
                                description "Assign the prefix to an interface on the specified link";
                            }

                            ///nokia-conf/configure/service/vprn/subscriber-interface/group-interface/ipv6/router-advertisements/prefix-options/preferred-lifetime
                            leaf preferred-lifetime {
                                type types-submgt:router-advertisement-prefix-options-lifetime;
                                units "seconds";
                                default "3600";
                                description "Time for a prefix to remain preferred";
                            }

                            ///nokia-conf/configure/service/vprn/subscriber-interface/group-interface/ipv6/router-advertisements/prefix-options/valid-lifetime
                            leaf valid-lifetime {
                                type types-submgt:router-advertisement-prefix-options-lifetime;
                                units "seconds";
                                default "86400";
                                description "Time for a prefix to remain valid";
                            }

                        } // container prefix-options

                    } // container router-advertisements

                    ///nokia-conf/configure/service/vprn/subscriber-interface/group-interface/ipv6/router-solicit
                    container router-solicit {
                        when "../../type = 'plain' or ../../type = 'lns' or ../../type = 'wlan-gw'" {
                            description "invalid group interface type";
                        }
                        description "Enable the router-solicit context";

                        ///nokia-conf/configure/service/vprn/subscriber-interface/group-interface/ipv6/router-solicit/admin-state
                        leaf admin-state {
                            type types-sros:admin-state;
                            default "disable";
                            description "Administrative state of router-solicit authentication";
                        }

                        ///nokia-conf/configure/service/vprn/subscriber-interface/group-interface/ipv6/router-solicit/inactivity-timer
                        leaf inactivity-timer {
                            type union {
                                type types-sros:time-duration {
                                    range "1..31536000";
                                }
                                type enumeration {
                                    enum infinite                       { value -1; }
                                }
                            }
                            units "seconds";
                            default "300";
                            description "Time before an inactive host is removed";
                        }

                        ///nokia-conf/configure/service/vprn/subscriber-interface/group-interface/ipv6/router-solicit/min-auth-interval
                        leaf min-auth-interval {
                            type types-sros:time-duration {
                                range "1..360000";
                            }
                            units "seconds";
                            default "300";
                            description "Minimum time between successive authentication attempts";
                        }

                        ///nokia-conf/configure/service/vprn/subscriber-interface/group-interface/ipv6/router-solicit/user-db
                        leaf user-db {
                            type leafref {
                                path "../../../../../../../subscriber-mgmt/local-user-db/name";
                            }
                            description "Local user database used for authentication";
                        }

                        ///nokia-conf/configure/service/vprn/subscriber-interface/group-interface/ipv6/router-solicit/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/ipv6/router-solicit/apply-groups-exclude
                        leaf-list apply-groups-exclude {
                            type leafref {
                                path "../../../../../../../groups/group/name";
                            }
                            max-elements 8;
                            ordered-by user;
                            description "Exclude a configuration group at this level";
                        }

                    } // container router-solicit

                } // container ipv6

                ///nokia-conf/configure/service/vprn/subscriber-interface/group-interface/cflowd-parameters
                container cflowd-parameters {
                    description "Enter the cflowd-parameters context";

                    ///nokia-conf/configure/service/vprn/subscriber-interface/group-interface/cflowd-parameters/sampling
                    list sampling {
                        key "sampling-type";
                        description "Enter the sampling list instance";

                        ///nokia-conf/configure/service/vprn/subscriber-interface/group-interface/cflowd-parameters/sampling/sampling-type
                        leaf sampling-type {
                            type types-router:cflowd-sampling;
                            description "Traffic sampling type";
                        }

                        ///nokia-conf/configure/service/vprn/subscriber-interface/group-interface/cflowd-parameters/sampling/type
                        leaf type {
                            when "not(../sampling-type = 'both')";
                            type enumeration {
                                enum acl                            { value 1; }
                                enum interface                      { value 2; }
                            }
                            mandatory true;
                            description "Type of cflowd analysis";
                        }

                        ///nokia-conf/configure/service/vprn/subscriber-interface/group-interface/cflowd-parameters/sampling/direction
                        leaf direction {
                            type enumeration {
                                enum ingress-only                   { value 1; }
                                enum egress-only                    { value 2; }
                                enum both                           { value 3; }
                            }
                            default "ingress-only";
                            description "Direction of traffic for cflowd sampling";
                        }

                        ///nokia-conf/configure/service/vprn/subscriber-interface/group-interface/cflowd-parameters/sampling/sample-profile
                        leaf sample-profile {
                            type union {
                                type enumeration {
                                    enum 1                              { value 1; }
                                }
                                type uint32;
                            }
                            description "Sample profile ID";
                        }

                        ///nokia-conf/configure/service/vprn/subscriber-interface/group-interface/cflowd-parameters/sampling/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/cflowd-parameters/sampling/apply-groups-exclude
                        leaf-list apply-groups-exclude {
                            type leafref {
                                path "../../../../../../../groups/group/name";
                            }
                            max-elements 8;
                            ordered-by user;
                            description "Exclude a configuration group at this level";
                        }

                    } // list sampling

                } // container cflowd-parameters

                ///nokia-conf/configure/service/vprn/subscriber-interface/group-interface/ipoe-linking
                container ipoe-linking {
                    when "../type = 'plain' or ../type = 'lns' or ../type = 'wlan-gw'" {
                        description "invalid group interface type";
                    }
                    description "Enable the ipoe-linking context";

                    ///nokia-conf/configure/service/vprn/subscriber-interface/group-interface/ipoe-linking/admin-state
                    leaf admin-state {
                        type types-sros:admin-state;
                        default "disable";
                        description "Administrative state of IPoE host linking";
                    }

                    ///nokia-conf/configure/service/vprn/subscriber-interface/group-interface/ipoe-linking/gratuitous-router-advertisement
                    leaf gratuitous-router-advertisement {
                        type boolean;
                        sros-ext:auto-restart-to-modify;
                        default "false";
                        description "Send unsolicited router advertisement after DHCP setup";
                    }

                    ///nokia-conf/configure/service/vprn/subscriber-interface/group-interface/ipoe-linking/shared-circuit-id
                    leaf shared-circuit-id {
                        when "not(../../type = 'wlan-gw')" {
                            description "group interface type must not be 'wlan-gw'";
                        }
                        type boolean;
                        sros-ext:auto-restart-to-modify;
                        default "false";
                        description "Enable circuit ID in DHCPv4 Option82 to validate DHCPv6";
                    }

                    ///nokia-conf/configure/service/vprn/subscriber-interface/group-interface/ipoe-linking/apply-groups
                    leaf-list apply-groups {
                        type leafref {
                            path "../../../../../../groups/group/name";
                        }
                        max-elements 8;
                        ordered-by user;
                        sros-ext:auto-restart-to-modify;
                        description "Apply a configuration group at this level";
                    }

                    ///nokia-conf/configure/service/vprn/subscriber-interface/group-interface/ipoe-linking/apply-groups-exclude
                    leaf-list apply-groups-exclude {
                        type leafref {
                            path "../../../../../../groups/group/name";
                        }
                        max-elements 8;
                        ordered-by user;
                        sros-ext:auto-restart-to-modify;
                        description "Exclude a configuration group at this level";
                    }

                } // container ipoe-linking

                ///nokia-conf/configure/service/vprn/subscriber-interface/group-interface/ipoe-session
                container ipoe-session {
                    when "../type = 'plain' or ../type = 'wlan-gw' or ../type = 'gtp' or ../type = 'bonding'" {
                        description "invalid group interface type";
                    }
                    description "Enter the ipoe-session context";

                    ///nokia-conf/configure/service/vprn/subscriber-interface/group-interface/ipoe-session/admin-state
                    leaf admin-state {
                        when "../../type = 'plain'" {
                            description "group interface type must be 'plain'";
                        }
                        type types-sros:admin-state;
                        description "Administrative state of IPoE session management";
                    }

                    ///nokia-conf/configure/service/vprn/subscriber-interface/group-interface/ipoe-session/description
                    leaf description {
                        type types-sros:description;
                        description "Text description";
                    }

                    ///nokia-conf/configure/service/vprn/subscriber-interface/group-interface/ipoe-session/ipoe-session-policy
                    leaf ipoe-session-policy {
                        when "../../type = 'plain'" {
                            description "group interface type must be 'plain'";
                        }
                        type leafref {
                            path "../../../../../../subscriber-mgmt/ipoe-session-policy/name";
                        }
                        sros-ext:auto-restart-to-modify;
                        description "IPoE Session policy to be used for new sessions";
                    }

                    ///nokia-conf/configure/service/vprn/subscriber-interface/group-interface/ipoe-session/user-db
                    leaf user-db {
                        type leafref {
                            path "../../../../../../subscriber-mgmt/local-user-db/name";
                        }
                        sros-ext:auto-restart-to-modify;
                        description "Local user database for IPoE session authentication";
                    }

                    ///nokia-conf/configure/service/vprn/subscriber-interface/group-interface/ipoe-session/session-limit
                    leaf session-limit {
                        type uint32 {
                            range "1..500000";
                        }
                        description "Maximum number of sessions on this group interface";
                    }

                    ///nokia-conf/configure/service/vprn/subscriber-interface/group-interface/ipoe-session/sap-session-limit
                    leaf sap-session-limit {
                        when "../../type = 'plain'" {
                            description "group interface type must be 'plain'";
                        }
                        type uint32 {
                            range "1..131071";
                        }
                        description "Maximum number of sessions per SAP";
                    }

                    ///nokia-conf/configure/service/vprn/subscriber-interface/group-interface/ipoe-session/min-auth-interval
                    leaf min-auth-interval {
                        type types-submgt:ipoe-session-min-auth-interval;
                        units "seconds";
                        default "infinite";
                        description "Minimum time between two authentication attempts";
                    }

                    ///nokia-conf/configure/service/vprn/subscriber-interface/group-interface/ipoe-session/radius-session-timeout
                    leaf radius-session-timeout {
                        when "../../type = 'wlan-gw'" {
                            description "group interface type must be 'wlan-gw'";
                        }
                        type types-submgt:ipoe-session-radius-session-timeout;
                        description "Session timeout attribute to be interpreted";
                    }

                    ///nokia-conf/configure/service/vprn/subscriber-interface/group-interface/ipoe-session/stateless-redundancy
                    leaf stateless-redundancy {
                        when "not(../../type = 'wlan-gw')" {
                            description "group interface type must not be 'wlan-gw'";
                        }
                        type boolean;
                        sros-ext:auto-restart-to-modify;
                        default "false";
                        description "Remove IPoE sessions when the system becomes stand-by in a stateless multi-chassis redundancy setup";
                    }

                    ///nokia-conf/configure/service/vprn/subscriber-interface/group-interface/ipoe-session/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/ipoe-session/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/ipoe-session/force-auth
                    container force-auth {
                        description "Enter the force-auth context";

                        ///nokia-conf/configure/service/vprn/subscriber-interface/group-interface/ipoe-session/force-auth/cid-change
                        leaf cid-change {
                            when "../../../type = 'plain' or ../../../type = 'wlan-gw'" {
                                description "invalid group interface type";
                            }
                            type boolean;
                            description "Ignore min-auth-interval when circuit ID changed";
                        }

                        ///nokia-conf/configure/service/vprn/subscriber-interface/group-interface/ipoe-session/force-auth/rid-change
                        leaf rid-change {
                            when "../../../type = 'plain' or ../../../type = 'wlan-gw'" {
                                description "invalid group interface type";
                            }
                            type boolean;
                            description "Ignore min-auth-interval when remote ID changed";
                        }

                    } // container force-auth

                } // container ipoe-session

                ///nokia-conf/configure/service/vprn/subscriber-interface/group-interface/brg
                container brg {
                    when "../type = 'plain'" {
                        description "group interface type must be 'plain'";
                    }
                    description "Enter the brg context";

                    ///nokia-conf/configure/service/vprn/subscriber-interface/group-interface/brg/admin-state
                    leaf admin-state {
                        type types-sros:admin-state;
                        default "disable";
                        description "Administrative state of BRG";
                    }

                    ///nokia-conf/configure/service/vprn/subscriber-interface/group-interface/brg/authenticated-brg-only
                    leaf authenticated-brg-only {
                        type boolean;
                        sros-ext:auto-restart-to-modify;
                        default "false";
                        description "Allow BRGs that have been pre-authenticated";
                    }

                    ///nokia-conf/configure/service/vprn/subscriber-interface/group-interface/brg/default-brg-profile
                    leaf default-brg-profile {
                        type leafref {
                            path "../../../../../../subscriber-mgmt/vrgw/brg-profile/brg-profile-name";
                        }
                        sros-ext:auto-restart-to-modify;
                        description "Default BRG profile for new BRGs";
                    }

                    ///nokia-conf/configure/service/vprn/subscriber-interface/group-interface/brg/apply-groups
                    leaf-list apply-groups {
                        type leafref {
                            path "../../../../../../groups/group/name";
                        }
                        max-elements 8;
                        ordered-by user;
                        sros-ext:auto-restart-to-modify;
                        description "Apply a configuration group at this level";
                    }

                    ///nokia-conf/configure/service/vprn/subscriber-interface/group-interface/brg/apply-groups-exclude
                    leaf-list apply-groups-exclude {
                        type leafref {
                            path "../../../../../../groups/group/name";
                        }
                        max-elements 8;
                        ordered-by user;
                        sros-ext:auto-restart-to-modify;
                        description "Exclude a configuration group at this level";
                    }

                } // container brg

                ///nokia-conf/configure/service/vprn/subscriber-interface/group-interface/pppoe
                container pppoe {
                    when "../type = 'plain'" {
                        description "group interface type must be 'plain'";
                    }
                    description "Enter the pppoe context";

                    ///nokia-conf/configure/service/vprn/subscriber-interface/group-interface/pppoe/admin-state
                    leaf admin-state {
                        type types-sros:admin-state;
                        default "disable";
                        description "Administrative state of PPPoE";
                    }

                    ///nokia-conf/configure/service/vprn/subscriber-interface/group-interface/pppoe/description
                    leaf description {
                        type types-sros:description;
                        description "Text description";
                    }

                    ///nokia-conf/configure/service/vprn/subscriber-interface/group-interface/pppoe/anti-spoof
                    leaf anti-spoof {
                        type types-submgt:pppoe-anti-spoof;
                        default "mac-sid";
                        description "PPPoE anti-spoof filtering";
                    }

                    ///nokia-conf/configure/service/vprn/subscriber-interface/group-interface/pppoe/policy
                    leaf policy {
                        type leafref {
                            path "../../../../../../subscriber-mgmt/ppp-policy/name";
                        }
                        description "PPPoE policy";
                    }

                    ///nokia-conf/configure/service/vprn/subscriber-interface/group-interface/pppoe/session-limit
                    leaf session-limit {
                        type uint32 {
                            range "1..333823";
                        }
                        default "1";
                        description "Maximum PPPoE sessions";
                    }

                    ///nokia-conf/configure/service/vprn/subscriber-interface/group-interface/pppoe/sap-session-limit
                    leaf sap-session-limit {
                        type uint32 {
                            range "1..131071";
                        }
                        default "1";
                        description "Maximum PPPoE sessions per SAP";
                    }

                    ///nokia-conf/configure/service/vprn/subscriber-interface/group-interface/pppoe/python-policy
                    leaf python-policy {
                        type leafref {
                            path "../../../../../../python/python-policy/name";
                        }
                        description "Python policy used to modify PPPoE packets";
                    }

                    ///nokia-conf/configure/service/vprn/subscriber-interface/group-interface/pppoe/user-db
                    leaf user-db {
                        type leafref {
                            path "../../../../../../subscriber-mgmt/local-user-db/name";
                        }
                        sros-ext:auto-restart-to-modify;
                        description "Local user database for authentication";
                    }

                    ///nokia-conf/configure/service/vprn/subscriber-interface/group-interface/pppoe/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/pppoe/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/pppoe/dhcp-client
                    container dhcp-client {
                        description "Enter the dhcp-client context";

                        ///nokia-conf/configure/service/vprn/subscriber-interface/group-interface/pppoe/dhcp-client/client-id
                        leaf client-id {
                            type enumeration {
                                enum mac-pppoe-session-id           { value 2; }
                            }
                            description "Type of information that DHCP option 61 contains";
                        }

                    } // container dhcp-client

                } // container pppoe

                ///nokia-conf/configure/service/vprn/subscriber-interface/group-interface/data-trigger
                container data-trigger {
                    when "../type = 'plain'" {
                        description "group interface type must be 'plain'";
                    }
                    description "Enter the data-trigger context";

                    ///nokia-conf/configure/service/vprn/subscriber-interface/group-interface/data-trigger/admin-state
                    leaf admin-state {
                        type types-sros:admin-state;
                        default "disable";
                        description "Administrative state of data-triggered host creation";
                    }

                    ///nokia-conf/configure/service/vprn/subscriber-interface/group-interface/data-trigger/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/data-trigger/apply-groups-exclude
                    leaf-list apply-groups-exclude {
                        type leafref {
                            path "../../../../../../groups/group/name";
                        }
                        max-elements 8;
                        ordered-by user;
                        description "Exclude a configuration group at this level";
                    }

                } // container data-trigger

                ///nokia-conf/configure/service/vprn/subscriber-interface/group-interface/local-address-assignment
                container local-address-assignment {
                    description "Enable the local-address-assignment context";

                    ///nokia-conf/configure/service/vprn/subscriber-interface/group-interface/local-address-assignment/admin-state
                    leaf admin-state {
                        type types-sros:admin-state;
                        default "disable";
                        description "Administrative state of Local Address Assignment";
                    }

                    ///nokia-conf/configure/service/vprn/subscriber-interface/group-interface/local-address-assignment/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/local-address-assignment/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/local-address-assignment/ipv4
                    container ipv4 {
                        description "Enter the ipv4 context";

                        ///nokia-conf/configure/service/vprn/subscriber-interface/group-interface/local-address-assignment/ipv4/server
                        leaf server {
                            when "../../../type = 'plain' or ../../../type = 'lns' or ../../../type = 'gtp' or ../../../type = 'bonding'" {
                                description "invalid group interface type";
                            }
                            type leafref {
                                path "../../../../../dhcp-server/dhcpv4/name";
                            }
                            description "Local DHCPv4 server for local pools management";
                        }

                        ///nokia-conf/configure/service/vprn/subscriber-interface/group-interface/local-address-assignment/ipv4/default-pool
                        leaf-list default-pool {
                            when "../../../type = 'plain' or ../../../type = 'lns'" {
                                description "invalid group interface type";
                            }
                            type types-sros:named-item;
                            max-elements 2;
                            ordered-by user;
                            description "Default pools";
                        }

                        ///nokia-conf/configure/service/vprn/subscriber-interface/group-interface/local-address-assignment/ipv4/client-applications
                        container client-applications {
                            description "Enter the client-applications context";

                            ///nokia-conf/configure/service/vprn/subscriber-interface/group-interface/local-address-assignment/ipv4/client-applications/ppp
                            leaf ppp {
                                when "../../../../type = 'plain' or ../../../../type = 'lns' or ../../../../type = 'gtp' or ../../../../type = 'bonding'" {
                                    description "invalid group interface type";
                                }
                                type boolean;
                                default "false";
                                description "Request local addresses for PPP IPCP hosts";
                            }

                            ///nokia-conf/configure/service/vprn/subscriber-interface/group-interface/local-address-assignment/ipv4/client-applications/ipoe
                            leaf ipoe {
                                when "../../../../type = 'gtp' or ../../../../type = 'bonding'" {
                                    description "invalid group interface type";
                                }
                                type boolean;
                                default "false";
                                description "Request local addresses for non-DHCP/managed IPoE hosts";
                            }

                        } // container client-applications

                    } // container ipv4

                    ///nokia-conf/configure/service/vprn/subscriber-interface/group-interface/local-address-assignment/ipv6
                    container ipv6 {
                        description "Enter the ipv6 context";

                        ///nokia-conf/configure/service/vprn/subscriber-interface/group-interface/local-address-assignment/ipv6/server
                        leaf server {
                            type leafref {
                                path "../../../../../dhcp-server/dhcpv6/name";
                            }
                            description "Local DHCPv6 server for local pools management";
                        }

                        ///nokia-conf/configure/service/vprn/subscriber-interface/group-interface/local-address-assignment/ipv6/client-applications
                        container client-applications {
                            description "Enter the client-applications context";

                            ///nokia-conf/configure/service/vprn/subscriber-interface/group-interface/local-address-assignment/ipv6/client-applications/ppp-slaac
                            leaf ppp-slaac {
                                when "../../../../type = 'plain' or ../../../../type = 'lns' or ../../../../type = 'gtp' or ../../../../type = 'bonding'" {
                                    description "invalid group interface type";
                                }
                                type boolean;
                                default "false";
                                description "Request local addresses for PPP SLAAC hosts";
                            }

                            ///nokia-conf/configure/service/vprn/subscriber-interface/group-interface/local-address-assignment/ipv6/client-applications/ipoe-wan
                            leaf ipoe-wan {
                                type boolean;
                                default "false";
                                description "Request local addresses for IPoE IA NA hosts";
                            }

                            ///nokia-conf/configure/service/vprn/subscriber-interface/group-interface/local-address-assignment/ipv6/client-applications/ipoe-slaac
                            leaf ipoe-slaac {
                                type boolean;
                                default "false";
                                description "Request local addresses for IPoE SLAAC hosts";
                            }

                        } // container client-applications

                    } // container ipv6

                } // container local-address-assignment

                ///nokia-conf/configure/service/vprn/subscriber-interface/group-interface/srrp
                list srrp {
                    when "../type = 'plain' or ../type = 'lns'" {
                        description "invalid group interface type";
                    }
                    key "srrp-id";
                    max-elements 1;
                    description "Enter the srrp list instance";

                    ///nokia-conf/configure/service/vprn/subscriber-interface/group-interface/srrp/srrp-id
                    leaf srrp-id {
                        type uint32 {
                            range "1..4294967295";
                        }
                        description "SRRP instance ID";
                    }

                    ///nokia-conf/configure/service/vprn/subscriber-interface/group-interface/srrp/admin-state
                    leaf admin-state {
                        type types-sros:admin-state;
                        default "disable";
                        description "Administrative state of SRRP";
                    }

                    ///nokia-conf/configure/service/vprn/subscriber-interface/group-interface/srrp/description
                    leaf description {
                        type types-sros:description;
                        description "Text description";
                    }

                    ///nokia-conf/configure/service/vprn/subscriber-interface/group-interface/srrp/gw-mac
                    leaf gw-mac {
                        type types-sros:mac-unicast-address;
                        description "Gateway MAC address";
                    }

                    ///nokia-conf/configure/service/vprn/subscriber-interface/group-interface/srrp/keep-alive-interval
                    leaf keep-alive-interval {
                        type uint32 {
                            range "1..100";
                        }
                        units "deciseconds";
                        default "10";
                        description "Interval between SRRP advertisements";
                    }

                    ///nokia-conf/configure/service/vprn/subscriber-interface/group-interface/srrp/message-path
                    leaf message-path {
                        type leafref {
                            path "../../sap/sap-id";
                        }
                        sros-ext:auto-restart-to-modify;
                        description "SAP to use as the SRRP message path";
                    }

                    ///nokia-conf/configure/service/vprn/subscriber-interface/group-interface/srrp/policy
                    leaf-list policy {
                        type leafref {
                            path "../../../../../../vrrp/policy/policy-id";
                        }
                        max-elements 2;
                        ordered-by user;
                        description "VRRP priority control policy associated with the SRRP";
                    }

                    ///nokia-conf/configure/service/vprn/subscriber-interface/group-interface/srrp/priority
                    leaf priority {
                        type uint32 {
                            range "1..254";
                        }
                        default "100";
                        description "Priority for this interface at this level";
                    }

                    ///nokia-conf/configure/service/vprn/subscriber-interface/group-interface/srrp/send-fib-population-packets
                    leaf send-fib-population-packets {
                        type enumeration {
                            enum all                            { value 1; }
                            enum outer-tag-only                 { value 2; }
                        }
                        default "all";
                        description "Mode used to send FIB population packets on switchover";
                    }

                    ///nokia-conf/configure/service/vprn/subscriber-interface/group-interface/srrp/preempt
                    leaf preempt {
                        type boolean;
                        default "true";
                        description "Allow the SRRP instance to override an existing master";
                    }

                    ///nokia-conf/configure/service/vprn/subscriber-interface/group-interface/srrp/one-garp-per-sap
                    leaf one-garp-per-sap {
                        type boolean;
                        default "false";
                        description "Send one gratuitous ARP to each SAP";
                    }

                    ///nokia-conf/configure/service/vprn/subscriber-interface/group-interface/srrp/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/srrp/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/srrp/monitor-oper-group
                    container monitor-oper-group {
                        description "Enter the monitor-oper-group context";

                        ///nokia-conf/configure/service/vprn/subscriber-interface/group-interface/srrp/monitor-oper-group/group-name
                        leaf group-name {
                            type leafref {
                                path "../../../../../../oper-group/name";
                            }
                            description "Operational group name";
                        }

                        ///nokia-conf/configure/service/vprn/subscriber-interface/group-interface/srrp/monitor-oper-group/priority-step
                        leaf priority-step {
                            type uint8 {
                                range "1..10";
                            }
                            description "Step value to change priority of SRRP instance";
                        }

                    } // container monitor-oper-group

                    ///nokia-conf/configure/service/vprn/subscriber-interface/group-interface/srrp/bfd-liveness
                    container bfd-liveness {
                        presence "Enable the bfd-liveness context";
                        description "Enable the bfd-liveness context";

                        ///nokia-conf/configure/service/vprn/subscriber-interface/group-interface/srrp/bfd-liveness/dest-ip
                        leaf dest-ip {
                            type types-sros:ipv4-address;
                            sros-ext:immutable;
                            mandatory true;
                            description "Destination IPv4 prefix";
                        }

                        ///nokia-conf/configure/service/vprn/subscriber-interface/group-interface/srrp/bfd-liveness/service-name
                        leaf service-name {
                            type types-services:service-name;
                            sros-ext:immutable;
                            description "Administrative service name";
                        }

                        ///nokia-conf/configure/service/vprn/subscriber-interface/group-interface/srrp/bfd-liveness/interface-name
                        leaf interface-name {
                            type types-sros:interface-name;
                            sros-ext:immutable;
                            mandatory true;
                            description "Name of the interface running BFD";
                        }

                        ///nokia-conf/configure/service/vprn/subscriber-interface/group-interface/srrp/bfd-liveness/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/srrp/bfd-liveness/apply-groups-exclude
                        leaf-list apply-groups-exclude {
                            type leafref {
                                path "../../../../../../../groups/group/name";
                            }
                            max-elements 8;
                            ordered-by user;
                            description "Exclude a configuration group at this level";
                        }

                    } // container bfd-liveness

                } // list srrp

                ///nokia-conf/configure/service/vprn/subscriber-interface/group-interface/sap-parameters
                container sap-parameters {
                    when "../type = 'lns' or ../type = 'wlan-gw' or ../type = 'gtp' or ../type = 'bonding'" {
                        description "invalid group interface type";
                    }
                    description "Enter the sap-parameters context";

                    ///nokia-conf/configure/service/vprn/subscriber-interface/group-interface/sap-parameters/description
                    leaf description {
                        type types-sros:description;
                        description "Text description";
                    }

                    ///nokia-conf/configure/service/vprn/subscriber-interface/group-interface/sap-parameters/anti-spoof
                    leaf anti-spoof {
                        when "../../type = 'wlan-gw'" {
                            description "group interface type must be 'wlan-gw'";
                        }
                        type enumeration {
                            enum ip-mac                         { value 3; }
                            enum nh-mac                         { value 4; }
                        }
                        default "ip-mac";
                        description "Anti-spoof type of the SAP";
                    }

                    ///nokia-conf/configure/service/vprn/subscriber-interface/group-interface/sap-parameters/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/sap-parameters/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/sap-parameters/sub-sla-mgmt
                    container sub-sla-mgmt {
                        description "Enter the sub-sla-mgmt context";

                        ///nokia-conf/configure/service/vprn/subscriber-interface/group-interface/sap-parameters/sub-sla-mgmt/sub-ident-policy
                        leaf sub-ident-policy {
                            type leafref {
                                path "../../../../../../../subscriber-mgmt/sub-ident-policy/name";
                            }
                            description "Subscriber identification policy";
                        }

                        ///nokia-conf/configure/service/vprn/subscriber-interface/group-interface/sap-parameters/sub-sla-mgmt/defaults
                        container defaults {
                            description "Enter the defaults context";

                            ///nokia-conf/configure/service/vprn/subscriber-interface/group-interface/sap-parameters/sub-sla-mgmt/defaults/sub-profile
                            leaf sub-profile {
                                type leafref {
                                    path "../../../../../../../../subscriber-mgmt/sub-profile/name";
                                }
                                description "Default subscriber profile";
                            }

                            ///nokia-conf/configure/service/vprn/subscriber-interface/group-interface/sap-parameters/sub-sla-mgmt/defaults/app-profile
                            leaf app-profile {
                                type leafref {
                                    path "../../../../../../../../application-assurance/group/partition/policy/app-profile/app-profile-name";
                                }
                                description "Default application profile name";
                            }

                            ///nokia-conf/configure/service/vprn/subscriber-interface/group-interface/sap-parameters/sub-sla-mgmt/defaults/sla-profile
                            leaf sla-profile {
                                type leafref {
                                    path "../../../../../../../../subscriber-mgmt/sla-profile/name";
                                }
                                description "Default SLA profile";
                            }

                            ///nokia-conf/configure/service/vprn/subscriber-interface/group-interface/sap-parameters/sub-sla-mgmt/defaults/subscriber-id
                            container subscriber-id {
                                description "Enter the subscriber-id context";

                                ///nokia-conf/configure/service/vprn/subscriber-interface/group-interface/sap-parameters/sub-sla-mgmt/defaults/subscriber-id/subscriber-id
                                choice subscriber-id {
                                    ///nokia-conf/configure/service/vprn/subscriber-interface/group-interface/sap-parameters/sub-sla-mgmt/defaults/subscriber-id/subscriber-id/string
                                    case string {

                                        ///nokia-conf/configure/service/vprn/subscriber-interface/group-interface/sap-parameters/sub-sla-mgmt/defaults/subscriber-id/subscriber-id/string/string
                                        leaf string {
                                            type types-submgt:subscriber-id;
                                            description "String to be used as default subscriber ID";
                                        }

                                    }
                                    ///nokia-conf/configure/service/vprn/subscriber-interface/group-interface/sap-parameters/sub-sla-mgmt/defaults/subscriber-id/subscriber-id/auto-id
                                    case auto-id {

                                        ///nokia-conf/configure/service/vprn/subscriber-interface/group-interface/sap-parameters/sub-sla-mgmt/defaults/subscriber-id/subscriber-id/auto-id/auto-id
                                        leaf auto-id {
                                            type empty;
                                            description "Subscriber ID that is autogenerated";
                                        }

                                    }
                                }
                            } // container subscriber-id

                        } // container defaults

                    } // container sub-sla-mgmt

                } // container sap-parameters

                ///nokia-conf/configure/service/vprn/subscriber-interface/group-interface/bonding-parameters
                container bonding-parameters {
                    when "../type = 'bonding'" {
                        description "group interface type must be 'bonding'";
                    }
                    description "Enable the bonding-parameters context";

                    ///nokia-conf/configure/service/vprn/subscriber-interface/group-interface/bonding-parameters/admin-state
                    leaf admin-state {
                        type types-sros:admin-state;
                        default "disable";
                        description "Administrative state of ESM connection bonding";
                    }

                    ///nokia-conf/configure/service/vprn/subscriber-interface/group-interface/bonding-parameters/fpe
                    leaf fpe {
                        type leafref {
                            path "../../../../../../fwd-path-ext/fpe/fpe-id";
                        }
                        sros-ext:auto-restart-to-modify;
                        description "FPE that provisions bonding functionality";
                    }

                    ///nokia-conf/configure/service/vprn/subscriber-interface/group-interface/bonding-parameters/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/bonding-parameters/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/bonding-parameters/multicast
                    container multicast {
                        description "Enter the multicast context";

                        ///nokia-conf/configure/service/vprn/subscriber-interface/group-interface/bonding-parameters/multicast/connection
                        leaf connection {
                            type types-submgt:multicast-bonding-connection;
                            sros-ext:auto-restart-to-modify;
                            default "use-incoming";
                            description "Multicast connection";
                        }

                    } // container multicast

                    ///nokia-conf/configure/service/vprn/subscriber-interface/group-interface/bonding-parameters/connection
                    list connection {
                        key "connection-index";
                        description "Enter the connection list instance";

                        ///nokia-conf/configure/service/vprn/subscriber-interface/group-interface/bonding-parameters/connection/connection-index
                        leaf connection-index {
                            type types-submgt:bonding-connection-index;
                            description "Bonding connection index";
                        }

                        ///nokia-conf/configure/service/vprn/subscriber-interface/group-interface/bonding-parameters/connection/service
                        leaf service {
                            type types-services:service-name;
                            description "Connection service";
                        }

                        ///nokia-conf/configure/service/vprn/subscriber-interface/group-interface/bonding-parameters/connection/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/bonding-parameters/connection/apply-groups-exclude
                        leaf-list apply-groups-exclude {
                            type leafref {
                                path "../../../../../../../groups/group/name";
                            }
                            max-elements 8;
                            ordered-by user;
                            description "Exclude a configuration group at this level";
                        }

                    } // list connection

                } // container bonding-parameters

                ///nokia-conf/configure/service/vprn/subscriber-interface/group-interface/gtp-parameters
                container gtp-parameters {
                    when "../type = 'gtp'" {
                        description "group interface type must be 'gtp'";
                    }
                    description "Enter the gtp-parameters context";

                    ///nokia-conf/configure/service/vprn/subscriber-interface/group-interface/gtp-parameters/admin-state
                    leaf admin-state {
                        type types-sros:admin-state;
                        default "disable";
                        description "Administrative state of GTP access";
                    }

                    ///nokia-conf/configure/service/vprn/subscriber-interface/group-interface/gtp-parameters/fpe
                    leaf fpe {
                        type leafref {
                            path "../../../../../../fwd-path-ext/fpe/fpe-id";
                        }
                        sros-ext:auto-restart-to-modify;
                        description "PE that provisions the GTP user interface";
                    }

                    ///nokia-conf/configure/service/vprn/subscriber-interface/group-interface/gtp-parameters/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/gtp-parameters/apply-groups-exclude
                    leaf-list apply-groups-exclude {
                        type leafref {
                            path "../../../../../../groups/group/name";
                        }
                        max-elements 8;
                        ordered-by user;
                        description "Exclude a configuration group at this level";
                    }

                } // container gtp-parameters

                ///nokia-conf/configure/service/vprn/subscriber-interface/group-interface/wpp
                container wpp {
                    when "../type = 'plain'" {
                        description "group interface type must be 'plain'";
                    }
                    presence "Enable the wpp context";
                    description "Enable the wpp context";

                    ///nokia-conf/configure/service/vprn/subscriber-interface/group-interface/wpp/admin-state
                    leaf admin-state {
                        type types-sros:admin-state;
                        default "disable";
                        description "Administrative state of WPP";
                    }

                    ///nokia-conf/configure/service/vprn/subscriber-interface/group-interface/wpp/restore-to-initial-on-disconnect
                    leaf restore-to-initial-on-disconnect {
                        type boolean;
                        default "true";
                        description "Restore initial profiles after a host has disconnected";
                    }

                    ///nokia-conf/configure/service/vprn/subscriber-interface/group-interface/wpp/user-db
                    leaf user-db {
                        type leafref {
                            path "../../../../../../subscriber-mgmt/local-user-db/name";
                        }
                        description "User database";
                    }

                    ///nokia-conf/configure/service/vprn/subscriber-interface/group-interface/wpp/lease-time
                    leaf lease-time {
                        type types-sros:time-duration {
                            range "10..315446399";
                        }
                        default "600";
                        description "Lease time";
                    }

                    ///nokia-conf/configure/service/vprn/subscriber-interface/group-interface/wpp/triggered-hosts
                    leaf triggered-hosts {
                        type boolean;
                        default "false";
                        description "Enable/disable triggered hosts";
                    }

                    ///nokia-conf/configure/service/vprn/subscriber-interface/group-interface/wpp/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/wpp/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/wpp/portal
                    container portal {
                        description "Enter the portal context";

                        ///nokia-conf/configure/service/vprn/subscriber-interface/group-interface/wpp/portal/portal
                        choice portal {
                            ///nokia-conf/configure/service/vprn/subscriber-interface/group-interface/wpp/portal/portal/portal
                            case portal {

                                ///nokia-conf/configure/service/vprn/subscriber-interface/group-interface/wpp/portal/portal/portal/router-instance
                                leaf router-instance {
                                    type string;
                                    description "Virtual router instance of WPP portal for interface";
                                }

                                ///nokia-conf/configure/service/vprn/subscriber-interface/group-interface/wpp/portal/portal/portal/name
                                leaf name {
                                    type types-sros:named-item;
                                    description "Web portal server name";
                                }

                            }
                            ///nokia-conf/configure/service/vprn/subscriber-interface/group-interface/wpp/portal/portal/portal-group
                            case portal-group {

                                ///nokia-conf/configure/service/vprn/subscriber-interface/group-interface/wpp/portal/portal/portal-group/portal-group
                                leaf portal-group {
                                    type leafref {
                                        path "../../../../../../../aaa/wpp/portal-group/group-name";
                                    }
                                    description "WPP portal group for this interface";
                                }

                            }
                        }
                    } // container portal

                    ///nokia-conf/configure/service/vprn/subscriber-interface/group-interface/wpp/initial
                    container initial {
                        description "Enter the initial context";

                        ///nokia-conf/configure/service/vprn/subscriber-interface/group-interface/wpp/initial/sub-profile
                        leaf sub-profile {
                            type leafref {
                                path "../../../../../../../subscriber-mgmt/sub-profile/name";
                            }
                            description "Initial subscriber profile";
                        }

                        ///nokia-conf/configure/service/vprn/subscriber-interface/group-interface/wpp/initial/sla-profile
                        leaf sla-profile {
                            type leafref {
                                path "../../../../../../../subscriber-mgmt/sla-profile/name";
                            }
                            description "Initial SLA profile";
                        }

                        ///nokia-conf/configure/service/vprn/subscriber-interface/group-interface/wpp/initial/app-profile
                        leaf app-profile {
                            type leafref {
                                path "../../../../../../../application-assurance/group/partition/policy/app-profile/app-profile-name";
                            }
                            description "Initial application profile name";
                        }

                    } // container initial

                } // container wpp

                ///nokia-conf/configure/service/vprn/subscriber-interface/group-interface/sap
                list sap {
                    when "../type = 'plain'" {
                        description "group interface type must be 'plain'";
                    }
                    key "sap-id";
                    description "Enter the sap list instance";

                    ///nokia-conf/configure/service/vprn/subscriber-interface/group-interface/sap/sap-id
                    leaf sap-id {
                        type types-sros:sap;
                        description "SAP ID";
                    }

                    ///nokia-conf/configure/service/vprn/subscriber-interface/group-interface/sap/description
                    leaf description {
                        type types-sros:long-description;
                        description "Text description";
                    }

                    ///nokia-conf/configure/service/vprn/subscriber-interface/group-interface/sap/admin-state
                    leaf admin-state {
                        type types-sros:admin-state;
                        default "enable";
                        description "Administrative state of the SAP";
                    }

                    ///nokia-conf/configure/service/vprn/subscriber-interface/group-interface/sap/accounting-policy
                    leaf accounting-policy {
                        type leafref {
                            path "../../../../../../log/accounting-policy/policy-id";
                        }
                        description "Accounting policy";
                    }

                    ///nokia-conf/configure/service/vprn/subscriber-interface/group-interface/sap/anti-spoof
                    leaf anti-spoof {
                        type types-services:anti-spoof-option-ip;
                        description "Type of anti-spoof filtering";
                    }

                    ///nokia-conf/configure/service/vprn/subscriber-interface/group-interface/sap/app-profile
                    leaf app-profile {
                        type leafref {
                            path "../../../../../../application-assurance/group/partition/policy/app-profile/app-profile-name";
                        }
                        description "Application profile name";
                    }

                    ///nokia-conf/configure/service/vprn/subscriber-interface/group-interface/sap/calling-station-id
                    leaf calling-station-id {
                        type types-sros:string-not-all-spaces {
                            length "1..64";
                        }
                        description "Calling station ID";
                    }

                    ///nokia-conf/configure/service/vprn/subscriber-interface/group-interface/sap/collect-stats
                    leaf collect-stats {
                        type boolean;
                        default "false";
                        description "Collect accounting statistics";
                    }

                    ///nokia-conf/configure/service/vprn/subscriber-interface/group-interface/sap/dist-cpu-protection
                    leaf dist-cpu-protection {
                        type leafref {
                            path "../../../../../../system/security/dist-cpu-protection/policy/policy-name";
                        }
                        description "Distributed CPU protection policy for SAP";
                    }

                    ///nokia-conf/configure/service/vprn/subscriber-interface/group-interface/sap/host-admin-state
                    leaf host-admin-state {
                        type types-sros:admin-state;
                        default "enable";
                        description "Administrative state of the hosts";
                    }

                    ///nokia-conf/configure/service/vprn/subscriber-interface/group-interface/sap/host-lockout-policy
                    leaf host-lockout-policy {
                        type leafref {
                            path "../../../../../../subscriber-mgmt/host-lockout-policy/name";
                        }
                        description "Host lockout policy";
                    }

                    ///nokia-conf/configure/service/vprn/subscriber-interface/group-interface/sap/multi-service-site
                    leaf multi-service-site {
                        type leafref {
                            path "../../../../../customer/multi-service-site/multi-service-site-name";
                        }
                        description "Multi service site name";
                    }

                    ///nokia-conf/configure/service/vprn/subscriber-interface/group-interface/sap/apply-groups
                    leaf-list apply-groups {
                        type leafref {
                            path "../../../../../../groups/group/name";
                        }
                        max-elements 8;
                        ordered-by user;
                        description "Apply a configuration group at this level";
                    }

                    ///nokia-conf/configure/service/vprn/subscriber-interface/group-interface/sap/apply-groups-exclude
                    leaf-list apply-groups-exclude {
                        type leafref {
                            path "../../../../../../groups/group/name";
                        }
                        max-elements 8;
                        ordered-by user;
                        description "Exclude a configuration group at this level";
                    }

                    ///nokia-conf/configure/service/vprn/subscriber-interface/group-interface/sap/oper-group-association
                    choice oper-group-association {
                        ///nokia-conf/configure/service/vprn/subscriber-interface/group-interface/sap/oper-group-association/oper-group
                        case oper-group {

                            ///nokia-conf/configure/service/vprn/subscriber-interface/group-interface/sap/oper-group-association/oper-group/oper-group
                            leaf oper-group {
                                type leafref {
                                    path "../../../../../oper-group/name";
                                }
                                description "Operational group";
                            }

                        }
                        ///nokia-conf/configure/service/vprn/subscriber-interface/group-interface/sap/oper-group-association/monitor-oper-group
                        case monitor-oper-group {

                            ///nokia-conf/configure/service/vprn/subscriber-interface/group-interface/sap/oper-group-association/monitor-oper-group/monitor-oper-group
                            leaf monitor-oper-group {
                                type leafref {
                                    path "../../../../../oper-group/name";
                                }
                                description "Monitor operational group";
                            }

                        }
                    }
                    ///nokia-conf/configure/service/vprn/subscriber-interface/group-interface/sap/ingress
                    container ingress {
                        description "Enter the ingress context";

                        ///nokia-conf/configure/service/vprn/subscriber-interface/group-interface/sap/ingress/shared-policer
                        leaf shared-policer {
                            type leafref {
                                path "../../../../../../../qos/shared-policers/policer/shared-policer-name";
                            }
                            description "Ingress shared policer";
                        }

                        ///nokia-conf/configure/service/vprn/subscriber-interface/group-interface/sap/ingress/qos
                        container qos {
                            description "Enter the qos context";

                            ///nokia-conf/configure/service/vprn/subscriber-interface/group-interface/sap/ingress/qos/match-qinq-dot1p
                            leaf match-qinq-dot1p {
                                type enumeration {
                                    enum top                            { value 2; }
                                    enum bottom                         { value 3; }
                                }
                                description "Ingress match QinQ Dot1p";
                            }

                            ///nokia-conf/configure/service/vprn/subscriber-interface/group-interface/sap/ingress/qos/sap-ingress
                            container sap-ingress {
                                description "Enter the sap-ingress context";

                                ///nokia-conf/configure/service/vprn/subscriber-interface/group-interface/sap/ingress/qos/sap-ingress/policy-name
                                leaf policy-name {
                                    type leafref {
                                        path "../../../../../../../../../qos/sap-ingress/sap-ingress-policy-name";
                                    }
                                    description "Policy ID";
                                }

                                ///nokia-conf/configure/service/vprn/subscriber-interface/group-interface/sap/ingress/qos/sap-ingress/queuing-type
                                leaf queuing-type {
                                    type types-services:services-sap-queuing-type;
                                    description "Queuing type";
                                }

                            } // container sap-ingress

                            ///nokia-conf/configure/service/vprn/subscriber-interface/group-interface/sap/ingress/qos/policer-control-policy
                            container policer-control-policy {
                                description "Enter the policer-control-policy context";

                                ///nokia-conf/configure/service/vprn/subscriber-interface/group-interface/sap/ingress/qos/policer-control-policy/policy-name
                                leaf policy-name {
                                    type leafref {
                                        path "../../../../../../../../../qos/policer-control-policy/policer-control-policy-name";
                                    }
                                    description "Policer control policy name";
                                }

                            } // container policer-control-policy

                            ///nokia-conf/configure/service/vprn/subscriber-interface/group-interface/sap/ingress/qos/scheduler-policy
                            container scheduler-policy {
                                description "Enter the scheduler-policy context";

                                ///nokia-conf/configure/service/vprn/subscriber-interface/group-interface/sap/ingress/qos/scheduler-policy/policy-name
                                leaf policy-name {
                                    type leafref {
                                        path "../../../../../../../../../qos/scheduler-policy/scheduler-policy-name";
                                    }
                                    description "Scheduler policy name";
                                }

                            } // container scheduler-policy

                        } // container qos

                        ///nokia-conf/configure/service/vprn/subscriber-interface/group-interface/sap/ingress/filter
                        container filter {
                            description "Enter the filter context";

                            ///nokia-conf/configure/service/vprn/subscriber-interface/group-interface/sap/ingress/filter/ip
                            leaf ip {
                                type leafref {
                                    path "../../../../../../../../filter/ip-filter/filter-name";
                                }
                                description "IPv4 filter policy name";
                            }

                            ///nokia-conf/configure/service/vprn/subscriber-interface/group-interface/sap/ingress/filter/ipv6
                            leaf ipv6 {
                                type leafref {
                                    path "../../../../../../../../filter/ipv6-filter/filter-name";
                                }
                                description "IPv6 filter policy name";
                            }

                        } // container filter

                    } // container ingress

                    ///nokia-conf/configure/service/vprn/subscriber-interface/group-interface/sap/egress
                    container egress {
                        description "Enter the egress context";

                        ///nokia-conf/configure/service/vprn/subscriber-interface/group-interface/sap/egress/agg-rate-or-percent-agg-rate
                        choice agg-rate-or-percent-agg-rate {
                            default "agg-rate";
                            ///nokia-conf/configure/service/vprn/subscriber-interface/group-interface/sap/egress/agg-rate-or-percent-agg-rate/agg-rate
                            case agg-rate {

                                ///nokia-conf/configure/service/vprn/subscriber-interface/group-interface/sap/egress/agg-rate-or-percent-agg-rate/agg-rate/agg-rate
                                container agg-rate {
                                    description "Enter the agg-rate context";

                                    ///nokia-conf/configure/service/vprn/subscriber-interface/group-interface/sap/egress/agg-rate-or-percent-agg-rate/agg-rate/agg-rate/limit-unused-bandwidth
                                    leaf limit-unused-bandwidth {
                                        type boolean;
                                        default "false";
                                        description "Enable aggregate rate overrun protection";
                                    }

                                    ///nokia-conf/configure/service/vprn/subscriber-interface/group-interface/sap/egress/agg-rate-or-percent-agg-rate/agg-rate/agg-rate/rate
                                    leaf rate {
                                        type types-services:agg-rate-rate;
                                        units "kilobps";
                                        description "Enforced aggregate rate for all queues";
                                    }

                                    ///nokia-conf/configure/service/vprn/subscriber-interface/group-interface/sap/egress/agg-rate-or-percent-agg-rate/agg-rate/agg-rate/queue-frame-based-accounting
                                    leaf queue-frame-based-accounting {
                                        type boolean;
                                        default "false";
                                        description "Enable frame based accounting on policers and queues";
                                    }

                                    ///nokia-conf/configure/service/vprn/subscriber-interface/group-interface/sap/egress/agg-rate-or-percent-agg-rate/agg-rate/agg-rate/burst-limit
                                    leaf burst-limit {
                                        type union {
                                            type types-qos:bytes {
                                                range "1..14000000";
                                            }
                                            type enumeration {
                                                enum auto                           { value -1; }
                                            }
                                        }
                                        default "auto";
                                        description "Shaping burst size when an aggregate shaper is used";
                                    }

                                    ///nokia-conf/configure/service/vprn/subscriber-interface/group-interface/sap/egress/agg-rate-or-percent-agg-rate/agg-rate/agg-rate/adaptation-rule
                                    leaf adaptation-rule {
                                        type types-qos:adaptation-rule;
                                        default "closest";
                                        description "Adaptation rule to compute the operational PIR value when an aggregate shaper is used";
                                    }

                                } // container agg-rate

                            }
                        }
                        ///nokia-conf/configure/service/vprn/subscriber-interface/group-interface/sap/egress/qos
                        container qos {
                            description "Enter the qos context";

                            ///nokia-conf/configure/service/vprn/subscriber-interface/group-interface/sap/egress/qos/qinq-mark-top-only
                            leaf qinq-mark-top-only {
                                type boolean;
                                default "false";
                                description "Mark top Q-tags";
                            }

                            ///nokia-conf/configure/service/vprn/subscriber-interface/group-interface/sap/egress/qos/sap-egress
                            container sap-egress {
                                description "Enter the sap-egress context";

                                ///nokia-conf/configure/service/vprn/subscriber-interface/group-interface/sap/egress/qos/sap-egress/policy-name
                                leaf policy-name {
                                    type leafref {
                                        path "../../../../../../../../../qos/sap-egress/sap-egress-policy-name";
                                    }
                                    description "Policy ID to associate with SAP for mirrored service";
                                }

                            } // container sap-egress

                            ///nokia-conf/configure/service/vprn/subscriber-interface/group-interface/sap/egress/qos/policer-control-policy
                            container policer-control-policy {
                                description "Enter the policer-control-policy context";

                                ///nokia-conf/configure/service/vprn/subscriber-interface/group-interface/sap/egress/qos/policer-control-policy/policy-name
                                leaf policy-name {
                                    type leafref {
                                        path "../../../../../../../../../qos/policer-control-policy/policer-control-policy-name";
                                    }
                                    description "Policer control policy name";
                                }

                            } // container policer-control-policy

                            ///nokia-conf/configure/service/vprn/subscriber-interface/group-interface/sap/egress/qos/scheduler-policy
                            container scheduler-policy {
                                description "Enter the scheduler-policy context";

                                ///nokia-conf/configure/service/vprn/subscriber-interface/group-interface/sap/egress/qos/scheduler-policy/policy-name
                                leaf policy-name {
                                    type leafref {
                                        path "../../../../../../../../../qos/scheduler-policy/scheduler-policy-name";
                                    }
                                    description "Scheduler policy name";
                                }

                            } // container scheduler-policy

                        } // container qos

                        ///nokia-conf/configure/service/vprn/subscriber-interface/group-interface/sap/egress/filter
                        container filter {
                            description "Enter the filter context";

                            ///nokia-conf/configure/service/vprn/subscriber-interface/group-interface/sap/egress/filter/ip
                            leaf ip {
                                type leafref {
                                    path "../../../../../../../../filter/ip-filter/filter-name";
                                }
                                description "IPv4 filter policy name";
                            }

                            ///nokia-conf/configure/service/vprn/subscriber-interface/group-interface/sap/egress/filter/ipv6
                            leaf ipv6 {
                                type leafref {
                                    path "../../../../../../../../filter/ipv6-filter/filter-name";
                                }
                                description "IPv6 filter policy name";
                            }

                        } // container filter


                    } // container egress

                    ///nokia-conf/configure/service/vprn/subscriber-interface/group-interface/sap/cpu-protection
                    container cpu-protection {
                        description "Enter the cpu-protection context";

                        ///nokia-conf/configure/service/vprn/subscriber-interface/group-interface/sap/cpu-protection/policy-id
                        leaf policy-id {
                            type leafref {
                                path "../../../../../../../system/security/cpu-protection/policy/policy-id";
                            }
                            description "CPM protection policy";
                        }

                        ///nokia-conf/configure/service/vprn/subscriber-interface/group-interface/sap/cpu-protection/monitoring
                        choice monitoring {
                            ///nokia-conf/configure/service/vprn/subscriber-interface/group-interface/sap/cpu-protection/monitoring/mac
                            case mac {

                                ///nokia-conf/configure/service/vprn/subscriber-interface/group-interface/sap/cpu-protection/monitoring/mac/mac-monitoring
                                leaf mac-monitoring {
                                    type empty;
                                    description "Monitor MAC for CPU protection";
                                }

                            }
                            ///nokia-conf/configure/service/vprn/subscriber-interface/group-interface/sap/cpu-protection/monitoring/cfm
                            case cfm {

                                ///nokia-conf/configure/service/vprn/subscriber-interface/group-interface/sap/cpu-protection/monitoring/cfm/eth-cfm-monitoring
                                container eth-cfm-monitoring {
                                    presence "Enable the eth-cfm-monitoring context";
                                    description "Enable the eth-cfm-monitoring context";

                                    ///nokia-conf/configure/service/vprn/subscriber-interface/group-interface/sap/cpu-protection/monitoring/cfm/eth-cfm-monitoring/aggregate
                                    leaf aggregate {
                                        type empty;
                                        description "Apply rate limit to the sum of the per peer packet rates";
                                    }

                                    ///nokia-conf/configure/service/vprn/subscriber-interface/group-interface/sap/cpu-protection/monitoring/cfm/eth-cfm-monitoring/car
                                    leaf car {
                                        type empty;
                                        description "Ignore Ethernet CFM packets when enforcing overall rate";
                                    }

                                } // container eth-cfm-monitoring

                            }
                            ///nokia-conf/configure/service/vprn/subscriber-interface/group-interface/sap/cpu-protection/monitoring/ip
                            case ip {

                                ///nokia-conf/configure/service/vprn/subscriber-interface/group-interface/sap/cpu-protection/monitoring/ip/ip-src-monitoring
                                leaf ip-src-monitoring {
                                    type empty;
                                    description "Enable IP source monitoring for CPU protection";
                                }

                            }
                        }
                    } // container cpu-protection

                    ///nokia-conf/configure/service/vprn/subscriber-interface/group-interface/sap/lag
                    container lag {
                        description "Enter the lag context";

                        ///nokia-conf/configure/service/vprn/subscriber-interface/group-interface/sap/lag/link-map-profile
                        leaf link-map-profile {
                            type types-services:link-map-profile-id;
                            description "LAG link map profile for a SAP or network interface";
                        }

                        ///nokia-conf/configure/service/vprn/subscriber-interface/group-interface/sap/lag/per-link-hash
                        container per-link-hash {
                            description "Enter the per-link-hash context";

                            ///nokia-conf/configure/service/vprn/subscriber-interface/group-interface/sap/lag/per-link-hash/class
                            leaf class {
                                type types-services:sap-lag-per-link-hash-class;
                                default "1";
                                description "Class used on LAG egress using weighted per-link-hash";
                            }

                            ///nokia-conf/configure/service/vprn/subscriber-interface/group-interface/sap/lag/per-link-hash/weight
                            leaf weight {
                                type types-services:sap-lag-per-link-hash-weight;
                                default "1";
                                description "Weight used on LAG egress using weighted per-link-hash";
                            }

                        } // container per-link-hash

                    } // container lag

                    ///nokia-conf/configure/service/vprn/subscriber-interface/group-interface/sap/fwd-wholesale
                    container fwd-wholesale {
                        description "Enter the fwd-wholesale context";

                        ///nokia-conf/configure/service/vprn/subscriber-interface/group-interface/sap/fwd-wholesale/pppoe-service
                        leaf pppoe-service {
                            type leafref {
                                path "../../../../../../epipe/service-name";
                            }
                            description "PPPoE service name";
                        }

                    } // container fwd-wholesale

                    ///nokia-conf/configure/service/vprn/subscriber-interface/group-interface/sap/eth-cfm
                    container eth-cfm {
                        description "Enable the eth-cfm context";

                        ///nokia-conf/configure/service/vprn/subscriber-interface/group-interface/sap/eth-cfm/collect-lmm-stats
                        leaf collect-lmm-stats {
                            type boolean;
                            default "false";
                            description "Collect statistics for loss measurement message tests";
                        }

                        ///nokia-conf/configure/service/vprn/subscriber-interface/group-interface/sap/eth-cfm/squelch-ingress-levels
                        leaf-list squelch-ingress-levels {
                            type uint32 {
                                range "0..7";
                            }
                            max-elements 8;
                            description "Levels for which ETH-CFM packets are silently discarded";
                        }

                        ///nokia-conf/configure/service/vprn/subscriber-interface/group-interface/sap/eth-cfm/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/sap/eth-cfm/apply-groups-exclude
                        leaf-list apply-groups-exclude {
                            type leafref {
                                path "../../../../../../../groups/group/name";
                            }
                            max-elements 8;
                            ordered-by user;
                            description "Exclude a configuration group at this level";
                        }

                        ///nokia-conf/configure/service/vprn/subscriber-interface/group-interface/sap/eth-cfm/collect-lmm-fc-stats
                        container collect-lmm-fc-stats {
                            description "Enter the collect-lmm-fc-stats context";

                            ///nokia-conf/configure/service/vprn/subscriber-interface/group-interface/sap/eth-cfm/collect-lmm-fc-stats/fc
                            leaf-list fc {
                                type types-eth-cfm:fc-type;
                                max-elements 8;
                                description "Forwarding class name for profile-unaware counter";
                            }

                            ///nokia-conf/configure/service/vprn/subscriber-interface/group-interface/sap/eth-cfm/collect-lmm-fc-stats/fc-in-profile
                            leaf-list fc-in-profile {
                                type types-eth-cfm:fc-type;
                                max-elements 8;
                                description "Forwarding class name for profile-aware counter";
                            }

                        } // container collect-lmm-fc-stats

                        ///nokia-conf/configure/service/vprn/subscriber-interface/group-interface/sap/eth-cfm/mep
                        list mep {
                            key "md-admin-name ma-admin-name mep-id";
                            description "Enter the mep list instance";

                            ///nokia-conf/configure/service/vprn/subscriber-interface/group-interface/sap/eth-cfm/mep/md-admin-name
                            leaf md-admin-name {
                                type leafref {
                                    path "../../../../../../../../eth-cfm/domain/md-admin-name";
                                }
                                description "Maintenance Domain (MD) name";
                            }

                            ///nokia-conf/configure/service/vprn/subscriber-interface/group-interface/sap/eth-cfm/mep/ma-admin-name
                            leaf ma-admin-name {
                                type leafref {
                                    path "../../../../../../../../eth-cfm/domain[md-admin-name=current()/../md-admin-name]/association/ma-admin-name";
                                }
                                description "Maintenance Association (MA) name";
                            }

                            ///nokia-conf/configure/service/vprn/subscriber-interface/group-interface/sap/eth-cfm/mep/mep-id
                            leaf mep-id {
                                type types-eth-cfm:mep-id-type;
                                description "Maintenance Endpoint (MEP) ID";
                            }

                            ///nokia-conf/configure/service/vprn/subscriber-interface/group-interface/sap/eth-cfm/mep/admin-state
                            leaf admin-state {
                                type types-sros:admin-state;
                                default "disable";
                                description "Administrative state of the MEP";
                            }

                            ///nokia-conf/configure/service/vprn/subscriber-interface/group-interface/sap/eth-cfm/mep/description
                            leaf description {
                                type types-sros:description;
                                description "Text description";
                            }

                            ///nokia-conf/configure/service/vprn/subscriber-interface/group-interface/sap/eth-cfm/mep/low-priority-defect
                            leaf low-priority-defect {
                                type types-eth-cfm:lowest-alarm-priority;
                                default "mac-rem-err-xcon";
                                description "Lowest priority defect allowed to generate fault alarm";
                            }

                            ///nokia-conf/configure/service/vprn/subscriber-interface/group-interface/sap/eth-cfm/mep/fault-propagation
                            leaf fault-propagation {
                                type types-eth-cfm:fault-propagation-type;
                                description "Fault propagation for the MEP";
                            }

                            ///nokia-conf/configure/service/vprn/subscriber-interface/group-interface/sap/eth-cfm/mep/ccm
                            leaf ccm {
                                type boolean;
                                default "false";
                                description "Generate CCM messages";
                            }

                            ///nokia-conf/configure/service/vprn/subscriber-interface/group-interface/sap/eth-cfm/mep/ccm-ltm-priority
                            leaf ccm-ltm-priority {
                                type types-eth-cfm:frame-priority;
                                default "7";
                                description "Priority of CCM and LTM messages transmitted by the MEP";
                            }

                            ///nokia-conf/configure/service/vprn/subscriber-interface/group-interface/sap/eth-cfm/mep/ccm-padding-size
                            leaf ccm-padding-size {
                                type uint32 {
                                    range "3..1500";
                                }
                                description "Number of octets of padding to insert in CCM packets";
                            }

                            ///nokia-conf/configure/service/vprn/subscriber-interface/group-interface/sap/eth-cfm/mep/one-way-delay-threshold
                            leaf one-way-delay-threshold {
                                type uint32 {
                                    range "0..600";
                                }
                                units "seconds";
                                default "3";
                                description "Threshold time limit for the one-way delay test";
                            }

                            ///nokia-conf/configure/service/vprn/subscriber-interface/group-interface/sap/eth-cfm/mep/ais
                            leaf ais {
                                type boolean;
                                default "false";
                                description "Enable the generation and the reception of AIS messages";
                            }

                            ///nokia-conf/configure/service/vprn/subscriber-interface/group-interface/sap/eth-cfm/mep/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/sap/eth-cfm/mep/apply-groups-exclude
                            leaf-list apply-groups-exclude {
                                type leafref {
                                    path "../../../../../../../../groups/group/name";
                                }
                                max-elements 8;
                                ordered-by user;
                                description "Exclude a configuration group at this level";
                            }

                            ///nokia-conf/configure/service/vprn/subscriber-interface/group-interface/sap/eth-cfm/mep/alarm-notification
                            container alarm-notification {
                                description "Enter the alarm-notification context";

                                ///nokia-conf/configure/service/vprn/subscriber-interface/group-interface/sap/eth-cfm/mep/alarm-notification/fng-alarm-time
                                leaf fng-alarm-time {
                                    type int32 {
                                        range "250|500|1000";
                                    }
                                    units "centiseconds";
                                    description "Time that must expire before an FNG alarm is raised";
                                }

                                ///nokia-conf/configure/service/vprn/subscriber-interface/group-interface/sap/eth-cfm/mep/alarm-notification/fng-reset-time
                                leaf fng-reset-time {
                                    type int32 {
                                        range "250|500|1000";
                                    }
                                    units "centiseconds";
                                    description "Time that must expire before an FNG alarm is reset";
                                }

                            } // container alarm-notification

                            ///nokia-conf/configure/service/vprn/subscriber-interface/group-interface/sap/eth-cfm/mep/csf
                            container csf {
                                presence "Enable the csf context";
                                description "Enable the csf context";

                                ///nokia-conf/configure/service/vprn/subscriber-interface/group-interface/sap/eth-cfm/mep/csf/multiplier
                                leaf multiplier {
                                    type decimal64 {
                                        range "0.0|2.0..30.0";
                                        fraction-digits 1;
                                    }
                                    default "3.5";
                                    description "Multiplication factor used to clear the CSF condition";
                                }

                            } // container csf

                            ///nokia-conf/configure/service/vprn/subscriber-interface/group-interface/sap/eth-cfm/mep/eth-test
                            container eth-test {
                                presence "Enable the eth-test context";
                                description "Enable the eth-test context";

                                ///nokia-conf/configure/service/vprn/subscriber-interface/group-interface/sap/eth-cfm/mep/eth-test/bit-error-threshold
                                leaf bit-error-threshold {
                                    type uint32 {
                                        range "0..11840";
                                    }
                                    units "bit errors";
                                    default "1";
                                    description "Lowest priority defect allowed to generate fault alarm";
                                }

                                ///nokia-conf/configure/service/vprn/subscriber-interface/group-interface/sap/eth-cfm/mep/eth-test/test-pattern
                                container test-pattern {
                                    description "Enter the test-pattern context";

                                    ///nokia-conf/configure/service/vprn/subscriber-interface/group-interface/sap/eth-cfm/mep/eth-test/test-pattern/pattern
                                    leaf pattern {
                                        type enumeration {
                                            enum all-zeros                      { value 0; }
                                            enum all-ones                       { value 1; }
                                        }
                                        default "all-zeros";
                                        description "Test pattern for Ethernet Test frames";
                                    }

                                    ///nokia-conf/configure/service/vprn/subscriber-interface/group-interface/sap/eth-cfm/mep/eth-test/test-pattern/crc-tlv
                                    leaf crc-tlv {
                                        type boolean;
                                        default "false";
                                        description "Generate a CRC checksum";
                                    }

                                } // container test-pattern

                            } // container eth-test

                            ///nokia-conf/configure/service/vprn/subscriber-interface/group-interface/sap/eth-cfm/mep/grace
                            container grace {
                                description "Enter the grace context";

                                ///nokia-conf/configure/service/vprn/subscriber-interface/group-interface/sap/eth-cfm/mep/grace/eth-ed
                                container eth-ed {
                                    description "Enter the eth-ed context";

                                    ///nokia-conf/configure/service/vprn/subscriber-interface/group-interface/sap/eth-cfm/mep/grace/eth-ed/max-rx-defect-window
                                    leaf max-rx-defect-window {
                                        type uint32 {
                                            range "1..86400";
                                        }
                                        units "seconds";
                                        description "Maximum received ETH-ED expected defect window duration";
                                    }

                                    ///nokia-conf/configure/service/vprn/subscriber-interface/group-interface/sap/eth-cfm/mep/grace/eth-ed/priority
                                    leaf priority {
                                        type int32 {
                                            range "0..7";
                                        }
                                        description "Transmission priority for ETH-ED PDUs";
                                    }

                                    ///nokia-conf/configure/service/vprn/subscriber-interface/group-interface/sap/eth-cfm/mep/grace/eth-ed/rx-eth-ed
                                    leaf rx-eth-ed {
                                        type boolean;
                                        default "true";
                                        description "Receive and process ETH-ED ITU-T Y.1731 PDUs on the MEP";
                                    }

                                    ///nokia-conf/configure/service/vprn/subscriber-interface/group-interface/sap/eth-cfm/mep/grace/eth-ed/tx-eth-ed
                                    leaf tx-eth-ed {
                                        type boolean;
                                        default "false";
                                        description "Transmit ETH-ED PDUs from the MEP";
                                    }

                                } // container eth-ed

                                ///nokia-conf/configure/service/vprn/subscriber-interface/group-interface/sap/eth-cfm/mep/grace/eth-vsm-grace
                                container eth-vsm-grace {
                                    description "Enter the eth-vsm-grace context";

                                    ///nokia-conf/configure/service/vprn/subscriber-interface/group-interface/sap/eth-cfm/mep/grace/eth-vsm-grace/rx-eth-vsm-grace
                                    leaf rx-eth-vsm-grace {
                                        type boolean;
                                        default "true";
                                        description "Receive and process Nokia ETH-CFM Grace PDU on the MEP";
                                    }

                                    ///nokia-conf/configure/service/vprn/subscriber-interface/group-interface/sap/eth-cfm/mep/grace/eth-vsm-grace/tx-eth-vsm-grace
                                    leaf tx-eth-vsm-grace {
                                        type boolean;
                                        default "true";
                                        description "Transmit ETH-ED PDUs from the MEP";
                                    }

                                } // container eth-vsm-grace

                            } // container grace

                        } // list mep

                    } // container eth-cfm

                    ///nokia-conf/configure/service/vprn/subscriber-interface/group-interface/sap/sub-sla-mgmt
                    container sub-sla-mgmt {
                        description "Enter the sub-sla-mgmt context";

                        ///nokia-conf/configure/service/vprn/subscriber-interface/group-interface/sap/sub-sla-mgmt/admin-state
                        leaf admin-state {
                            type types-sros:admin-state;
                            default "disable";
                            description "Administrative state of SAP subscriber management";
                        }

                        ///nokia-conf/configure/service/vprn/subscriber-interface/group-interface/sap/sub-sla-mgmt/sub-ident-policy
                        leaf sub-ident-policy {
                            type leafref {
                                path "../../../../../../../subscriber-mgmt/sub-ident-policy/name";
                            }
                            description "Subscriber identification policy used on this SAP";
                        }

                        ///nokia-conf/configure/service/vprn/subscriber-interface/group-interface/sap/sub-sla-mgmt/subscriber-limit
                        leaf subscriber-limit {
                            type types-submgt:sap-subscriber-limit;
                            default "1";
                            description "Maximum number of subscribers on this SAP";
                        }

                        ///nokia-conf/configure/service/vprn/subscriber-interface/group-interface/sap/sub-sla-mgmt/defaults
                        container defaults {
                            description "Enter the defaults context";

                            ///nokia-conf/configure/service/vprn/subscriber-interface/group-interface/sap/sub-sla-mgmt/defaults/sub-profile
                            leaf sub-profile {
                                type leafref {
                                    path "../../../../../../../../subscriber-mgmt/sub-profile/name";
                                }
                                description "Default subscriber profile for the SAP";
                            }

                            ///nokia-conf/configure/service/vprn/subscriber-interface/group-interface/sap/sub-sla-mgmt/defaults/sla-profile
                            leaf sla-profile {
                                type leafref {
                                    path "../../../../../../../../subscriber-mgmt/sla-profile/name";
                                }
                                description "Default SLA profile for hosts on this SAP";
                            }

                            ///nokia-conf/configure/service/vprn/subscriber-interface/group-interface/sap/sub-sla-mgmt/defaults/app-profile
                            leaf app-profile {
                                type leafref {
                                    path "../../../../../../../../application-assurance/group/partition/policy/app-profile/app-profile-name";
                                }
                                description "Default application profile name for this SAP";
                            }

                            ///nokia-conf/configure/service/vprn/subscriber-interface/group-interface/sap/sub-sla-mgmt/defaults/subscriber-id
                            container subscriber-id {
                                description "Enter the subscriber-id context";

                                ///nokia-conf/configure/service/vprn/subscriber-interface/group-interface/sap/sub-sla-mgmt/defaults/subscriber-id/subscriber-id
                                choice subscriber-id {
                                    ///nokia-conf/configure/service/vprn/subscriber-interface/group-interface/sap/sub-sla-mgmt/defaults/subscriber-id/subscriber-id/auto-id
                                    case auto-id {

                                        ///nokia-conf/configure/service/vprn/subscriber-interface/group-interface/sap/sub-sla-mgmt/defaults/subscriber-id/subscriber-id/auto-id/auto-id
                                        leaf auto-id {
                                            type empty;
                                            description "Use auto-generated subscriber identification string";
                                        }

                                    }
                                    ///nokia-conf/configure/service/vprn/subscriber-interface/group-interface/sap/sub-sla-mgmt/defaults/subscriber-id/subscriber-id/sap-id
                                    case sap-id {

                                        ///nokia-conf/configure/service/vprn/subscriber-interface/group-interface/sap/sub-sla-mgmt/defaults/subscriber-id/subscriber-id/sap-id/sap-id
                                        leaf sap-id {
                                            type empty;
                                            description "Use SAP ID as default subscriber identification string";
                                        }

                                    }
                                    ///nokia-conf/configure/service/vprn/subscriber-interface/group-interface/sap/sub-sla-mgmt/defaults/subscriber-id/subscriber-id/string
                                    case string {

                                        ///nokia-conf/configure/service/vprn/subscriber-interface/group-interface/sap/sub-sla-mgmt/defaults/subscriber-id/subscriber-id/string/string
                                        leaf string {
                                            type types-submgt:subscriber-id;
                                            description "Default subscriber identification string for the SAP";
                                        }

                                    }
                                }
                            } // container subscriber-id

                            ///nokia-conf/configure/service/vprn/subscriber-interface/group-interface/sap/sub-sla-mgmt/defaults/int-dest-id
                            container int-dest-id {
                                description "Enter the int-dest-id context";

                                ///nokia-conf/configure/service/vprn/subscriber-interface/group-interface/sap/sub-sla-mgmt/defaults/int-dest-id/int-dest-id
                                choice int-dest-id {
                                    ///nokia-conf/configure/service/vprn/subscriber-interface/group-interface/sap/sub-sla-mgmt/defaults/int-dest-id/int-dest-id/top-q-tag
                                    case top-q-tag {

                                        ///nokia-conf/configure/service/vprn/subscriber-interface/group-interface/sap/sub-sla-mgmt/defaults/int-dest-id/int-dest-id/top-q-tag/top-q-tag
                                        leaf top-q-tag {
                                            type empty;
                                            description "Use the top Q-tag of this SAP";
                                        }

                                    }
                                    ///nokia-conf/configure/service/vprn/subscriber-interface/group-interface/sap/sub-sla-mgmt/defaults/int-dest-id/int-dest-id/string
                                    case string {

                                        ///nokia-conf/configure/service/vprn/subscriber-interface/group-interface/sap/sub-sla-mgmt/defaults/int-dest-id/int-dest-id/string/string
                                        leaf string {
                                            type types-submgt:int-dest-id;
                                            description "Use the configured string";
                                        }

                                    }
                                }
                            } // container int-dest-id

                        } // container defaults

                        ///nokia-conf/configure/service/vprn/subscriber-interface/group-interface/sap/sub-sla-mgmt/single-sub-parameters
                        container single-sub-parameters {
                            description "Enter the single-sub-parameters context";

                            ///nokia-conf/configure/service/vprn/subscriber-interface/group-interface/sap/sub-sla-mgmt/single-sub-parameters/profiled-traffic-only
                            leaf profiled-traffic-only {
                                type boolean;
                                default "false";
                                description "Include all traffic in subscriber profile";
                            }

                            ///nokia-conf/configure/service/vprn/subscriber-interface/group-interface/sap/sub-sla-mgmt/single-sub-parameters/non-sub-traffic
                            container non-sub-traffic {
                                presence "Enable the non-sub-traffic context";
                                description "Enable the non-sub-traffic context";

                                ///nokia-conf/configure/service/vprn/subscriber-interface/group-interface/sap/sub-sla-mgmt/single-sub-parameters/non-sub-traffic/sub-profile
                                leaf sub-profile {
                                    type leafref {
                                        path "../../../../../../../../../subscriber-mgmt/sub-profile/name";
                                    }
                                    mandatory true;
                                    description "Subscriber profile all non-subscriber traffic";
                                }

                                ///nokia-conf/configure/service/vprn/subscriber-interface/group-interface/sap/sub-sla-mgmt/single-sub-parameters/non-sub-traffic/sla-profile
                                leaf sla-profile {
                                    type leafref {
                                        path "../../../../../../../../../subscriber-mgmt/sla-profile/name";
                                    }
                                    mandatory true;
                                    description "SLA profile applicable for all non-subscriber traffic";
                                }

                                ///nokia-conf/configure/service/vprn/subscriber-interface/group-interface/sap/sub-sla-mgmt/single-sub-parameters/non-sub-traffic/subscriber-id
                                leaf subscriber-id {
                                    type types-submgt:subscriber-id;
                                    sros-ext:immutable;
                                    description "Subscriber ID applied for all non-subscriber traffic";
                                }

                                ///nokia-conf/configure/service/vprn/subscriber-interface/group-interface/sap/sub-sla-mgmt/single-sub-parameters/non-sub-traffic/app-profile
                                leaf app-profile {
                                    type leafref {
                                        path "../../../../../../../../../application-assurance/group/partition/policy/app-profile/app-profile-name";
                                    }
                                    description "Application profile name for all non-subscriber traffic";
                                }

                            } // container non-sub-traffic

                        } // container single-sub-parameters

                    } // container sub-sla-mgmt

                    ///nokia-conf/configure/service/vprn/subscriber-interface/group-interface/sap/static-host
                    container static-host {
                        description "Enter the static-host context";

                        ///nokia-conf/configure/service/vprn/subscriber-interface/group-interface/sap/static-host/mac-learning
                        container mac-learning {
                            description "Enter the mac-learning context";

                            ///nokia-conf/configure/service/vprn/subscriber-interface/group-interface/sap/static-host/mac-learning/data-triggered
                            leaf data-triggered {
                                type boolean;
                                default "false";
                                description "Enable learning of MAC addresses from data packets";
                            }

                            ///nokia-conf/configure/service/vprn/subscriber-interface/group-interface/sap/static-host/mac-learning/single-mac
                            leaf single-mac {
                                type boolean;
                                default "false";
                                description "Enforce single MAC address and subscriber for the SAP";
                            }

                        } // container mac-learning

                        ///nokia-conf/configure/service/vprn/subscriber-interface/group-interface/sap/static-host/ipv4
                        list ipv4 {
                            key "ip mac";
                            description "Enter the ipv4 list instance";

                            ///nokia-conf/configure/service/vprn/subscriber-interface/group-interface/sap/static-host/ipv4/ip
                            leaf ip {
                                type types-sros:ipv4-unicast-address;
                                description "IPv4 address used by the static host";
                            }

                            ///nokia-conf/configure/service/vprn/subscriber-interface/group-interface/sap/static-host/ipv4/mac
                            leaf mac {
                                type types-sros:mac-unicast-address;
                                description "MAC address used by the static host";
                            }

                            ///nokia-conf/configure/service/vprn/subscriber-interface/group-interface/sap/static-host/ipv4/rip-policy
                            leaf rip-policy {
                                type leafref {
                                    path "../../../../../../../../subscriber-mgmt/rip-policy/name";
                                }
                                description "RIP policy name";
                            }

                            ///nokia-conf/configure/service/vprn/subscriber-interface/group-interface/sap/static-host/ipv4/admin-state
                            leaf admin-state {
                                type types-sros:admin-state;
                                default "disable";
                                description "Administrative state of the static host";
                            }

                            ///nokia-conf/configure/service/vprn/subscriber-interface/group-interface/sap/static-host/ipv4/sub-profile
                            leaf sub-profile {
                                type leafref {
                                    path "../../../../../../../../subscriber-mgmt/sub-profile/name";
                                }
                                description "Sub-profile name";
                            }

                            ///nokia-conf/configure/service/vprn/subscriber-interface/group-interface/sap/static-host/ipv4/sla-profile
                            leaf sla-profile {
                                type leafref {
                                    path "../../../../../../../../subscriber-mgmt/sla-profile/name";
                                }
                                description "SLA profile name";
                            }

                            ///nokia-conf/configure/service/vprn/subscriber-interface/group-interface/sap/static-host/ipv4/ancp-string
                            leaf ancp-string {
                                type types-submgt:ancp-string;
                                description "ANCP string";
                            }

                            ///nokia-conf/configure/service/vprn/subscriber-interface/group-interface/sap/static-host/ipv4/int-dest-id
                            leaf int-dest-id {
                                type types-submgt:int-dest-id;
                                description "Intermediate destination ID";
                            }

                            ///nokia-conf/configure/service/vprn/subscriber-interface/group-interface/sap/static-host/ipv4/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/sap/static-host/ipv4/apply-groups-exclude
                            leaf-list apply-groups-exclude {
                                type leafref {
                                    path "../../../../../../../../groups/group/name";
                                }
                                max-elements 8;
                                ordered-by user;
                                description "Exclude a configuration group at this level";
                            }

                            ///nokia-conf/configure/service/vprn/subscriber-interface/group-interface/sap/static-host/ipv4/app-profile
                            container app-profile {
                                description "Enter the app-profile context";

                                ///nokia-conf/configure/service/vprn/subscriber-interface/group-interface/sap/static-host/ipv4/app-profile/profile
                                leaf profile {
                                    type leafref {
                                        path "../../../../../../../../../application-assurance/group/partition/policy/app-profile/app-profile-name";
                                    }
                                    description "Application profile used by the static host";
                                }

                                ///nokia-conf/configure/service/vprn/subscriber-interface/group-interface/sap/static-host/ipv4/app-profile/scope
                                leaf scope {
                                    type types-submgt:aa-sub-scope;
                                    default "subscriber";
                                    description "Scope of the static host application profile";
                                }

                            } // container app-profile

                            ///nokia-conf/configure/service/vprn/subscriber-interface/group-interface/sap/static-host/ipv4/subscriber-id
                            container subscriber-id {
                                description "Enter the subscriber-id context";

                                ///nokia-conf/configure/service/vprn/subscriber-interface/group-interface/sap/static-host/ipv4/subscriber-id/subscriber-id
                                choice subscriber-id {
                                    ///nokia-conf/configure/service/vprn/subscriber-interface/group-interface/sap/static-host/ipv4/subscriber-id/subscriber-id/string
                                    case string {

                                        ///nokia-conf/configure/service/vprn/subscriber-interface/group-interface/sap/static-host/ipv4/subscriber-id/subscriber-id/string/string
                                        leaf string {
                                            type types-submgt:subscriber-id;
                                            description "Subscriber identification";
                                        }

                                    }
                                    ///nokia-conf/configure/service/vprn/subscriber-interface/group-interface/sap/static-host/ipv4/subscriber-id/subscriber-id/use-sap-id
                                    case use-sap-id {

                                        ///nokia-conf/configure/service/vprn/subscriber-interface/group-interface/sap/static-host/ipv4/subscriber-id/subscriber-id/use-sap-id/use-sap-id
                                        leaf use-sap-id {
                                            type empty;
                                            description "Use the SAP id as subscriber ID";
                                        }

                                    }
                                }
                            } // container subscriber-id

                            ///nokia-conf/configure/service/vprn/subscriber-interface/group-interface/sap/static-host/ipv4/shcv
                            container shcv {
                                description "Enter the shcv context";

                            } // container shcv

                            ///nokia-conf/configure/service/vprn/subscriber-interface/group-interface/sap/static-host/ipv4/managed-route
                            list managed-route {
                                key "prefix";
                                description "Enter the managed-route list instance";

                                ///nokia-conf/configure/service/vprn/subscriber-interface/group-interface/sap/static-host/ipv4/managed-route/prefix
                                leaf prefix {
                                    type types-sros:ipv4-unicast-prefix;
                                    description "Managed route prefix associated with IPv4 static host";
                                }

                                ///nokia-conf/configure/service/vprn/subscriber-interface/group-interface/sap/static-host/ipv4/managed-route/metric
                                leaf metric {
                                    type uint32;
                                    default "0";
                                    description "Metric associated with the provisioned managed route";
                                }

                                ///nokia-conf/configure/service/vprn/subscriber-interface/group-interface/sap/static-host/ipv4/managed-route/preference
                                leaf preference {
                                    type uint32 {
                                        range "0..255";
                                    }
                                    default "0";
                                    description "Preference associated to the provisioned managed route";
                                }

                                ///nokia-conf/configure/service/vprn/subscriber-interface/group-interface/sap/static-host/ipv4/managed-route/tag
                                leaf tag {
                                    type uint32;
                                    default "0";
                                    description "Route tag used if CPE check fails";
                                }

                                ///nokia-conf/configure/service/vprn/subscriber-interface/group-interface/sap/static-host/ipv4/managed-route/apply-groups
                                leaf-list apply-groups {
                                    type leafref {
                                        path "../../../../../../../../../groups/group/name";
                                    }
                                    max-elements 8;
                                    ordered-by user;
                                    description "Apply a configuration group at this level";
                                }

                                ///nokia-conf/configure/service/vprn/subscriber-interface/group-interface/sap/static-host/ipv4/managed-route/apply-groups-exclude
                                leaf-list apply-groups-exclude {
                                    type leafref {
                                        path "../../../../../../../../../groups/group/name";
                                    }
                                    max-elements 8;
                                    ordered-by user;
                                    description "Exclude a configuration group at this level";
                                }

                                ///nokia-conf/configure/service/vprn/subscriber-interface/group-interface/sap/static-host/ipv4/managed-route/cpe-check
                                container cpe-check {
                                    presence "Enable the cpe-check context";
                                    description "Enable the cpe-check context";

                                    ///nokia-conf/configure/service/vprn/subscriber-interface/group-interface/sap/static-host/ipv4/managed-route/cpe-check/destination-ip-address
                                    leaf destination-ip-address {
                                        type types-sros:ip-address;
                                        sros-ext:immutable;
                                        description "IP address of the target CPE device";
                                    }

                                    ///nokia-conf/configure/service/vprn/subscriber-interface/group-interface/sap/static-host/ipv4/managed-route/cpe-check/drop-count
                                    leaf drop-count {
                                        type uint32 {
                                            range "1..255";
                                        }
                                        default "3";
                                        description "Consecutive ping replies missed before CPE deemed down";
                                    }

                                    ///nokia-conf/configure/service/vprn/subscriber-interface/group-interface/sap/static-host/ipv4/managed-route/cpe-check/interval
                                    leaf interval {
                                        type uint32 {
                                            range "1..255";
                                        }
                                        units "seconds";
                                        default "1";
                                        description "Interval between ICMP pings to target CPE IP address";
                                    }

                                    ///nokia-conf/configure/service/vprn/subscriber-interface/group-interface/sap/static-host/ipv4/managed-route/cpe-check/log
                                    leaf log {
                                        type boolean;
                                        default "false";
                                        description "Log CPE connectivity checks transitions";
                                    }

                                    ///nokia-conf/configure/service/vprn/subscriber-interface/group-interface/sap/static-host/ipv4/managed-route/cpe-check/padding-size
                                    leaf padding-size {
                                        type uint32 {
                                            range "0..16384";
                                        }
                                        units "bytes";
                                        default "56";
                                        description "Padding size for CPE connectivity checks";
                                    }

                                    ///nokia-conf/configure/service/vprn/subscriber-interface/group-interface/sap/static-host/ipv4/managed-route/cpe-check/timeout
                                    leaf timeout {
                                        type uint32 {
                                            range "1..10";
                                        }
                                        units "seconds";
                                        default "1";
                                        description "Time interval determining that a ping is missed";
                                    }

                                    ///nokia-conf/configure/service/vprn/subscriber-interface/group-interface/sap/static-host/ipv4/managed-route/cpe-check/source-ip-address
                                    leaf source-ip-address {
                                        type types-sros:ip-address;
                                        description "Source IP address used in the ICMP messages";
                                    }

                                    ///nokia-conf/configure/service/vprn/subscriber-interface/group-interface/sap/static-host/ipv4/managed-route/cpe-check/apply-groups
                                    leaf-list apply-groups {
                                        type leafref {
                                            path "../../../../../../../../../../groups/group/name";
                                        }
                                        max-elements 8;
                                        ordered-by user;
                                        description "Apply a configuration group at this level";
                                    }

                                    ///nokia-conf/configure/service/vprn/subscriber-interface/group-interface/sap/static-host/ipv4/managed-route/cpe-check/apply-groups-exclude
                                    leaf-list apply-groups-exclude {
                                        type leafref {
                                            path "../../../../../../../../../../groups/group/name";
                                        }
                                        max-elements 8;
                                        ordered-by user;
                                        description "Exclude a configuration group at this level";
                                    }

                                    ///nokia-conf/configure/service/vprn/subscriber-interface/group-interface/sap/static-host/ipv4/managed-route/cpe-check/failed-action
                                    container failed-action {
                                        description "Enter the failed-action context";

                                        ///nokia-conf/configure/service/vprn/subscriber-interface/group-interface/sap/static-host/ipv4/managed-route/cpe-check/failed-action/withdraw-or-modify
                                        choice withdraw-or-modify {
                                            ///nokia-conf/configure/service/vprn/subscriber-interface/group-interface/sap/static-host/ipv4/managed-route/cpe-check/failed-action/withdraw-or-modify/withdraw
                                            case withdraw {

                                                ///nokia-conf/configure/service/vprn/subscriber-interface/group-interface/sap/static-host/ipv4/managed-route/cpe-check/failed-action/withdraw-or-modify/withdraw/withdraw
                                                leaf withdraw {
                                                    type boolean;
                                                    default "false";
                                                    description "Withdraw the route when the CPE check fails";
                                                }

                                            }
                                            ///nokia-conf/configure/service/vprn/subscriber-interface/group-interface/sap/static-host/ipv4/managed-route/cpe-check/failed-action/withdraw-or-modify/modify
                                            case modify {

                                                ///nokia-conf/configure/service/vprn/subscriber-interface/group-interface/sap/static-host/ipv4/managed-route/cpe-check/failed-action/withdraw-or-modify/modify/metric
                                                leaf metric {
                                                    type uint32;
                                                    default "0";
                                                    description "Metric associated with the provisioned managed route";
                                                }

                                                ///nokia-conf/configure/service/vprn/subscriber-interface/group-interface/sap/static-host/ipv4/managed-route/cpe-check/failed-action/withdraw-or-modify/modify/preference
                                                leaf preference {
                                                    type int32 {
                                                        range "0..255";
                                                    }
                                                    description "Preference associated to the provisioned managed route";
                                                }

                                                ///nokia-conf/configure/service/vprn/subscriber-interface/group-interface/sap/static-host/ipv4/managed-route/cpe-check/failed-action/withdraw-or-modify/modify/tag
                                                leaf tag {
                                                    type uint32;
                                                    default "0";
                                                    description "Route tag used if CPE check fails";
                                                }

                                            }
                                        }
                                    } // container failed-action

                                } // container cpe-check

                            } // list managed-route

                        } // list ipv4

                        ///nokia-conf/configure/service/vprn/subscriber-interface/group-interface/sap/static-host/ipv6
                        list ipv6 {
                            key "prefix mac";
                            description "Enter the ipv6 list instance";

                            ///nokia-conf/configure/service/vprn/subscriber-interface/group-interface/sap/static-host/ipv6/prefix
                            leaf prefix {
                                type types-sros:ipv6-unicast-prefix;
                                description "IPv6 prefix";
                            }

                            ///nokia-conf/configure/service/vprn/subscriber-interface/group-interface/sap/static-host/ipv6/mac
                            leaf mac {
                                type types-sros:mac-unicast-address;
                                description "MAC address";
                            }

                            ///nokia-conf/configure/service/vprn/subscriber-interface/group-interface/sap/static-host/ipv6/admin-state
                            leaf admin-state {
                                type types-sros:admin-state;
                                default "disable";
                                description "Administrative state of the static host";
                            }

                            ///nokia-conf/configure/service/vprn/subscriber-interface/group-interface/sap/static-host/ipv6/sub-profile
                            leaf sub-profile {
                                type leafref {
                                    path "../../../../../../../../subscriber-mgmt/sub-profile/name";
                                }
                                description "Sub-profile name";
                            }

                            ///nokia-conf/configure/service/vprn/subscriber-interface/group-interface/sap/static-host/ipv6/sla-profile
                            leaf sla-profile {
                                type leafref {
                                    path "../../../../../../../../subscriber-mgmt/sla-profile/name";
                                }
                                description "SLA profile name";
                            }

                            ///nokia-conf/configure/service/vprn/subscriber-interface/group-interface/sap/static-host/ipv6/ancp-string
                            leaf ancp-string {
                                type types-submgt:ancp-string;
                                description "ANCP string";
                            }

                            ///nokia-conf/configure/service/vprn/subscriber-interface/group-interface/sap/static-host/ipv6/int-dest-id
                            leaf int-dest-id {
                                type types-submgt:int-dest-id;
                                description "Intermediate destination ID";
                            }

                            ///nokia-conf/configure/service/vprn/subscriber-interface/group-interface/sap/static-host/ipv6/mac-linking
                            leaf mac-linking {
                                type types-sros:ipv4-unicast-address;
                                description "IPv6 host linked with IPv4 host via learned MAC address";
                            }

                            ///nokia-conf/configure/service/vprn/subscriber-interface/group-interface/sap/static-host/ipv6/retail-svc-id
                            leaf retail-svc-id {
                                type types-services:external-service-id;
                                sros-ext:auto-restart-to-modify;
                                description "Retail service ID";
                            }

                            ///nokia-conf/configure/service/vprn/subscriber-interface/group-interface/sap/static-host/ipv6/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/sap/static-host/ipv6/apply-groups-exclude
                            leaf-list apply-groups-exclude {
                                type leafref {
                                    path "../../../../../../../../groups/group/name";
                                }
                                max-elements 8;
                                ordered-by user;
                                description "Exclude a configuration group at this level";
                            }

                            ///nokia-conf/configure/service/vprn/subscriber-interface/group-interface/sap/static-host/ipv6/app-profile
                            container app-profile {
                                description "Enter the app-profile context";

                                ///nokia-conf/configure/service/vprn/subscriber-interface/group-interface/sap/static-host/ipv6/app-profile/profile
                                leaf profile {
                                    type leafref {
                                        path "../../../../../../../../../application-assurance/group/partition/policy/app-profile/app-profile-name";
                                    }
                                    description "Application profile used by the static host";
                                }

                                ///nokia-conf/configure/service/vprn/subscriber-interface/group-interface/sap/static-host/ipv6/app-profile/scope
                                leaf scope {
                                    type types-submgt:aa-sub-scope;
                                    default "subscriber";
                                    description "Scope of the static host application profile";
                                }

                            } // container app-profile

                            ///nokia-conf/configure/service/vprn/subscriber-interface/group-interface/sap/static-host/ipv6/subscriber-id
                            container subscriber-id {
                                description "Enter the subscriber-id context";

                                ///nokia-conf/configure/service/vprn/subscriber-interface/group-interface/sap/static-host/ipv6/subscriber-id/subscriber-id
                                choice subscriber-id {
                                    ///nokia-conf/configure/service/vprn/subscriber-interface/group-interface/sap/static-host/ipv6/subscriber-id/subscriber-id/string
                                    case string {

                                        ///nokia-conf/configure/service/vprn/subscriber-interface/group-interface/sap/static-host/ipv6/subscriber-id/subscriber-id/string/string
                                        leaf string {
                                            type types-submgt:subscriber-id;
                                            description "Subscriber identification";
                                        }

                                    }
                                    ///nokia-conf/configure/service/vprn/subscriber-interface/group-interface/sap/static-host/ipv6/subscriber-id/subscriber-id/use-sap-id
                                    case use-sap-id {

                                        ///nokia-conf/configure/service/vprn/subscriber-interface/group-interface/sap/static-host/ipv6/subscriber-id/subscriber-id/use-sap-id/use-sap-id
                                        leaf use-sap-id {
                                            type empty;
                                            description "Use the SAP id as subscriber ID";
                                        }

                                    }
                                }
                            } // container subscriber-id

                            ///nokia-conf/configure/service/vprn/subscriber-interface/group-interface/sap/static-host/ipv6/shcv
                            container shcv {
                                description "Enter the shcv context";

                            } // container shcv

                            ///nokia-conf/configure/service/vprn/subscriber-interface/group-interface/sap/static-host/ipv6/managed-route
                            list managed-route {
                                key "ipv6-prefix";
                                description "Enter the managed-route list instance";

                                ///nokia-conf/configure/service/vprn/subscriber-interface/group-interface/sap/static-host/ipv6/managed-route/ipv6-prefix
                                leaf ipv6-prefix {
                                    type types-sros:ipv6-unicast-prefix;
                                    description "Managed route prefix associated with IPv6 static host";
                                }

                                ///nokia-conf/configure/service/vprn/subscriber-interface/group-interface/sap/static-host/ipv6/managed-route/metric
                                leaf metric {
                                    type uint32;
                                    default "0";
                                    description "Metric associated with the provisioned managed route";
                                }

                                ///nokia-conf/configure/service/vprn/subscriber-interface/group-interface/sap/static-host/ipv6/managed-route/preference
                                leaf preference {
                                    type uint32 {
                                        range "0..255";
                                    }
                                    default "0";
                                    description "Preference associated to the provisioned managed route";
                                }

                                ///nokia-conf/configure/service/vprn/subscriber-interface/group-interface/sap/static-host/ipv6/managed-route/tag
                                leaf tag {
                                    type uint32;
                                    default "0";
                                    description "Route tag used if CPE check fails";
                                }

                                ///nokia-conf/configure/service/vprn/subscriber-interface/group-interface/sap/static-host/ipv6/managed-route/apply-groups
                                leaf-list apply-groups {
                                    type leafref {
                                        path "../../../../../../../../../groups/group/name";
                                    }
                                    max-elements 8;
                                    ordered-by user;
                                    description "Apply a configuration group at this level";
                                }

                                ///nokia-conf/configure/service/vprn/subscriber-interface/group-interface/sap/static-host/ipv6/managed-route/apply-groups-exclude
                                leaf-list apply-groups-exclude {
                                    type leafref {
                                        path "../../../../../../../../../groups/group/name";
                                    }
                                    max-elements 8;
                                    ordered-by user;
                                    description "Exclude a configuration group at this level";
                                }

                                ///nokia-conf/configure/service/vprn/subscriber-interface/group-interface/sap/static-host/ipv6/managed-route/cpe-check
                                container cpe-check {
                                    presence "Enable the cpe-check context";
                                    description "Enable the cpe-check context";

                                    ///nokia-conf/configure/service/vprn/subscriber-interface/group-interface/sap/static-host/ipv6/managed-route/cpe-check/destination-ip-address
                                    leaf destination-ip-address {
                                        type types-sros:ip-address;
                                        sros-ext:immutable;
                                        description "IP address of the target CPE device";
                                    }

                                    ///nokia-conf/configure/service/vprn/subscriber-interface/group-interface/sap/static-host/ipv6/managed-route/cpe-check/drop-count
                                    leaf drop-count {
                                        type uint32 {
                                            range "1..255";
                                        }
                                        default "3";
                                        description "Consecutive ping replies missed before CPE deemed down";
                                    }

                                    ///nokia-conf/configure/service/vprn/subscriber-interface/group-interface/sap/static-host/ipv6/managed-route/cpe-check/interval
                                    leaf interval {
                                        type uint32 {
                                            range "1..255";
                                        }
                                        units "seconds";
                                        default "1";
                                        description "Interval between ICMP pings to target CPE IP address";
                                    }

                                    ///nokia-conf/configure/service/vprn/subscriber-interface/group-interface/sap/static-host/ipv6/managed-route/cpe-check/log
                                    leaf log {
                                        type boolean;
                                        default "false";
                                        description "Log CPE connectivity checks transitions";
                                    }

                                    ///nokia-conf/configure/service/vprn/subscriber-interface/group-interface/sap/static-host/ipv6/managed-route/cpe-check/padding-size
                                    leaf padding-size {
                                        type uint32 {
                                            range "0..16384";
                                        }
                                        units "bytes";
                                        default "56";
                                        description "Padding size for CPE connectivity checks";
                                    }

                                    ///nokia-conf/configure/service/vprn/subscriber-interface/group-interface/sap/static-host/ipv6/managed-route/cpe-check/timeout
                                    leaf timeout {
                                        type uint32 {
                                            range "1..10";
                                        }
                                        units "seconds";
                                        default "1";
                                        description "Time interval determining that a ping is missed";
                                    }

                                    ///nokia-conf/configure/service/vprn/subscriber-interface/group-interface/sap/static-host/ipv6/managed-route/cpe-check/source-ip-address
                                    leaf source-ip-address {
                                        type types-sros:ip-address;
                                        description "Source IP address used in the ICMP messages";
                                    }

                                    ///nokia-conf/configure/service/vprn/subscriber-interface/group-interface/sap/static-host/ipv6/managed-route/cpe-check/apply-groups
                                    leaf-list apply-groups {
                                        type leafref {
                                            path "../../../../../../../../../../groups/group/name";
                                        }
                                        max-elements 8;
                                        ordered-by user;
                                        description "Apply a configuration group at this level";
                                    }

                                    ///nokia-conf/configure/service/vprn/subscriber-interface/group-interface/sap/static-host/ipv6/managed-route/cpe-check/apply-groups-exclude
                                    leaf-list apply-groups-exclude {
                                        type leafref {
                                            path "../../../../../../../../../../groups/group/name";
                                        }
                                        max-elements 8;
                                        ordered-by user;
                                        description "Exclude a configuration group at this level";
                                    }

                                    ///nokia-conf/configure/service/vprn/subscriber-interface/group-interface/sap/static-host/ipv6/managed-route/cpe-check/failed-action
                                    container failed-action {
                                        description "Enter the failed-action context";

                                        ///nokia-conf/configure/service/vprn/subscriber-interface/group-interface/sap/static-host/ipv6/managed-route/cpe-check/failed-action/withdraw-or-modify
                                        choice withdraw-or-modify {
                                            ///nokia-conf/configure/service/vprn/subscriber-interface/group-interface/sap/static-host/ipv6/managed-route/cpe-check/failed-action/withdraw-or-modify/withdraw
                                            case withdraw {

                                                ///nokia-conf/configure/service/vprn/subscriber-interface/group-interface/sap/static-host/ipv6/managed-route/cpe-check/failed-action/withdraw-or-modify/withdraw/withdraw
                                                leaf withdraw {
                                                    type boolean;
                                                    default "false";
                                                    description "Withdraw the route when the CPE check fails";
                                                }

                                            }
                                            ///nokia-conf/configure/service/vprn/subscriber-interface/group-interface/sap/static-host/ipv6/managed-route/cpe-check/failed-action/withdraw-or-modify/modify
                                            case modify {

                                                ///nokia-conf/configure/service/vprn/subscriber-interface/group-interface/sap/static-host/ipv6/managed-route/cpe-check/failed-action/withdraw-or-modify/modify/metric
                                                leaf metric {
                                                    type uint32;
                                                    default "0";
                                                    description "Metric associated with the provisioned managed route";
                                                }

                                                ///nokia-conf/configure/service/vprn/subscriber-interface/group-interface/sap/static-host/ipv6/managed-route/cpe-check/failed-action/withdraw-or-modify/modify/preference
                                                leaf preference {
                                                    type int32 {
                                                        range "0..255";
                                                    }
                                                    description "Preference associated to the provisioned managed route";
                                                }

                                                ///nokia-conf/configure/service/vprn/subscriber-interface/group-interface/sap/static-host/ipv6/managed-route/cpe-check/failed-action/withdraw-or-modify/modify/tag
                                                leaf tag {
                                                    type uint32;
                                                    default "0";
                                                    description "Route tag used if CPE check fails";
                                                }

                                            }
                                        }
                                    } // container failed-action

                                } // container cpe-check

                            } // list managed-route

                        } // list ipv6

                    } // container static-host

                    ///nokia-conf/configure/service/vprn/subscriber-interface/group-interface/sap/igmp-host-tracking
                    container igmp-host-tracking {
                        description "Enable the igmp-host-tracking context";

                        ///nokia-conf/configure/service/vprn/subscriber-interface/group-interface/sap/igmp-host-tracking/expiry-time
                        leaf expiry-time {
                            type types-sros:time-duration {
                                range "1..65535";
                            }
                            units "seconds";
                            description "Time that the system continues to track inactive hosts";
                        }

                        ///nokia-conf/configure/service/vprn/subscriber-interface/group-interface/sap/igmp-host-tracking/import-policy
                        leaf import-policy {
                            type leafref {
                                path "../../../../../../../policy-options/policy-statement/name";
                            }
                            description "Import policy that filters IGMP packets";
                        }

                        ///nokia-conf/configure/service/vprn/subscriber-interface/group-interface/sap/igmp-host-tracking/maximum-number-groups
                        leaf maximum-number-groups {
                            type uint32 {
                                range "1..16000";
                            }
                            description "Maximum number of multicast groups to be tracked";
                        }

                        ///nokia-conf/configure/service/vprn/subscriber-interface/group-interface/sap/igmp-host-tracking/maximum-number-group-sources
                        leaf maximum-number-group-sources {
                            type uint32 {
                                range "1..32000";
                            }
                            description "Maximum number of multicast groups to track per group";
                        }

                        ///nokia-conf/configure/service/vprn/subscriber-interface/group-interface/sap/igmp-host-tracking/maximum-number-sources
                        leaf maximum-number-sources {
                            type uint32 {
                                range "1..1000";
                            }
                            description "Maximum number of multicast sources to be tracked";
                        }

                        ///nokia-conf/configure/service/vprn/subscriber-interface/group-interface/sap/igmp-host-tracking/router-alert-check
                        leaf router-alert-check {
                            type boolean;
                            default "true";
                            description "Enable IGMP router alert check option";
                        }

                        ///nokia-conf/configure/service/vprn/subscriber-interface/group-interface/sap/igmp-host-tracking/apply-groups
                        leaf-list apply-groups {
                            type leafref {
                                path "../../../../../../../groups/group/name";
                            }
                            max-elements 8;
                            ordered-by user;
                            description "Apply a configuration group at this level";
                        }

                        ///nokia-conf/configure/service/vprn/subscriber-interface/group-interface/sap/igmp-host-tracking/apply-groups-exclude
                        leaf-list apply-groups-exclude {
                            type leafref {
                                path "../../../../../../../groups/group/name";
                            }
                            max-elements 8;
                            ordered-by user;
                            description "Exclude a configuration group at this level";
                        }

                    } // container igmp-host-tracking

                    ///nokia-conf/configure/service/vprn/subscriber-interface/group-interface/sap/default-host
                    container default-host {
                        description "Enter the default-host context";

                        ///nokia-conf/configure/service/vprn/subscriber-interface/group-interface/sap/default-host/ipv4
                        list ipv4 {
                            key "address prefix-length";
                            description "Enter the ipv4 list instance";

                            ///nokia-conf/configure/service/vprn/subscriber-interface/group-interface/sap/default-host/ipv4/address
                            leaf address {
                                type leafref {
                                    path "../../../../../ipv4/address/ipv4-address";
                                }
                                description "IPv4 default host address";
                            }

                            ///nokia-conf/configure/service/vprn/subscriber-interface/group-interface/sap/default-host/ipv4/prefix-length
                            leaf prefix-length {
                                type uint32 {
                                    range "0..32";
                                }
                                description "IPv4 address prefix length";
                            }

                            ///nokia-conf/configure/service/vprn/subscriber-interface/group-interface/sap/default-host/ipv4/next-hop
                            leaf next-hop {
                                type types-sros:ipv4-unicast-address;
                                sros-ext:immutable;
                                mandatory true;
                                description "Next-hop IP address used to forward traffic on the SAP";
                            }

                            ///nokia-conf/configure/service/vprn/subscriber-interface/group-interface/sap/default-host/ipv4/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/sap/default-host/ipv4/apply-groups-exclude
                            leaf-list apply-groups-exclude {
                                type leafref {
                                    path "../../../../../../../../groups/group/name";
                                }
                                max-elements 8;
                                ordered-by user;
                                description "Exclude a configuration group at this level";
                            }

                        } // list ipv4

                        ///nokia-conf/configure/service/vprn/subscriber-interface/group-interface/sap/default-host/ipv6
                        list ipv6 {
                            key "address prefix-length";
                            description "Enter the ipv6 list instance";

                            ///nokia-conf/configure/service/vprn/subscriber-interface/group-interface/sap/default-host/ipv6/address
                            leaf address {
                                type types-sros:ipv6-unicast-address;
                                description "IPv6 default host address";
                            }

                            ///nokia-conf/configure/service/vprn/subscriber-interface/group-interface/sap/default-host/ipv6/prefix-length
                            leaf prefix-length {
                                type uint32 {
                                    range "0..128";
                                }
                                description "IPv6 prefix length";
                            }

                            ///nokia-conf/configure/service/vprn/subscriber-interface/group-interface/sap/default-host/ipv6/next-hop
                            leaf next-hop {
                                type types-sros:ipv6-unicast-address;
                                sros-ext:immutable;
                                mandatory true;
                                description "Next-hop IP address used to forward traffic on the SAP";
                            }

                            ///nokia-conf/configure/service/vprn/subscriber-interface/group-interface/sap/default-host/ipv6/apply-groups
                            leaf-list apply-groups {
                                type leafref {
                                    path "../../../../../../../../groups/group/name";
                                }
                                max-elements 8;
                                ordered-by user;
                                description "Apply a configuration group at this level";
                            }

                            ///nokia-conf/configure/service/vprn/subscriber-interface/group-interface/sap/default-host/ipv6/apply-groups-exclude
                            leaf-list apply-groups-exclude {
                                type leafref {
                                    path "../../../../../../../../groups/group/name";
                                }
                                max-elements 8;
                                ordered-by user;
                                description "Exclude a configuration group at this level";
                            }

                        } // list ipv6

                    } // container default-host

                } // list sap

                uses conf-svc-vprn-grp-if-wlangw-wlan-gw;
            } // list group-interface

            uses conf-svc-vprn-sub-if-wlangw-wlan-gw;
        } // list subscriber-interface

    } // grouping conf-svc-vprn-sub-if-subscriber-interface

}
