submodule nokia-state-router-origin-validation {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel23";
    organization "Nokia";
    contact
        "Nokia SR OS Support
         Web: <http://www.nokia.com>";
    description
        "Nokia YANG Data model with operational state for origin-validation on SR OS based routers.

         Copyright 2016 Nokia. All rights reserved. Reproduction of this document
         is authorized on the condition that the foregoing copyright notice is included.

         This nokia-state-router-origin-validation YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-12-06";

    grouping state-router-origin-validation {
        ///nokia-state/state/router/origin-validation
        container origin-validation {
            description "Enter the origin-validation context";

            ///nokia-state/state/router/origin-validation/rpki-session
            list rpki-session {
                key "ip-address";
                description "Enter the rpki-session list instance";

                ///nokia-state/state/router/origin-validation/rpki-session/ip-address
                leaf ip-address {
                    type types-sros:ip-address;
                    description "IPv4 or IPv6 address for the RPKI local cache server";
                }

                ///nokia-state/state/router/origin-validation/rpki-session/session-state
                leaf session-state {
                    type enumeration {
                        enum idle                           { value 0; }
                        enum connect                        { value 1; }
                        enum established                    { value 2; }
                        enum cleanup                        { value 3; }
                    }
                    description "The current state of a particular session.";
                }

                ///nokia-state/state/router/origin-validation/rpki-session/session-flaps
                leaf session-flaps {
                    type uint32;
                    description
                        "The number of times the session has transitioned from 'established'
                         state to 'idle' state.";
                }

                ///nokia-state/state/router/origin-validation/rpki-session/established-time
                leaf established-time {
                    type yang:date-and-time;
                    description "The time since this session is active.";
                }

                ///nokia-state/state/router/origin-validation/rpki-session/active-ipv4-records
                leaf active-ipv4-records {
                    type uint32;
                    description "The number of active, non-withdrawn IPv4 records.";
                }

                ///nokia-state/state/router/origin-validation/rpki-session/active-ipv6-records
                leaf active-ipv6-records {
                    type uint32;
                    description "The number of active, non-withdrawn IPv6 records.";
                }

                ///nokia-state/state/router/origin-validation/rpki-session/serial-id
                leaf serial-id {
                    type uint32;
                    description "The serial id associated with this session.";
                }

                ///nokia-state/state/router/origin-validation/rpki-session/session-id
                leaf session-id {
                    type uint32;
                    description "The session id of this session.";
                }

            } // list rpki-session

        } // container origin-validation

    } // grouping state-router-origin-validation

}
