submodule nokia-conf-svc-vprn-isis {

    yang-version "1.1";

    belongs-to nokia-conf { prefix "conf"; }

    import ietf-yang-types                { prefix "yang"; }
    import nokia-sros-yang-extensions     { prefix "sros-ext"; }
    import nokia-types-igp                { prefix "types-igp"; }
    import nokia-types-isis               { prefix "types-isis"; }
    import nokia-types-sros               { prefix "types-sros"; }

    include nokia-conf-groups;
    include nokia-conf-policy-options;
    include nokia-conf-routing-options;
    include nokia-conf-system;
    include nokia-conf-system-security;

    sros-ext:sros-major-release "rel23";
    organization "Nokia";
    contact
        "Nokia SR OS Support
         Web: <http://www.nokia.com>";
    description
        "Nokia YANG Data model to configure vprn isis protocol attributes on SR OS based routers.

         Copyright 2016 Nokia. All rights reserved. Reproduction of this document
         is authorized on the condition that the foregoing copyright notice is included.

         This nokia-conf-svc-vprn-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-02-02";

    grouping conf-svc-vprn-isis {
        ///nokia-conf/configure/service/vprn/isis
        list isis {
            key "isis-instance";
            description "Enter the isis list instance";

            ///nokia-conf/configure/service/vprn/isis/isis-instance
            leaf isis-instance {
                type int32 {
                    range "0..127";
                }
                description "Instance ID for the IS-IS instance";
            }

            ///nokia-conf/configure/service/vprn/isis/authentication-keychain
            leaf authentication-keychain {
                type leafref {
                    path "../../../../system/security/keychains/keychain/keychain-name";
                }
                description "Keychain used to sign and authenticate";
            }

            ///nokia-conf/configure/service/vprn/isis/authentication-key
            leaf authentication-key {
                type types-sros:encrypted-leaf {
                    length "1..366";
                }
                description "Authentication key to verify PDUs sent from neighbors";
            }

            ///nokia-conf/configure/service/vprn/isis/authentication-type
            leaf authentication-type {
                type types-isis:auth-type;
                description "Authentication type";
            }

            ///nokia-conf/configure/service/vprn/isis/csnp-authentication
            leaf csnp-authentication {
                type boolean;
                default "true";
                description "Authenticate individual IS-IS packets of the CSNP type";
            }

            ///nokia-conf/configure/service/vprn/isis/psnp-authentication
            leaf psnp-authentication {
                type boolean;
                default "true";
                description "Authenticate individual IS-IS protocol packets of partial sequence number PDU (PSNP) type";
            }

            ///nokia-conf/configure/service/vprn/isis/admin-state
            leaf admin-state {
                type types-sros:admin-state;
                default "disable";
                description "Administrative state of the IS-IS instance";
            }

            ///nokia-conf/configure/service/vprn/isis/advertise-passive-only
            leaf advertise-passive-only {
                type boolean;
                default "false";
                description "Advertise prefixes that belong to passive interfaces";
            }

            ///nokia-conf/configure/service/vprn/isis/advertise-router-capability
            leaf advertise-router-capability {
                type enumeration {
                    enum area                           { value 2; }
                    enum as                             { value 3; }
                }
                description "Router capabilities advertisement to neighbors";
            }

            ///nokia-conf/configure/service/vprn/isis/all-l1isis
            leaf all-l1isis {
                type yang:mac-address;
                default "01:80:C2:00:00:14";
                description "Destination MAC address for all L1 IS-IS routers";
            }

            ///nokia-conf/configure/service/vprn/isis/all-l2isis
            leaf all-l2isis {
                type yang:mac-address;
                default "01:80:C2:00:00:15";
                description "Destination MAC address for all L2 IS-IS routers";
            }

            ///nokia-conf/configure/service/vprn/isis/authentication-check
            leaf authentication-check {
                type boolean;
                default "true";
                description "Perform authentication check to reject mismatch PDUs";
            }

            ///nokia-conf/configure/service/vprn/isis/default-route-tag
            leaf default-route-tag {
                type uint32 {
                    range "1..max";
                }
                description "Route tag for the default route";
            }

            ///nokia-conf/configure/service/vprn/isis/hello-authentication
            leaf hello-authentication {
                type boolean;
                default "true";
                description "Authenticate Hello type IS-IS protocol packets";
            }

            ///nokia-conf/configure/service/vprn/isis/ignore-attached-bit
            leaf ignore-attached-bit {
                type boolean;
                default "false";
                description "Ignore attached bit on received Layer 1 LSPs";
            }

            ///nokia-conf/configure/service/vprn/isis/ignore-lsp-errors
            leaf ignore-lsp-errors {
                type boolean;
                default "false";
                description "Ignore LSP packets with errors";
            }

            ///nokia-conf/configure/service/vprn/isis/ignore-narrow-metric
            leaf ignore-narrow-metric {
                type boolean;
                default "false";
                description "Ignore links with narrow metrics";
            }

            ///nokia-conf/configure/service/vprn/isis/iid-tlv
            leaf iid-tlv {
                type boolean;
                default "false";
                description "Use IID TLVs with IS-IS multi-instance";
            }

            ///nokia-conf/configure/service/vprn/isis/ipv4-multicast-routing
            leaf ipv4-multicast-routing {
                type types-isis:routing-topology;
                default "native";
                description "IS-IS topology for IPv4 multicast routing";
            }

            ///nokia-conf/configure/service/vprn/isis/ipv4-routing
            leaf ipv4-routing {
                type boolean;
                default "true";
                description "Support IPv4 routing for IS-IS instance";
            }

            ///nokia-conf/configure/service/vprn/isis/ipv6-routing
            leaf ipv6-routing {
                type types-isis:routing-topology;
                default "false";
                description "Routing topology for IPv6";
            }

            ///nokia-conf/configure/service/vprn/isis/hello-padding
            leaf hello-padding {
                type types-isis:hello-padding-type;
                description "IS-IS Hello message padding";
            }

            ///nokia-conf/configure/service/vprn/isis/level-capability
            leaf level-capability {
                type types-isis:level;
                description "Routing level for instance";
            }

            ///nokia-conf/configure/service/vprn/isis/lsp-lifetime
            leaf lsp-lifetime {
                type uint32 {
                    range "350..65535";
                }
                units "seconds";
                sros-ext:manual-restart-to-modify;
                default "1200";
                description "Amount of time during which an LSP is considered valid";
            }

            ///nokia-conf/configure/service/vprn/isis/lsp-minimum-remaining-lifetime
            leaf lsp-minimum-remaining-lifetime {
                type uint32 {
                    range "350..65535";
                }
                units "seconds";
                description "Minimum value for the Remaining Lifetime of an LSP";
            }

            ///nokia-conf/configure/service/vprn/isis/lsp-mtu-size
            leaf lsp-mtu-size {
                type types-isis:lsp-buffer-ext-size;
                units "bytes";
                sros-ext:manual-restart-to-modify;
                default "1492";
                description "LSP MTU size";
            }

            ///nokia-conf/configure/service/vprn/isis/mru-mismatch-detection
            leaf mru-mismatch-detection {
                type boolean;
                default "false";
                description "Enable detection of MRU mismatch";
            }

            ///nokia-conf/configure/service/vprn/isis/overload-export-interlevel
            leaf overload-export-interlevel {
                type boolean;
                default "false";
                description "Advertise the inter-level routes when router is overloaded";
            }

            ///nokia-conf/configure/service/vprn/isis/overload-export-external
            leaf overload-export-external {
                type boolean;
                default "false";
                description "Advertise the external routes when router is in overloaded";
            }

            ///nokia-conf/configure/service/vprn/isis/poi-tlv
            leaf poi-tlv {
                type boolean;
                default "false";
                description "Purge Originator Identification TLV";
            }

            ///nokia-conf/configure/service/vprn/isis/prefix-attributes-tlv
            leaf prefix-attributes-tlv {
                type boolean;
                default "false";
                description "Use IS-IS Prefix Attributes TLV to exchange extended IPv4 and IPv6 reachability information";
            }

            ///nokia-conf/configure/service/vprn/isis/reference-bandwidth
            leaf reference-bandwidth {
                type types-sros:reference-bandwidth-ext;
                units "kilobps";
                description "Reference bandwidth for bandwidth relative costing";
            }

            ///nokia-conf/configure/service/vprn/isis/router-id
            leaf router-id {
                type types-igp:router-id;
                sros-ext:auto-restart-to-modify;
                description "Unique router ID for the ISIS instance";
            }

            ///nokia-conf/configure/service/vprn/isis/standard-multi-instance
            leaf standard-multi-instance {
                type boolean;
                default "false";
                description "Enable RFC standards compliant multi-instance behavior";
            }

            ///nokia-conf/configure/service/vprn/isis/strict-adjacency-check
            leaf strict-adjacency-check {
                type boolean;
                default "false";
                description "Enable strict checking of address families for IS-IS adjacencies";
            }

            ///nokia-conf/configure/service/vprn/isis/suppress-attached-bit
            leaf suppress-attached-bit {
                type boolean;
                default "false";
                description "Allow IS-IS to suppress setting attached bit on LSPs";
            }

            ///nokia-conf/configure/service/vprn/isis/system-id
            leaf system-id {
                type types-igp:system-id;
                sros-ext:auto-restart-to-modify;
                sros-ext:manual-restart-to-modify;
                description "System ID";
            }

            ///nokia-conf/configure/service/vprn/isis/export-policy
            leaf-list export-policy {
                type leafref {
                    path "../../../../policy-options/policy-statement/name";
                }
                max-elements 5;
                ordered-by user;
                description "Export policies that determine exported routes";
            }

            ///nokia-conf/configure/service/vprn/isis/import-policy
            leaf-list import-policy {
                type leafref {
                    path "../../../../policy-options/policy-statement/name";
                }
                max-elements 5;
                ordered-by user;
                description "Import policy names for routes from IGP to route table";
            }

            ///nokia-conf/configure/service/vprn/isis/area-address
            leaf-list area-address {
                type types-isis:area-address;
                max-elements 3;
                description "Area address portion of the NSAP address";
            }

            ///nokia-conf/configure/service/vprn/isis/apply-groups
            leaf-list apply-groups {
                type leafref {
                    path "../../../../groups/group/name";
                }
                max-elements 8;
                ordered-by user;
                description "Apply a configuration group at this level";
            }

            ///nokia-conf/configure/service/vprn/isis/apply-groups-exclude
            leaf-list apply-groups-exclude {
                type leafref {
                    path "../../../../groups/group/name";
                }
                max-elements 8;
                ordered-by user;
                description "Exclude a configuration group at this level";
            }

            ///nokia-conf/configure/service/vprn/isis/export-limit
            container export-limit {
                presence "Enable the export-limit context";
                description "Enable the export-limit context";

                ///nokia-conf/configure/service/vprn/isis/export-limit/number
                leaf number {
                    type uint32 {
                        range "1..max";
                    }
                    mandatory true;
                    description "Maximum routes or prefixes exported from route table";
                }

                ///nokia-conf/configure/service/vprn/isis/export-limit/log-percent
                leaf log-percent {
                    type uint32 {
                        range "1..100";
                    }
                    description "Export limit before warning and SNMP notification sent";
                }

            } // container export-limit

            ///nokia-conf/configure/service/vprn/isis/graceful-restart
            container graceful-restart {
                presence "Enable the graceful-restart context";
                description "Enable the graceful-restart context";

                ///nokia-conf/configure/service/vprn/isis/graceful-restart/helper-mode
                leaf helper-mode {
                    type boolean;
                    default "true";
                    description "Enable the Graceful Restart helper for IS-IS";
                }

            } // container graceful-restart

            ///nokia-conf/configure/service/vprn/isis/multi-topology
            container multi-topology {
                presence "Enable the multi-topology context";
                description "Enable the multi-topology context";

                ///nokia-conf/configure/service/vprn/isis/multi-topology/ipv6-unicast
                leaf ipv6-unicast {
                    type boolean;
                    default "false";
                    description "Support multi-topology TLVs";
                }

                ///nokia-conf/configure/service/vprn/isis/multi-topology/ipv4-multicast
                leaf ipv4-multicast {
                    type boolean;
                    default "false";
                    description "Support IPv4 topology (MT3)";
                }

            } // container multi-topology

            ///nokia-conf/configure/service/vprn/isis/multicast-import
            container multicast-import {
                description "Enter the multicast-import context";

                ///nokia-conf/configure/service/vprn/isis/multicast-import/ipv4
                leaf ipv4 {
                    type boolean;
                    default "false";
                    description "Submit IPv4 routes into the multicast RPF of the RTM";
                }

            } // container multicast-import

            ///nokia-conf/configure/service/vprn/isis/overload
            container overload {
                presence "Enable the overload context";
                description "Enable the overload context";

                ///nokia-conf/configure/service/vprn/isis/overload/max-metric
                leaf max-metric {
                    type boolean;
                    default "false";
                    description "Advertise transit links with maximum metric instead of setting overload bit";
                }

            } // container overload

            ///nokia-conf/configure/service/vprn/isis/overload-on-boot
            container overload-on-boot {
                presence "Enable the overload-on-boot context";
                description "Enable the overload-on-boot context";

                ///nokia-conf/configure/service/vprn/isis/overload-on-boot/timeout
                leaf timeout {
                    type uint32 {
                        range "60..1800";
                    }
                    units "seconds";
                    description "Time during which the router operates in overload state after reboot";
                }

                ///nokia-conf/configure/service/vprn/isis/overload-on-boot/max-metric
                leaf max-metric {
                    type boolean;
                    default "false";
                    description "Advertise transit links with maximum metric instead of setting overload bit";
                }

            } // container overload-on-boot

            ///nokia-conf/configure/service/vprn/isis/overload-fib-error-notify-only
            container overload-fib-error-notify-only {
                presence "Enable the overload-fib-error-notify-only context";
                description "Enable the overload-fib-error-notify-only context";

                ///nokia-conf/configure/service/vprn/isis/overload-fib-error-notify-only/retry
                leaf retry {
                    type uint32 {
                        range "10..1800";
                    }
                    units "seconds";
                    default "10";
                    description "Time to retry programming failed entries in the FIB";
                }

            } // container overload-fib-error-notify-only

            ///nokia-conf/configure/service/vprn/isis/prefix-limit
            container prefix-limit {
                presence "Enable the prefix-limit context";
                description "Enable the prefix-limit context";

                ///nokia-conf/configure/service/vprn/isis/prefix-limit/limit
                leaf limit {
                    type uint32 {
                        range "1..max";
                    }
                    mandatory true;
                    description "Maximum number of prefixes for IS-IS instance";
                }

                ///nokia-conf/configure/service/vprn/isis/prefix-limit/log-only
                leaf log-only {
                    type boolean;
                    default "false";
                    description "Send warning message when the prefix limit is reached";
                }

                ///nokia-conf/configure/service/vprn/isis/prefix-limit/warning-threshold
                leaf warning-threshold {
                    type uint32 {
                        range "0..100";
                    }
                    units "percent";
                    default "0";
                    description "Threshold value to trigger a warning message to be sent";
                }

                ///nokia-conf/configure/service/vprn/isis/prefix-limit/overload-timeout
                leaf overload-timeout {
                    type types-igp:overload-timeout;
                    default "forever";
                    description "Time in overload state when prefix limit is reached";
                }

            } // container prefix-limit

            ///nokia-conf/configure/service/vprn/isis/lsp-refresh
            container lsp-refresh {
                description "Enter the lsp-refresh context";

                ///nokia-conf/configure/service/vprn/isis/lsp-refresh/interval
                leaf interval {
                    type uint32 {
                        range "150..65535";
                    }
                    units "seconds";
                    default "600";
                    description "Refresh timer interval";
                }

                ///nokia-conf/configure/service/vprn/isis/lsp-refresh/half-lifetime
                leaf half-lifetime {
                    type boolean;
                    default "true";
                    description "Set the refresh interval to always be half the LSP lifetime";
                }

            } // container lsp-refresh

            ///nokia-conf/configure/service/vprn/isis/rib-priority
            container rib-priority {
                description "Enter the rib-priority context";

                ///nokia-conf/configure/service/vprn/isis/rib-priority/high
                container high {
                    description "Enter the high context";

                    ///nokia-conf/configure/service/vprn/isis/rib-priority/high/type
                    choice type {
                        ///nokia-conf/configure/service/vprn/isis/rib-priority/high/type/prefix-list
                        case prefix-list {

                            ///nokia-conf/configure/service/vprn/isis/rib-priority/high/type/prefix-list/prefix-list
                            leaf prefix-list {
                                type leafref {
                                    path "../../../../../../policy-options/prefix-list/name";
                                }
                                description "List used to select routes processed at higher priority through OSPF route calculation process";
                            }

                        }
                        ///nokia-conf/configure/service/vprn/isis/rib-priority/high/type/tag
                        case tag {

                            ///nokia-conf/configure/service/vprn/isis/rib-priority/high/type/tag/tag
                            leaf tag {
                                type uint32 {
                                    range "1..max";
                                }
                                description "Tag value that is used to match IS-IS routes";
                            }

                        }
                    }
                } // container high

            } // container rib-priority

            ///nokia-conf/configure/service/vprn/isis/timers
            container timers {
                description "Enter the timers context";

                ///nokia-conf/configure/service/vprn/isis/timers/spf-wait
                container spf-wait {
                    description "Enter the spf-wait context";

                    ///nokia-conf/configure/service/vprn/isis/timers/spf-wait/spf-max-wait
                    leaf spf-max-wait {
                        type uint32 {
                            range "10..120000";
                        }
                        units "milliseconds";
                        default "10000";
                        description "Maximum interval amid two consecutive SPF calculations";
                    }

                    ///nokia-conf/configure/service/vprn/isis/timers/spf-wait/spf-initial-wait
                    leaf spf-initial-wait {
                        type uint32 {
                            range "10..100000";
                        }
                        units "milliseconds";
                        default "1000";
                        description "Initial SPF calculation delay after topology change";
                    }

                    ///nokia-conf/configure/service/vprn/isis/timers/spf-wait/spf-second-wait
                    leaf spf-second-wait {
                        type uint32 {
                            range "10..100000";
                        }
                        units "milliseconds";
                        default "1000";
                        description "Hold time between first and second SPF calculations";
                    }

                } // container spf-wait

                ///nokia-conf/configure/service/vprn/isis/timers/lsp-wait
                container lsp-wait {
                    description "Enter the lsp-wait context";

                    ///nokia-conf/configure/service/vprn/isis/timers/lsp-wait/lsp-max-wait
                    leaf lsp-max-wait {
                        type uint32 {
                            range "10..120000";
                        }
                        units "milliseconds";
                        default "5000";
                        description "Maximum time between two consecutive LSP occurrences";
                    }

                    ///nokia-conf/configure/service/vprn/isis/timers/lsp-wait/lsp-initial-wait
                    leaf lsp-initial-wait {
                        type uint32 {
                            range "10..100000";
                        }
                        units "milliseconds";
                        default "10";
                        description "Initial LSP generation delay";
                    }

                    ///nokia-conf/configure/service/vprn/isis/timers/lsp-wait/lsp-second-wait
                    leaf lsp-second-wait {
                        type uint32 {
                            range "10..100000";
                        }
                        units "milliseconds";
                        default "1000";
                        description "Delay between first and second LSP generation";
                    }

                } // container lsp-wait

            } // container timers

            ///nokia-conf/configure/service/vprn/isis/unicast-import
            container unicast-import {
                description "Enter the unicast-import context";

                ///nokia-conf/configure/service/vprn/isis/unicast-import/ipv4
                leaf ipv4 {
                    type boolean;
                    default "true";
                    description "Submit IPv4 routes into unicast RTM";
                }

                ///nokia-conf/configure/service/vprn/isis/unicast-import/ipv6
                leaf ipv6 {
                    type boolean;
                    default "true";
                    description "Submit IPv6 routes into unicast RTM";
                }

            } // container unicast-import

            ///nokia-conf/configure/service/vprn/isis/loopfree-alternate
            container loopfree-alternate {
                presence "Enable the loopfree-alternate context";
                description "Enable the loopfree-alternate context";

                ///nokia-conf/configure/service/vprn/isis/loopfree-alternate/exclude
                container exclude {
                    description "Enter the exclude context";

                    ///nokia-conf/configure/service/vprn/isis/loopfree-alternate/exclude/prefix-policy
                    leaf-list prefix-policy {
                        type leafref {
                            path "../../../../../../policy-options/policy-statement/name";
                        }
                        max-elements 5;
                        ordered-by user;
                        description "Policy to exclude prefixes from LFA SPF calculation";
                    }

                } // container exclude

            } // container loopfree-alternate

            ///nokia-conf/configure/service/vprn/isis/interface
            list interface {
                key "interface-name";
                description "Enter the interface list instance";

                ///nokia-conf/configure/service/vprn/isis/interface/interface-name
                leaf interface-name {
                    type types-sros:interface-name;
                    description "IP interface name";
                }

                ///nokia-conf/configure/service/vprn/isis/interface/admin-state
                leaf admin-state {
                    type types-sros:admin-state;
                    default "enable";
                    description "Administrative state of the IS-IS interface";
                }

                ///nokia-conf/configure/service/vprn/isis/interface/hello-authentication-key
                leaf hello-authentication-key {
                    type types-sros:encrypted-leaf {
                        length "1..366";
                    }
                    description "Authentication key or hash string for Hello PDUs";
                }

                ///nokia-conf/configure/service/vprn/isis/interface/hello-authentication-keychain
                leaf hello-authentication-keychain {
                    type leafref {
                        path "../../../../../system/security/keychains/keychain/keychain-name";
                    }
                    description "Authentication keychain to use for the session";
                }

                ///nokia-conf/configure/service/vprn/isis/interface/hello-authentication-type
                leaf hello-authentication-type {
                    type types-isis:auth-type;
                    description "Hello authentication type";
                }

                ///nokia-conf/configure/service/vprn/isis/interface/hello-padding
                leaf hello-padding {
                    type types-isis:hello-padding-type;
                    description "Padding on IS-IS Hello packets";
                }

                ///nokia-conf/configure/service/vprn/isis/interface/passive
                leaf passive {
                    type boolean;
                    default "false";
                    description "Passive interface";
                }

                ///nokia-conf/configure/service/vprn/isis/interface/csnp-interval
                leaf csnp-interval {
                    type uint32 {
                        range "1..65535";
                    }
                    units "seconds";
                    default "10";
                    description "Time interval between successive CSN PDUs sent";
                }

                ///nokia-conf/configure/service/vprn/isis/interface/default-instance
                leaf default-instance {
                    type boolean;
                    default "false";
                    description "Allow non-MI capable router to establish an adjacency";
                }

                ///nokia-conf/configure/service/vprn/isis/interface/hello-authentication
                leaf hello-authentication {
                    type boolean;
                    default "true";
                    description "Authenticate Hello type IS-IS protocol packets";
                }

                ///nokia-conf/configure/service/vprn/isis/interface/interface-type
                leaf interface-type {
                    type types-isis:interface-type;
                    description "Interface type to broadcast, point-to-point, or to be default";
                }

                ///nokia-conf/configure/service/vprn/isis/interface/ipv4-multicast
                leaf ipv4-multicast {
                    type boolean;
                    default "true";
                    description "Enable IPv4 multicast routing for the interface";
                }

                ///nokia-conf/configure/service/vprn/isis/interface/ipv6-unicast
                leaf ipv6-unicast {
                    type boolean;
                    default "true";
                    description "Enable IPv6 unicast routing for the interface";
                }

                ///nokia-conf/configure/service/vprn/isis/interface/level-capability
                leaf level-capability {
                    type types-isis:level;
                    description "IS-IS levels for this interface";
                }

                ///nokia-conf/configure/service/vprn/isis/interface/load-balancing-weight
                leaf load-balancing-weight {
                    type uint32;
                    description "Load balancing weight";
                }

                ///nokia-conf/configure/service/vprn/isis/interface/lsp-pacing-interval
                leaf lsp-pacing-interval {
                    type uint32 {
                        range "0..65535";
                    }
                    units "milliseconds";
                    default "100";
                    description "Interval for sending LSPs from interface";
                }

                ///nokia-conf/configure/service/vprn/isis/interface/retransmit-interval
                leaf retransmit-interval {
                    type uint32 {
                        range "1..65535";
                    }
                    units "seconds";
                    default "5";
                    description "Minimum time between LSP PDU retransmissions on point-to-point interface";
                }

                ///nokia-conf/configure/service/vprn/isis/interface/tag
                leaf tag {
                    type uint32 {
                        range "1..max";
                    }
                    description "Route tag for IP address of interface";
                }

                ///nokia-conf/configure/service/vprn/isis/interface/apply-groups
                leaf-list apply-groups {
                    type leafref {
                        path "../../../../../groups/group/name";
                    }
                    max-elements 8;
                    ordered-by user;
                    description "Apply a configuration group at this level";
                }

                ///nokia-conf/configure/service/vprn/isis/interface/apply-groups-exclude
                leaf-list apply-groups-exclude {
                    type leafref {
                        path "../../../../../groups/group/name";
                    }
                    max-elements 8;
                    ordered-by user;
                    description "Exclude a configuration group at this level";
                }

                ///nokia-conf/configure/service/vprn/isis/interface/loopfree-alternate
                container loopfree-alternate {
                    description "Enter the loopfree-alternate context";

                    ///nokia-conf/configure/service/vprn/isis/interface/loopfree-alternate/exclude
                    leaf exclude {
                        type boolean;
                        default "false";
                        description "Enable/disable Loopfree Alternative at interface level.";
                    }

                    ///nokia-conf/configure/service/vprn/isis/interface/loopfree-alternate/policy-map
                    container policy-map {
                        presence "Enable the policy-map context";
                        description "Enable the policy-map context";

                        ///nokia-conf/configure/service/vprn/isis/interface/loopfree-alternate/policy-map/route-nh-template
                        leaf route-nh-template {
                            type leafref {
                                path "../../../../../../../routing-options/route-next-hop-policy/template/template-name";
                            }
                            mandatory true;
                            description "Route next hop policy template name";
                        }

                    } // container policy-map

                } // container loopfree-alternate

                ///nokia-conf/configure/service/vprn/isis/interface/mesh-group
                container mesh-group {
                    presence "Enable the mesh-group context";
                    description "Enable the mesh-group context";

                    ///nokia-conf/configure/service/vprn/isis/interface/mesh-group/type
                    choice type {
                        ///nokia-conf/configure/service/vprn/isis/interface/mesh-group/type/value
                        case value {

                            ///nokia-conf/configure/service/vprn/isis/interface/mesh-group/type/value/value
                            leaf value {
                                type int32 {
                                    range "1..2000000000";
                                }
                                description "Mesh group for the interface";
                            }

                        }
                        ///nokia-conf/configure/service/vprn/isis/interface/mesh-group/type/blocked
                        case blocked {

                            ///nokia-conf/configure/service/vprn/isis/interface/mesh-group/type/blocked/blocked
                            leaf blocked {
                                type empty;
                                description "Prevent the interface from flooding LSPs";
                            }

                        }
                    }
                } // container mesh-group

                ///nokia-conf/configure/service/vprn/isis/interface/bfd-liveness
                container bfd-liveness {
                    description "Enter the bfd-liveness context";

                    ///nokia-conf/configure/service/vprn/isis/interface/bfd-liveness/ipv4
                    container ipv4 {
                        presence "Enable the ipv4 context";
                        description "Enable the ipv4 context";

                        ///nokia-conf/configure/service/vprn/isis/interface/bfd-liveness/ipv4/include-bfd-tlv
                        leaf include-bfd-tlv {
                            type boolean;
                            default "false";
                            description "Enable IS-IS BFD TLVs on the interface";
                        }

                    } // container ipv4

                    ///nokia-conf/configure/service/vprn/isis/interface/bfd-liveness/ipv6
                    container ipv6 {
                        presence "Enable the ipv6 context";
                        description "Enable the ipv6 context";

                        ///nokia-conf/configure/service/vprn/isis/interface/bfd-liveness/ipv6/include-bfd-tlv
                        leaf include-bfd-tlv {
                            type boolean;
                            default "false";
                            description "Enable IS-IS BFD TLVs on the interface";
                        }

                    } // container ipv6

                } // container bfd-liveness

                ///nokia-conf/configure/service/vprn/isis/interface/level
                list level {
                    key "level-number";
                    max-elements 2;
                    description "Enter the level list instance";

                    ///nokia-conf/configure/service/vprn/isis/interface/level/level-number
                    leaf level-number {
                        type enumeration {
                            enum 1                              { value 1; }
                            enum 2                              { value 2; }
                        }
                        description "ISIS protocol level number";
                    }

                    ///nokia-conf/configure/service/vprn/isis/interface/level/hello-authentication-key
                    leaf hello-authentication-key {
                        type types-sros:encrypted-leaf {
                            length "1..366";
                        }
                        description "Authentication key for Hello PDUs";
                    }

                    ///nokia-conf/configure/service/vprn/isis/interface/level/hello-authentication-keychain
                    leaf hello-authentication-keychain {
                        type leafref {
                            path "../../../../../../system/security/keychains/keychain/keychain-name";
                        }
                        description "Authentication keychain to use for the session";
                    }

                    ///nokia-conf/configure/service/vprn/isis/interface/level/hello-authentication-type
                    leaf hello-authentication-type {
                        type types-isis:auth-type;
                        description "Hello authentication enabled on the context";
                    }

                    ///nokia-conf/configure/service/vprn/isis/interface/level/hello-padding
                    leaf hello-padding {
                        type types-isis:hello-padding-type;
                        description "Padding on IS-IS Hello packets";
                    }

                    ///nokia-conf/configure/service/vprn/isis/interface/level/passive
                    leaf passive {
                        type boolean;
                        default "false";
                        description "Passive interface";
                    }

                    ///nokia-conf/configure/service/vprn/isis/interface/level/hello-interval
                    leaf hello-interval {
                        type uint32 {
                            range "1..20000";
                        }
                        units "seconds";
                        default "9";
                        description "Interval between Hello messages sent on this level";
                    }

                    ///nokia-conf/configure/service/vprn/isis/interface/level/hello-multiplier
                    leaf hello-multiplier {
                        type int32 {
                            range "2..100";
                        }
                        default "3";
                        description "Hello messages missed from neighbor before router declares adjacency down";
                    }

                    ///nokia-conf/configure/service/vprn/isis/interface/level/ipv4-multicast-metric
                    leaf ipv4-multicast-metric {
                        type types-isis:metric;
                        description "IS-IS interface metric applied for IPv4 multicast";
                    }

                    ///nokia-conf/configure/service/vprn/isis/interface/level/ipv6-unicast-metric
                    leaf ipv6-unicast-metric {
                        type types-isis:metric;
                        description "IS-IS interface metric applied for IPv6 unicast";
                    }

                    ///nokia-conf/configure/service/vprn/isis/interface/level/metric
                    leaf metric {
                        type types-isis:metric;
                        description "IS-IS interface metric applied for IPv4 unicast";
                    }

                    ///nokia-conf/configure/service/vprn/isis/interface/level/priority
                    leaf priority {
                        type uint32 {
                            range "0..127";
                        }
                        default "64";
                        description "Router to become the designated router on a multi-access network";
                    }

                    ///nokia-conf/configure/service/vprn/isis/interface/level/sd-offset
                    leaf sd-offset {
                        type types-isis:metric;
                        description "Value of the signal degrade offset";
                    }

                    ///nokia-conf/configure/service/vprn/isis/interface/level/sf-offset
                    leaf sf-offset {
                        type types-isis:metric;
                        description "Value of the signal fail offset";
                    }

                    ///nokia-conf/configure/service/vprn/isis/interface/level/apply-groups
                    leaf-list apply-groups {
                        type leafref {
                            path "../../../../../../groups/group/name";
                        }
                        max-elements 8;
                        ordered-by user;
                        description "Apply a configuration group at this level";
                    }

                    ///nokia-conf/configure/service/vprn/isis/interface/level/apply-groups-exclude
                    leaf-list apply-groups-exclude {
                        type leafref {
                            path "../../../../../../groups/group/name";
                        }
                        max-elements 8;
                        ordered-by user;
                        description "Exclude a configuration group at this level";
                    }

                } // list level

            } // list interface

            ///nokia-conf/configure/service/vprn/isis/level
            list level {
                key "level-number";
                max-elements 2;
                description "Enter the level list instance";

                ///nokia-conf/configure/service/vprn/isis/level/level-number
                leaf level-number {
                    type enumeration {
                        enum 1                              { value 1; }
                        enum 2                              { value 2; }
                    }
                    description "ISIS protocol level number";
                }

                ///nokia-conf/configure/service/vprn/isis/level/authentication-keychain
                leaf authentication-keychain {
                    type leafref {
                        path "../../../../../system/security/keychains/keychain/keychain-name";
                    }
                    description "Keychain used to sign and authenticate";
                }

                ///nokia-conf/configure/service/vprn/isis/level/authentication-key
                leaf authentication-key {
                    type types-sros:encrypted-leaf {
                        length "1..366";
                    }
                    description "Authentication key to verify PDUs sent on the interface";
                }

                ///nokia-conf/configure/service/vprn/isis/level/authentication-type
                leaf authentication-type {
                    type types-isis:auth-type;
                    description "Authentication type to be used";
                }

                ///nokia-conf/configure/service/vprn/isis/level/csnp-authentication
                leaf csnp-authentication {
                    type boolean;
                    default "true";
                    description "Enable authentication of CSNP IS-IS protocol packets";
                }

                ///nokia-conf/configure/service/vprn/isis/level/psnp-authentication
                leaf psnp-authentication {
                    type boolean;
                    default "true";
                    description "Enable authentication on PSNP IS-IS protocol packets";
                }

                ///nokia-conf/configure/service/vprn/isis/level/advertise-router-capability
                leaf advertise-router-capability {
                    type boolean;
                    default "true";
                    description "Allow router advertisement capabilities";
                }

                ///nokia-conf/configure/service/vprn/isis/level/default-ipv4-multicast-metric
                leaf default-ipv4-multicast-metric {
                    type types-isis:metric;
                    default "10";
                    description "Default metric for IPv4 unicast";
                }

                ///nokia-conf/configure/service/vprn/isis/level/default-ipv6-unicast-metric
                leaf default-ipv6-unicast-metric {
                    type types-isis:metric;
                    default "10";
                    description "Default metric for IPv6 unicast";
                }

                ///nokia-conf/configure/service/vprn/isis/level/default-metric
                leaf default-metric {
                    type types-isis:metric;
                    default "10";
                    description "Default metric";
                }

                ///nokia-conf/configure/service/vprn/isis/level/external-preference
                leaf external-preference {
                    type uint32 {
                        range "1..255";
                    }
                    description "External route preference for IS-IS level";
                }

                ///nokia-conf/configure/service/vprn/isis/level/hello-authentication
                leaf hello-authentication {
                    type boolean;
                    default "true";
                    description "Authenticate Hello type IS-IS protocol packets";
                }

                ///nokia-conf/configure/service/vprn/isis/level/hello-padding
                leaf hello-padding {
                    type types-isis:hello-padding-type;
                    description "Padding on IS-IS Hello packets";
                }

                ///nokia-conf/configure/service/vprn/isis/level/loopfree-alternate-exclude
                leaf loopfree-alternate-exclude {
                    type boolean;
                    default "false";
                    description "Exclude interface participating in specific IS-IS level in SPF LFA computation";
                }

                ///nokia-conf/configure/service/vprn/isis/level/lsp-mtu-size
                leaf lsp-mtu-size {
                    type types-isis:lsp-buffer-ext-size;
                    units "bytes";
                    sros-ext:manual-restart-to-modify;
                    default "1492";
                    description "LSP MTU size";
                }

                ///nokia-conf/configure/service/vprn/isis/level/preference
                leaf preference {
                    type uint32 {
                        range "1..255";
                    }
                    description "External route preference at level";
                }

                ///nokia-conf/configure/service/vprn/isis/level/wide-metrics-only
                leaf wide-metrics-only {
                    type boolean;
                    default "false";
                    description "Use wide metrics advertisements in the LSPs";
                }

                ///nokia-conf/configure/service/vprn/isis/level/apply-groups
                leaf-list apply-groups {
                    type leafref {
                        path "../../../../../groups/group/name";
                    }
                    max-elements 8;
                    ordered-by user;
                    description "Apply a configuration group at this level";
                }

                ///nokia-conf/configure/service/vprn/isis/level/apply-groups-exclude
                leaf-list apply-groups-exclude {
                    type leafref {
                        path "../../../../../groups/group/name";
                    }
                    max-elements 8;
                    ordered-by user;
                    description "Exclude a configuration group at this level";
                }

            } // list level

            ///nokia-conf/configure/service/vprn/isis/link-group
            list link-group {
                key "link-group-name";
                description "Enter the link-group list instance";

                ///nokia-conf/configure/service/vprn/isis/link-group/link-group-name
                leaf link-group-name {
                    type types-sros:named-item;
                    description "Link group name for the IS-IS protocol";
                }

                ///nokia-conf/configure/service/vprn/isis/link-group/description
                leaf description {
                    type types-sros:very-long-description;
                    description "Text description";
                }

                ///nokia-conf/configure/service/vprn/isis/link-group/apply-groups
                leaf-list apply-groups {
                    type leafref {
                        path "../../../../../groups/group/name";
                    }
                    max-elements 8;
                    ordered-by user;
                    description "Apply a configuration group at this level";
                }

                ///nokia-conf/configure/service/vprn/isis/link-group/apply-groups-exclude
                leaf-list apply-groups-exclude {
                    type leafref {
                        path "../../../../../groups/group/name";
                    }
                    max-elements 8;
                    ordered-by user;
                    description "Exclude a configuration group at this level";
                }

                ///nokia-conf/configure/service/vprn/isis/link-group/level
                list level {
                    key "level-number";
                    max-elements 2;
                    description "Enter the level list instance";

                    ///nokia-conf/configure/service/vprn/isis/link-group/level/level-number
                    leaf level-number {
                        type enumeration {
                            enum 1                              { value 1; }
                            enum 2                              { value 2; }
                        }
                        description "ISIS protocol level number";
                    }

                    ///nokia-conf/configure/service/vprn/isis/link-group/level/ipv4-multicast-metric-offset
                    leaf ipv4-multicast-metric-offset {
                        type types-isis:metric;
                        description "Offset value for the IPv4 multicast address family";
                    }

                    ///nokia-conf/configure/service/vprn/isis/link-group/level/ipv4-unicast-metric-offset
                    leaf ipv4-unicast-metric-offset {
                        type types-isis:metric;
                        description "Offset value for the IPv4 unicast address family";
                    }

                    ///nokia-conf/configure/service/vprn/isis/link-group/level/ipv6-unicast-metric-offset
                    leaf ipv6-unicast-metric-offset {
                        type types-isis:metric;
                        description "Offset value for the IPv6 unicast address family";
                    }

                    ///nokia-conf/configure/service/vprn/isis/link-group/level/oper-members
                    leaf oper-members {
                        type uint32 {
                            range "1..8";
                        }
                        description "Minimum number of operational links";
                    }

                    ///nokia-conf/configure/service/vprn/isis/link-group/level/revert-members
                    leaf revert-members {
                        type uint32 {
                            range "1..8";
                        }
                        description "Minimum number of operational links to return link group to normal state and remove offsets";
                    }

                    ///nokia-conf/configure/service/vprn/isis/link-group/level/apply-groups
                    leaf-list apply-groups {
                        type leafref {
                            path "../../../../../../groups/group/name";
                        }
                        max-elements 8;
                        ordered-by user;
                        description "Apply a configuration group at this level";
                    }

                    ///nokia-conf/configure/service/vprn/isis/link-group/level/apply-groups-exclude
                    leaf-list apply-groups-exclude {
                        type leafref {
                            path "../../../../../../groups/group/name";
                        }
                        max-elements 8;
                        ordered-by user;
                        description "Exclude a configuration group at this level";
                    }

                    ///nokia-conf/configure/service/vprn/isis/link-group/level/member
                    list member {
                        key "interface-name";
                        max-elements 8;
                        description "Add a list entry for member";

                        ///nokia-conf/configure/service/vprn/isis/link-group/level/member/interface-name
                        leaf interface-name {
                            type leafref {
                                path "../../../../interface/interface-name";
                            }
                            description "Interface name for the associated link group";
                        }

                    } // list member

                } // list level

            } // list link-group

            ///nokia-conf/configure/service/vprn/isis/summary-address
            list summary-address {
                key "ip-prefix";
                description "Enter the summary-address list instance";

                ///nokia-conf/configure/service/vprn/isis/summary-address/ip-prefix
                leaf ip-prefix {
                    type types-sros:ip-prefix;
                    description "IP prefix for the summary address";
                }

                ///nokia-conf/configure/service/vprn/isis/summary-address/level-capability
                leaf level-capability {
                    type types-isis:level;
                    description "IS-IS level for the summary address";
                }

                ///nokia-conf/configure/service/vprn/isis/summary-address/route-tag
                leaf route-tag {
                    type uint32 {
                        range "1..max";
                    }
                    description "Route tag assigned to the summary address";
                }

                ///nokia-conf/configure/service/vprn/isis/summary-address/apply-groups
                leaf-list apply-groups {
                    type leafref {
                        path "../../../../../groups/group/name";
                    }
                    max-elements 8;
                    ordered-by user;
                    description "Apply a configuration group at this level";
                }

                ///nokia-conf/configure/service/vprn/isis/summary-address/apply-groups-exclude
                leaf-list apply-groups-exclude {
                    type leafref {
                        path "../../../../../groups/group/name";
                    }
                    max-elements 8;
                    ordered-by user;
                    description "Exclude a configuration group at this level";
                }

            } // list summary-address

        } // list isis

    } // grouping conf-svc-vprn-isis

}
