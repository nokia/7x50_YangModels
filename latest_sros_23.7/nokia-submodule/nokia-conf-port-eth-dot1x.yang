submodule nokia-conf-port-eth-dot1x {

    yang-version "1.1";

    belongs-to nokia-conf { prefix "conf"; }

    import ietf-yang-types                { prefix "yang"; }
    import nokia-sros-yang-extensions     { prefix "sros-ext"; }
    import nokia-types-port               { prefix "types-port"; }
    import nokia-types-sros               { prefix "types-sros"; }

    include nokia-conf-aaa;
    include nokia-conf-groups;
    include nokia-conf-macsec;
    include nokia-conf-system;
    include nokia-conf-system-security;

    sros-ext:sros-major-release "rel23";
    organization "Nokia";
    contact
        "Nokia SR OS Support
         Web: <http://www.nokia.com>";
    description
        "Nokia YANG Data model to configure ethernet ports 802.1x authentication capabilities on SR OS based routers.

         Copyright 2016 Nokia. All rights reserved. Reproduction of this document
         is authorized on the condition that the foregoing copyright notice is included.

         This nokia-conf-port-eth-dot1x YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-25";

    grouping conf-port-eth-dot1x {
        ///nokia-conf/configure/port/ethernet/dot1x
        container dot1x {
            description "Enable the dot1x context";

            ///nokia-conf/configure/port/ethernet/dot1x/admin-state
            leaf admin-state {
                type types-sros:admin-state;
                default "enable";
                description "Administrative state of dot1x packet extraction to CPM";
            }

            ///nokia-conf/configure/port/ethernet/dot1x/max-authentication-requests
            leaf max-authentication-requests {
                type uint32 {
                    range "1..10";
                }
                default "2";
                description "Maximum number of RADIUS retries";
            }

            ///nokia-conf/configure/port/ethernet/dot1x/port-control
            leaf port-control {
                type types-port:pae-controlled-port-control;
                default "force-authorized";
                description "802.1x authentication mode";
            }

            ///nokia-conf/configure/port/ethernet/dot1x/quiet-period
            leaf quiet-period {
                type uint32 {
                    range "1..3600";
                }
                units "seconds";
                default "60";
                description "Time between two sessions when no EAPOL frames are sent";
            }

            ///nokia-conf/configure/port/ethernet/dot1x/radius-policy
            leaf radius-policy {
                type leafref {
                    path "../../../../system/security/dot1x/radius-policy/policy-name";
                }
                description "RADIUS policy used for 802.1x authentication";
            }

            ///nokia-conf/configure/port/ethernet/dot1x/server-timeout
            leaf server-timeout {
                type uint32 {
                    range "1..300";
                }
                units "seconds";
                default "30";
                description "Wait time for a response from the RADIUS server";
            }

            ///nokia-conf/configure/port/ethernet/dot1x/supplicant-timeout
            leaf supplicant-timeout {
                type uint32 {
                    range "1..300";
                }
                units "seconds";
                default "30";
                description "Wait time for a response to EAPOL messages";
            }

            ///nokia-conf/configure/port/ethernet/dot1x/transmit-period
            leaf transmit-period {
                type uint32 {
                    range "1..3600";
                }
                units "seconds";
                default "30";
                description "Time after which a new EAPOL request message is sent";
            }

            ///nokia-conf/configure/port/ethernet/dot1x/tunneling
            leaf tunneling {
                type boolean;
                default "false";
                description "Allow tunneling of untagged 802.1x frames";
            }

            ///nokia-conf/configure/port/ethernet/dot1x/tunnel-dot1q
            leaf tunnel-dot1q {
                type boolean;
                default "true";
                description "Enable dot1x tunneling for 802.1q tagged packets";
            }

            ///nokia-conf/configure/port/ethernet/dot1x/tunnel-qinq
            leaf tunnel-qinq {
                type boolean;
                default "true";
                description "Enable dot1x tunneling for QinQ tagged packets";
            }

            ///nokia-conf/configure/port/ethernet/dot1x/apply-groups
            leaf-list apply-groups {
                type leafref {
                    path "../../../../groups/group/name";
                }
                max-elements 8;
                ordered-by user;
                description "Apply a configuration group at this level";
            }

            ///nokia-conf/configure/port/ethernet/dot1x/apply-groups-exclude
            leaf-list apply-groups-exclude {
                type leafref {
                    path "../../../../groups/group/name";
                }
                max-elements 8;
                ordered-by user;
                description "Exclude a configuration group at this level";
            }

            ///nokia-conf/configure/port/ethernet/dot1x/radius-server-policy-config
            choice radius-server-policy-config {
                ///nokia-conf/configure/port/ethernet/dot1x/radius-server-policy-config/common
                case common {

                    ///nokia-conf/configure/port/ethernet/dot1x/radius-server-policy-config/common/radius-server-policy
                    leaf radius-server-policy {
                        type leafref {
                            path "../../../../aaa/radius/server-policy/name";
                        }
                        description "RADIUS server policy name";
                    }

                }
                ///nokia-conf/configure/port/ethernet/dot1x/radius-server-policy-config/split
                case split {

                    ///nokia-conf/configure/port/ethernet/dot1x/radius-server-policy-config/split/radius-server-policy-auth
                    leaf radius-server-policy-auth {
                        type leafref {
                            path "../../../../aaa/radius/server-policy/name";
                        }
                        description "RADIUS server policy name for authentication";
                    }

                    ///nokia-conf/configure/port/ethernet/dot1x/radius-server-policy-config/split/radius-server-policy-acct
                    leaf radius-server-policy-acct {
                        type leafref {
                            path "../../../../aaa/radius/server-policy/name";
                        }
                        description "RADIUS server policy name for accounting";
                    }

                }
            }
            ///nokia-conf/configure/port/ethernet/dot1x/macsec
            container macsec {
                description "Enter the macsec context";

                ///nokia-conf/configure/port/ethernet/dot1x/macsec/rx-must-be-encrypted
                leaf rx-must-be-encrypted {
                    type boolean;
                    default "false";
                    description "Drop all port traffic that is not MACsec-secured";
                }

                ///nokia-conf/configure/port/ethernet/dot1x/macsec/exclude-mac-policy
                leaf exclude-mac-policy {
                    type leafref {
                        path "../../../../../macsec/mac-policy/mac-policy-id";
                    }
                    description "MAC policy excluded from MACsec encryption";
                }

                ///nokia-conf/configure/port/ethernet/dot1x/macsec/apply-groups
                leaf-list apply-groups {
                    type leafref {
                        path "../../../../../groups/group/name";
                    }
                    max-elements 8;
                    ordered-by user;
                    description "Apply a configuration group at this level";
                }

                ///nokia-conf/configure/port/ethernet/dot1x/macsec/apply-groups-exclude
                leaf-list apply-groups-exclude {
                    type leafref {
                        path "../../../../../groups/group/name";
                    }
                    max-elements 8;
                    ordered-by user;
                    description "Exclude a configuration group at this level";
                }

                ///nokia-conf/configure/port/ethernet/dot1x/macsec/exclude-protocol
                container exclude-protocol {
                    description "Enter the exclude-protocol context";

                    ///nokia-conf/configure/port/ethernet/dot1x/macsec/exclude-protocol/cdp
                    leaf cdp {
                        type boolean;
                        default "false";
                        description "Disable MACsec for all packets on the link for CDP";
                    }

                    ///nokia-conf/configure/port/ethernet/dot1x/macsec/exclude-protocol/eapol-start
                    leaf eapol-start {
                        type boolean;
                        default "false";
                        description "Disable MACsec for all packets on the link for EAPOL";
                    }

                    ///nokia-conf/configure/port/ethernet/dot1x/macsec/exclude-protocol/lacp
                    leaf lacp {
                        type boolean;
                        default "false";
                        description "Disable MACsec for all packets on the link for LACP";
                    }

                    ///nokia-conf/configure/port/ethernet/dot1x/macsec/exclude-protocol/lldp
                    leaf lldp {
                        type boolean;
                        default "false";
                        description "Disable MACsec for all packets on the link for LLDP";
                    }

                    ///nokia-conf/configure/port/ethernet/dot1x/macsec/exclude-protocol/efm-oam
                    leaf efm-oam {
                        type boolean;
                        default "false";
                        description "Disable MACsec for all packets on the link for EFM-OAM";
                    }

                    ///nokia-conf/configure/port/ethernet/dot1x/macsec/exclude-protocol/eth-cfm
                    leaf eth-cfm {
                        type boolean;
                        default "false";
                        description "Disable MACsec for all packets on the link for ETH-CFM";
                    }

                    ///nokia-conf/configure/port/ethernet/dot1x/macsec/exclude-protocol/ptp
                    leaf ptp {
                        type boolean;
                        default "false";
                        description "Disable MACsec for all packets on the link for PTP";
                    }

                    ///nokia-conf/configure/port/ethernet/dot1x/macsec/exclude-protocol/ubfd
                    leaf ubfd {
                        type boolean;
                        default "false";
                        description "Disable MACsec for all packets on the link for uBFD";
                    }

                } // container exclude-protocol

                ///nokia-conf/configure/port/ethernet/dot1x/macsec/sub-port
                list sub-port {
                    key "sub-port-id";
                    description "Enter the sub-port list instance";

                    ///nokia-conf/configure/port/ethernet/dot1x/macsec/sub-port/sub-port-id
                    leaf sub-port-id {
                        type uint32 {
                            range "1..1023";
                        }
                        description "Sub-port ID";
                    }

                    ///nokia-conf/configure/port/ethernet/dot1x/macsec/sub-port/admin-state
                    leaf admin-state {
                        type types-sros:admin-state;
                        default "disable";
                        description "Administrative state of MACsec on the port";
                    }

                    ///nokia-conf/configure/port/ethernet/dot1x/macsec/sub-port/ca-name
                    leaf ca-name {
                        type leafref {
                            path "../../../../../../macsec/connectivity-association/ca-name";
                        }
                        description "Connectivity association linked to the MACsec sub-port";
                    }

                    ///nokia-conf/configure/port/ethernet/dot1x/macsec/sub-port/eapol-destination-address
                    leaf eapol-destination-address {
                        type yang:mac-address;
                        description "EAPOL destination MAC address";
                    }

                    ///nokia-conf/configure/port/ethernet/dot1x/macsec/sub-port/max-peers
                    leaf max-peers {
                        type uint32 {
                            range "1..32";
                        }
                        sros-ext:auto-restart-to-modify;
                        description "Maximum number of peers supported on the port";
                    }

                    ///nokia-conf/configure/port/ethernet/dot1x/macsec/sub-port/apply-groups
                    leaf-list apply-groups {
                        type leafref {
                            path "../../../../../../groups/group/name";
                        }
                        max-elements 8;
                        ordered-by user;
                        description "Apply a configuration group at this level";
                    }

                    ///nokia-conf/configure/port/ethernet/dot1x/macsec/sub-port/apply-groups-exclude
                    leaf-list apply-groups-exclude {
                        type leafref {
                            path "../../../../../../groups/group/name";
                        }
                        max-elements 8;
                        ordered-by user;
                        description "Exclude a configuration group at this level";
                    }

                    ///nokia-conf/configure/port/ethernet/dot1x/macsec/sub-port/encap-match
                    container encap-match {
                        description "Enter the encap-match context";

                        ///nokia-conf/configure/port/ethernet/dot1x/macsec/sub-port/encap-match/encap
                        choice encap {
                            default "all-match";
                            ///nokia-conf/configure/port/ethernet/dot1x/macsec/sub-port/encap-match/encap/all-match
                            case all-match {

                                ///nokia-conf/configure/port/ethernet/dot1x/macsec/sub-port/encap-match/encap/all-match/all-match
                                leaf all-match {
                                    type boolean;
                                    default "true";
                                    description "Match and encrypt all traffic patterns";
                                }

                            }
                            ///nokia-conf/configure/port/ethernet/dot1x/macsec/sub-port/encap-match/encap/untagged
                            case untagged {

                                ///nokia-conf/configure/port/ethernet/dot1x/macsec/sub-port/encap-match/encap/untagged/untagged
                                leaf untagged {
                                    type boolean;
                                    description "Match and encrypt untagged traffic only";
                                }

                            }
                            ///nokia-conf/configure/port/ethernet/dot1x/macsec/sub-port/encap-match/encap/single-tag
                            case single-tag {

                                ///nokia-conf/configure/port/ethernet/dot1x/macsec/sub-port/encap-match/encap/single-tag/single-tag
                                leaf single-tag {
                                    type types-sros:single-vlan-encap;
                                    description "Dot1q single tag traffic pattern to match";
                                }

                            }
                            ///nokia-conf/configure/port/ethernet/dot1x/macsec/sub-port/encap-match/encap/double-tag
                            case double-tag {

                                ///nokia-conf/configure/port/ethernet/dot1x/macsec/sub-port/encap-match/encap/double-tag/double-tag
                                leaf double-tag {
                                    type types-sros:double-vlan-encap;
                                    description "QinQ double tag traffic pattern to match";
                                }

                            }
                        }
                    } // container encap-match

                } // list sub-port

            } // container macsec

            ///nokia-conf/configure/port/ethernet/dot1x/re-authentication
            container re-authentication {
                presence "Enable the re-authentication context";
                description "Enable the re-authentication context";

                ///nokia-conf/configure/port/ethernet/dot1x/re-authentication/period
                leaf period {
                    type uint32 {
                        range "1..9000";
                    }
                    units "seconds";
                    default "3600";
                    description "Delay before re-authentication is performed";
                }

            } // container re-authentication

            ///nokia-conf/configure/port/ethernet/dot1x/per-host-authentication
            container per-host-authentication {
                description "Enter the per-host-authentication context";

                ///nokia-conf/configure/port/ethernet/dot1x/per-host-authentication/admin-state
                leaf admin-state {
                    type types-sros:admin-state;
                    default "disable";
                    description "Administrative state of per-host authentication";
                }

                ///nokia-conf/configure/port/ethernet/dot1x/per-host-authentication/authenticator-init
                leaf authenticator-init {
                    type boolean;
                    default "true";
                    description "Initiate per-host authentication";
                }

                ///nokia-conf/configure/port/ethernet/dot1x/per-host-authentication/allowed-source-macs
                container allowed-source-macs {
                    description "Enter the allowed-source-macs context";

                    ///nokia-conf/configure/port/ethernet/dot1x/per-host-authentication/allowed-source-macs/mac-address
                    list mac-address {
                        key "mac";
                        description "Add a list entry for mac-address";

                        ///nokia-conf/configure/port/ethernet/dot1x/per-host-authentication/allowed-source-macs/mac-address/mac
                        leaf mac {
                            type yang:mac-address;
                            description "Source MAC address of a host selected for authentication";
                        }

                    } // list mac-address

                } // container allowed-source-macs

            } // container per-host-authentication

        } // container dot1x

    } // grouping conf-port-eth-dot1x

}
