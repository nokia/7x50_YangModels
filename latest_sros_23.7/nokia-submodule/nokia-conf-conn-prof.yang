submodule nokia-conf-conn-prof {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure connection profile on SR OS based routers.

         Copyright 2016 Nokia. All rights reserved. Reproduction of this document
         is authorized on the condition that the foregoing copyright notice is included.

         This nokia-conf-conn-prof YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-05";

    grouping conf-conn-prof-connection-profile {
        ///nokia-conf/configure/connection-profile
        container connection-profile {
            description "Enable the connection-profile context";

            ///nokia-conf/configure/connection-profile/apply-groups
            leaf-list apply-groups {
                type leafref {
                    path "../../groups/group/name";
                }
                max-elements 8;
                ordered-by user;
                description "Apply a configuration group at this level";
            }

            ///nokia-conf/configure/connection-profile/apply-groups-exclude
            leaf-list apply-groups-exclude {
                type leafref {
                    path "../../groups/group/name";
                }
                max-elements 8;
                ordered-by user;
                description "Exclude a configuration group at this level";
            }

            ///nokia-conf/configure/connection-profile/vlan
            list vlan {
                key "connection-profile-id";
                description "Enter the vlan list instance";

                ///nokia-conf/configure/connection-profile/vlan/connection-profile-id
                leaf connection-profile-id {
                    type uint32 {
                        range "1..8000";
                    }
                    description "Identifier of this connection profile";
                }

                ///nokia-conf/configure/connection-profile/vlan/description
                leaf description {
                    type types-sros:description;
                    description "Text description";
                }

                ///nokia-conf/configure/connection-profile/vlan/apply-groups
                leaf-list apply-groups {
                    type leafref {
                        path "../../../groups/group/name";
                    }
                    max-elements 8;
                    ordered-by user;
                    description "Apply a configuration group at this level";
                }

                ///nokia-conf/configure/connection-profile/vlan/apply-groups-exclude
                leaf-list apply-groups-exclude {
                    type leafref {
                        path "../../../groups/group/name";
                    }
                    max-elements 8;
                    ordered-by user;
                    description "Exclude a configuration group at this level";
                }

                ///nokia-conf/configure/connection-profile/vlan/qtag-range
                list qtag-range {
                    key "start";
                    description "Enter the qtag-range list instance";

                    ///nokia-conf/configure/connection-profile/vlan/qtag-range/start
                    leaf start {
                        type int32 {
                            range "1..4094";
                        }
                        description "Lower bound of VLAN range for connection profile";
                    }

                    ///nokia-conf/configure/connection-profile/vlan/qtag-range/end
                    leaf end {
                        type int32 {
                            range "1..4094";
                        }
                        sros-ext:immutable;
                        description "Upper bound of VLAN range for connection profile";
                    }

                    ///nokia-conf/configure/connection-profile/vlan/qtag-range/apply-groups
                    leaf-list apply-groups {
                        type leafref {
                            path "../../../../groups/group/name";
                        }
                        max-elements 8;
                        ordered-by user;
                        description "Apply a configuration group at this level";
                    }

                    ///nokia-conf/configure/connection-profile/vlan/qtag-range/apply-groups-exclude
                    leaf-list apply-groups-exclude {
                        type leafref {
                            path "../../../../groups/group/name";
                        }
                        max-elements 8;
                        ordered-by user;
                        description "Exclude a configuration group at this level";
                    }

                } // list qtag-range

            } // list vlan

        } // container connection-profile

    } // grouping conf-conn-prof-connection-profile

}
