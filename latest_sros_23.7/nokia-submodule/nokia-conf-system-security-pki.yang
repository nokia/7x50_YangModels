submodule nokia-conf-system-security-pki {

    yang-version "1.1";

    belongs-to nokia-conf { prefix "conf"; }

    import nokia-sros-yang-extensions     { prefix "sros-ext"; }
    import nokia-types-security           { prefix "types-security"; }
    import nokia-types-services           { prefix "types-services"; }
    import nokia-types-sros               { prefix "types-sros"; }
    import nokia-types-system             { prefix "types-system"; }

    include nokia-conf-groups;
    include nokia-conf-system;

    sros-ext:sros-major-release "rel23";
    organization "Nokia";
    contact
        "Nokia SR OS Support
         Web: <http://www.nokia.com>";
    description
        "Nokia YANG Data model to configure system security pki parameters. on SR OS based routers.

         Copyright 2016 Nokia. All rights reserved. Reproduction of this document
         is authorized on the condition that the foregoing copyright notice is included.

         This nokia-conf-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-07";

    grouping conf-system-security-pki {
        ///nokia-conf/configure/system/security/pki
        container pki {
            description "Enter the pki context";

            ///nokia-conf/configure/system/security/pki/certificate-display-format
            leaf certificate-display-format {
                type enumeration {
                    enum ascii                          { value 1; }
                    enum utf8                           { value 2; }
                }
                default "ascii";
                description "Display format for Certificates and CRLs";
            }

            ///nokia-conf/configure/system/security/pki/imported-format
            leaf imported-format {
                type enumeration {
                    enum any                            { value 1; }
                    enum secure                         { value 2; }
                }
                default "any";
                description "The supported encrypted file formats";
            }

            ///nokia-conf/configure/system/security/pki/maximum-cert-chain-depth
            leaf maximum-cert-chain-depth {
                type uint32 {
                    range "1..7";
                }
                default "7";
                description "Maximum depth of certificate chain verification";
            }

            ///nokia-conf/configure/system/security/pki/apply-groups
            leaf-list apply-groups {
                type leafref {
                    path "../../../../groups/group/name";
                }
                max-elements 8;
                ordered-by user;
                description "Apply a configuration group at this level";
            }

            ///nokia-conf/configure/system/security/pki/apply-groups-exclude
            leaf-list apply-groups-exclude {
                type leafref {
                    path "../../../../groups/group/name";
                }
                max-elements 8;
                ordered-by user;
                description "Exclude a configuration group at this level";
            }

            ///nokia-conf/configure/system/security/pki/certificate-expiration-warning
            container certificate-expiration-warning {
                description "Enter the certificate-expiration-warning context";

                ///nokia-conf/configure/system/security/pki/certificate-expiration-warning/hours
                leaf hours {
                    type int32 {
                        range "0..8760";
                    }
                    units "hours";
                    description "Time before system generates certificate warning trap";
                }

                ///nokia-conf/configure/system/security/pki/certificate-expiration-warning/repeat-hours
                leaf repeat-hours {
                    type int32 {
                        range "0..8760";
                    }
                    units "hours";
                    default "0";
                    description "Time system repeats certificate expiration warning trap";
                }

            } // container certificate-expiration-warning

            ///nokia-conf/configure/system/security/pki/crl-expiration-warning
            container crl-expiration-warning {
                description "Enter the crl-expiration-warning context";

                ///nokia-conf/configure/system/security/pki/crl-expiration-warning/hours
                leaf hours {
                    type int32 {
                        range "0..8760";
                    }
                    units "hours";
                    description "Time before system generates CRL expiration warning trap";
                }

                ///nokia-conf/configure/system/security/pki/crl-expiration-warning/repeat-hours
                leaf repeat-hours {
                    type int32 {
                        range "0..8760";
                    }
                    units "hours";
                    default "0";
                    description "Time system repeats CRL expiration warning trap";
                }

            } // container crl-expiration-warning

            ///nokia-conf/configure/system/security/pki/ca-profile
            list ca-profile {
                key "ca-profile-name";
                max-elements 128;
                description "Enter the ca-profile list instance";

                ///nokia-conf/configure/system/security/pki/ca-profile/ca-profile-name
                leaf ca-profile-name {
                    type types-sros:named-item;
                    description "CA profile name";
                }

                ///nokia-conf/configure/system/security/pki/ca-profile/admin-state
                leaf admin-state {
                    type types-sros:admin-state;
                    default "disable";
                    description "Administrative state of the CA profile";
                }

                ///nokia-conf/configure/system/security/pki/ca-profile/description
                leaf description {
                    type types-sros:description;
                    description "Text description";
                }

                ///nokia-conf/configure/system/security/pki/ca-profile/cert-file
                leaf cert-file {
                    type types-security:pki-file-name;
                    sros-ext:auto-restart-to-modify;
                    description "Certificate file name";
                }

                ///nokia-conf/configure/system/security/pki/ca-profile/crl-file
                leaf crl-file {
                    type types-security:pki-file-name;
                    sros-ext:auto-restart-to-modify;
                    description "Certificate Revocation List (CRL) file name";
                }

                ///nokia-conf/configure/system/security/pki/ca-profile/revocation-check
                leaf revocation-check {
                    type enumeration {
                        enum crl                            { value 1; }
                        enum crl-optional                   { value 2; }
                    }
                    sros-ext:auto-restart-to-modify;
                    default "crl";
                    description "Revocation method to check status of CA certificates";
                }

                ///nokia-conf/configure/system/security/pki/ca-profile/apply-groups
                leaf-list apply-groups {
                    type leafref {
                        path "../../../../../groups/group/name";
                    }
                    max-elements 8;
                    ordered-by user;
                    sros-ext:auto-restart-to-modify;
                    description "Apply a configuration group at this level";
                }

                ///nokia-conf/configure/system/security/pki/ca-profile/apply-groups-exclude
                leaf-list apply-groups-exclude {
                    type leafref {
                        path "../../../../../groups/group/name";
                    }
                    max-elements 8;
                    ordered-by user;
                    sros-ext:auto-restart-to-modify;
                    description "Exclude a configuration group at this level";
                }

                ///nokia-conf/configure/system/security/pki/ca-profile/ocsp
                container ocsp {
                    sros-ext:auto-restart-to-modify;
                    description "Enter the ocsp context";

                    ///nokia-conf/configure/system/security/pki/ca-profile/ocsp/responder-url
                    leaf responder-url {
                        type union {
                            type types-sros:http-optional-url-loose;
                        }
                        sros-ext:auto-restart-to-modify;
                        description "HTTP URL of the OCSP responder for the CA";
                    }

                    ///nokia-conf/configure/system/security/pki/ca-profile/ocsp/service-name
                    leaf service-name {
                        type types-services:service-name;
                        sros-ext:auto-restart-to-modify;
                        description "Administrative service name";
                    }

                    ///nokia-conf/configure/system/security/pki/ca-profile/ocsp/transmission-profile
                    leaf transmission-profile {
                        type leafref {
                            path "../../../../../transmission-profile/name";
                        }
                        sros-ext:auto-restart-to-modify;
                        description "Transmission profile for the OCSP";
                    }

                } // container ocsp

                ///nokia-conf/configure/system/security/pki/ca-profile/cmpv2
                container cmpv2 {
                    sros-ext:auto-restart-to-modify;
                    description "Enter the cmpv2 context";

                    ///nokia-conf/configure/system/security/pki/ca-profile/cmpv2/always-set-sender-for-ir
                    leaf always-set-sender-for-ir {
                        type boolean;
                        sros-ext:auto-restart-to-modify;
                        default "false";
                        description "Set subject name in CMPv2 header for all IR messages";
                    }

                    ///nokia-conf/configure/system/security/pki/ca-profile/cmpv2/same-recipient-nonce-for-poll-request
                    leaf same-recipient-nonce-for-poll-request {
                        type boolean;
                        sros-ext:auto-restart-to-modify;
                        default "false";
                        description "Use same recipNonce as last CMPv2 response";
                    }

                    ///nokia-conf/configure/system/security/pki/ca-profile/cmpv2/signing-cert-subject
                    leaf signing-cert-subject {
                        type string {
                            length "1..256";
                        }
                        sros-ext:auto-restart-to-modify;
                        description "Subject DN attributes to identify signing certificate";
                    }

                    ///nokia-conf/configure/system/security/pki/ca-profile/cmpv2/response-signing
                    choice response-signing {
                        default "response-signing-cert";
                        ///nokia-conf/configure/system/security/pki/ca-profile/cmpv2/response-signing/response-signing-use-extracert
                        case response-signing-use-extracert {

                            ///nokia-conf/configure/system/security/pki/ca-profile/cmpv2/response-signing/response-signing-use-extracert/response-signing-use-extracert
                            leaf response-signing-use-extracert {
                                type empty;
                                sros-ext:auto-restart-to-modify;
                                description "Use extraCerts certificate to verify response signature";
                            }

                        }
                        ///nokia-conf/configure/system/security/pki/ca-profile/cmpv2/response-signing/response-signing-cert
                        case response-signing-cert {

                            ///nokia-conf/configure/system/security/pki/ca-profile/cmpv2/response-signing/response-signing-cert/response-signing-cert
                            leaf response-signing-cert {
                                type types-security:pki-file-name;
                                sros-ext:auto-restart-to-modify;
                                description "File name of the certificate to verify CMPv2 responses";
                            }

                        }
                    }
                    ///nokia-conf/configure/system/security/pki/ca-profile/cmpv2/recipient
                    choice recipient {
                        default "use-ca-subject";
                        ///nokia-conf/configure/system/security/pki/ca-profile/cmpv2/recipient/use-ca-subject
                        case use-ca-subject {

                            ///nokia-conf/configure/system/security/pki/ca-profile/cmpv2/recipient/use-ca-subject/use-ca-subject
                            leaf use-ca-subject {
                                type empty;
                                sros-ext:auto-restart-to-modify;
                                description "Use subject DN in CA certificate as CMPv2 request recipient";
                            }

                        }
                        ///nokia-conf/configure/system/security/pki/ca-profile/cmpv2/recipient/recipient-subject
                        case recipient-subject {

                            ///nokia-conf/configure/system/security/pki/ca-profile/cmpv2/recipient/recipient-subject/recipient-subject
                            leaf recipient-subject {
                                type string {
                                    length "1..256";
                                }
                                sros-ext:auto-restart-to-modify;
                                description "DN attributes for recipient subject of CMPv2 requests";
                            }

                        }
                    }
                    ///nokia-conf/configure/system/security/pki/ca-profile/cmpv2/accept-unprotected-message
                    container accept-unprotected-message {
                        sros-ext:auto-restart-to-modify;
                        description "Enter the accept-unprotected-message context";

                        ///nokia-conf/configure/system/security/pki/ca-profile/cmpv2/accept-unprotected-message/error-message
                        leaf error-message {
                            type boolean;
                            sros-ext:auto-restart-to-modify;
                            default "false";
                            description "Accept unprotected error messages";
                        }

                        ///nokia-conf/configure/system/security/pki/ca-profile/cmpv2/accept-unprotected-message/pkiconf-message
                        leaf pkiconf-message {
                            type boolean;
                            sros-ext:auto-restart-to-modify;
                            default "false";
                            description "Accept unprotected PKI confirmation messages";
                        }

                    } // container accept-unprotected-message

                    ///nokia-conf/configure/system/security/pki/ca-profile/cmpv2/http
                    container http {
                        sros-ext:auto-restart-to-modify;
                        description "Enter the http context";

                        ///nokia-conf/configure/system/security/pki/ca-profile/cmpv2/http/response-timeout
                        leaf response-timeout {
                            type uint32 {
                                range "1..3600";
                            }
                            units "seconds";
                            sros-ext:auto-restart-to-modify;
                            default "30";
                            description "HTTP response timeout";
                        }

                        ///nokia-conf/configure/system/security/pki/ca-profile/cmpv2/http/version
                        leaf version {
                            type types-system:http-version-type;
                            sros-ext:auto-restart-to-modify;
                            description "HTTP version for CMPv2 messages";
                        }

                    } // container http

                    ///nokia-conf/configure/system/security/pki/ca-profile/cmpv2/url
                    container url {
                        sros-ext:auto-restart-to-modify;
                        description "Enter the url context";

                        ///nokia-conf/configure/system/security/pki/ca-profile/cmpv2/url/url-string
                        leaf url-string {
                            type union {
                                type types-sros:http-optional-url-loose;
                            }
                            sros-ext:auto-restart-to-modify;
                            description "URL for CMPv2";
                        }

                        ///nokia-conf/configure/system/security/pki/ca-profile/cmpv2/url/transport
                        choice transport {
                            ///nokia-conf/configure/system/security/pki/ca-profile/cmpv2/url/transport/service
                            case service {

                                ///nokia-conf/configure/system/security/pki/ca-profile/cmpv2/url/transport/service/service-name
                                leaf service-name {
                                    type types-services:service-name;
                                    sros-ext:auto-restart-to-modify;
                                    description "Administrative service name";
                                }

                            }
                            ///nokia-conf/configure/system/security/pki/ca-profile/cmpv2/url/transport/transmission
                            case transmission {

                                ///nokia-conf/configure/system/security/pki/ca-profile/cmpv2/url/transport/transmission/transmission-profile
                                leaf transmission-profile {
                                    type leafref {
                                        path "../../../../../../transmission-profile/name";
                                    }
                                    sros-ext:auto-restart-to-modify;
                                    description "Transmission profile for CMPv2";
                                }

                            }
                        }
                    } // container url

                    ///nokia-conf/configure/system/security/pki/ca-profile/cmpv2/key-list
                    container key-list {
                        sros-ext:auto-restart-to-modify;
                        description "Enter the key-list context";

                        ///nokia-conf/configure/system/security/pki/ca-profile/cmpv2/key-list/key
                        list key {
                            key "reference-number";
                            max-elements 128;
                            description "Enter the key list instance";

                            ///nokia-conf/configure/system/security/pki/ca-profile/cmpv2/key-list/key/reference-number
                            leaf reference-number {
                                type types-sros:display-string {
                                    length "1..64";
                                    pattern ".*\\S.*" {
                                        error-message "Reference number must not be all spaces";
                                    }
                                }
                                description "Unique identifier for the CA initial authentication key";
                            }

                            ///nokia-conf/configure/system/security/pki/ca-profile/cmpv2/key-list/key/password
                            leaf password {
                                type types-sros:encrypted-leaf {
                                    length "1..115";
                                }
                                description "Shared secret for this CA initial authentication key";
                            }

                            ///nokia-conf/configure/system/security/pki/ca-profile/cmpv2/key-list/key/apply-groups
                            leaf-list apply-groups {
                                type leafref {
                                    path "../../../../../../../../groups/group/name";
                                }
                                max-elements 8;
                                ordered-by user;
                                description "Apply a configuration group at this level";
                            }

                            ///nokia-conf/configure/system/security/pki/ca-profile/cmpv2/key-list/key/apply-groups-exclude
                            leaf-list apply-groups-exclude {
                                type leafref {
                                    path "../../../../../../../../groups/group/name";
                                }
                                max-elements 8;
                                ordered-by user;
                                description "Exclude a configuration group at this level";
                            }

                        } // list key

                    } // container key-list

                } // container cmpv2

                ///nokia-conf/configure/system/security/pki/ca-profile/auto-crl-update
                container auto-crl-update {
                    presence "Enable the auto-crl-update context";
                    description "Enable the auto-crl-update context";

                    ///nokia-conf/configure/system/security/pki/ca-profile/auto-crl-update/admin-state
                    leaf admin-state {
                        type types-sros:admin-state;
                        default "disable";
                        description "Administrative state of the automatic CRL update";
                    }

                    ///nokia-conf/configure/system/security/pki/ca-profile/auto-crl-update/periodic-update-interval
                    leaf periodic-update-interval {
                        type types-sros:time-duration {
                            range "3600..31622400";
                        }
                        units "seconds";
                        sros-ext:auto-restart-to-modify;
                        default "86400";
                        description "Interval between two consecutive CRL updates";
                    }

                    ///nokia-conf/configure/system/security/pki/ca-profile/auto-crl-update/pre-update-time
                    leaf pre-update-time {
                        type types-sros:time-duration {
                            range "0..31622400";
                        }
                        units "seconds";
                        sros-ext:auto-restart-to-modify;
                        default "3600";
                        description "Time prior to the next update time of the current CRL";
                    }

                    ///nokia-conf/configure/system/security/pki/ca-profile/auto-crl-update/retry-interval
                    leaf retry-interval {
                        type types-sros:time-duration {
                            range "0..31622400";
                        }
                        units "seconds";
                        sros-ext:auto-restart-to-modify;
                        default "3600";
                        description "Interval before retrying to update CRL";
                    }

                    ///nokia-conf/configure/system/security/pki/ca-profile/auto-crl-update/schedule-type
                    leaf schedule-type {
                        type enumeration {
                            enum next-update-based              { value 1; }
                            enum periodic                       { value 2; }
                        }
                        sros-ext:auto-restart-to-modify;
                        default "next-update-based";
                        description "Time scheduler type for an automated CRL update";
                    }

                    ///nokia-conf/configure/system/security/pki/ca-profile/auto-crl-update/apply-groups
                    leaf-list apply-groups {
                        type leafref {
                            path "../../../../../../groups/group/name";
                        }
                        max-elements 8;
                        ordered-by user;
                        sros-ext:auto-restart-to-modify;
                        description "Apply a configuration group at this level";
                    }

                    ///nokia-conf/configure/system/security/pki/ca-profile/auto-crl-update/apply-groups-exclude
                    leaf-list apply-groups-exclude {
                        type leafref {
                            path "../../../../../../groups/group/name";
                        }
                        max-elements 8;
                        ordered-by user;
                        sros-ext:auto-restart-to-modify;
                        description "Exclude a configuration group at this level";
                    }

                    ///nokia-conf/configure/system/security/pki/ca-profile/auto-crl-update/crl-urls
                    container crl-urls {
                        sros-ext:auto-restart-to-modify;
                        description "Enter the crl-urls context";

                        ///nokia-conf/configure/system/security/pki/ca-profile/auto-crl-update/crl-urls/url-entry
                        list url-entry {
                            key "entry-id";
                            description "Enter the url-entry list instance";

                            ///nokia-conf/configure/system/security/pki/ca-profile/auto-crl-update/crl-urls/url-entry/entry-id
                            leaf entry-id {
                                type uint32 {
                                    range "1..8";
                                }
                                description "URL on this system";
                            }

                            ///nokia-conf/configure/system/security/pki/ca-profile/auto-crl-update/crl-urls/url-entry/transmission-profile
                            leaf transmission-profile {
                                type leafref {
                                    path "../../../../../../../transmission-profile/name";
                                }
                                description "File transmission profile to update CRL";
                            }

                            ///nokia-conf/configure/system/security/pki/ca-profile/auto-crl-update/crl-urls/url-entry/url
                            leaf url {
                                type union {
                                    type types-sros:http-url-path-loose;
                                }
                                description "Location of updated CRL";
                            }

                            ///nokia-conf/configure/system/security/pki/ca-profile/auto-crl-update/crl-urls/url-entry/apply-groups
                            leaf-list apply-groups {
                                type leafref {
                                    path "../../../../../../../../groups/group/name";
                                }
                                max-elements 8;
                                ordered-by user;
                                description "Apply a configuration group at this level";
                            }

                            ///nokia-conf/configure/system/security/pki/ca-profile/auto-crl-update/crl-urls/url-entry/apply-groups-exclude
                            leaf-list apply-groups-exclude {
                                type leafref {
                                    path "../../../../../../../../groups/group/name";
                                }
                                max-elements 8;
                                ordered-by user;
                                description "Exclude a configuration group at this level";
                            }

                        } // list url-entry

                    } // container crl-urls

                } // container auto-crl-update

            } // list ca-profile

            ///nokia-conf/configure/system/security/pki/common-name-list
            list common-name-list {
                key "cn-list-name";
                max-elements 64;
                description "Enter the common-name-list list instance";

                ///nokia-conf/configure/system/security/pki/common-name-list/cn-list-name
                leaf cn-list-name {
                    type types-sros:named-item;
                    description "CN list name";
                }

                ///nokia-conf/configure/system/security/pki/common-name-list/apply-groups
                leaf-list apply-groups {
                    type leafref {
                        path "../../../../../groups/group/name";
                    }
                    max-elements 8;
                    ordered-by user;
                    description "Apply a configuration group at this level";
                }

                ///nokia-conf/configure/system/security/pki/common-name-list/apply-groups-exclude
                leaf-list apply-groups-exclude {
                    type leafref {
                        path "../../../../../groups/group/name";
                    }
                    max-elements 8;
                    ordered-by user;
                    description "Exclude a configuration group at this level";
                }

                ///nokia-conf/configure/system/security/pki/common-name-list/common-name
                list common-name {
                    key "cn-index";
                    description "Enter the common-name list instance";

                    ///nokia-conf/configure/system/security/pki/common-name-list/common-name/cn-index
                    leaf cn-index {
                        type uint32 {
                            range "1..128";
                        }
                        description "Common name index";
                    }

                    ///nokia-conf/configure/system/security/pki/common-name-list/common-name/cn-type
                    leaf cn-type {
                        type enumeration {
                            enum ip-address                     { value 1; }
                            enum domain-name                    { value 2; }
                        }
                        mandatory true;
                        description "Common name type";
                    }

                    ///nokia-conf/configure/system/security/pki/common-name-list/common-name/cn-value
                    leaf cn-value {
                        type types-sros:regular-expression-not-all-spaces;
                        mandatory true;
                        description "Common name value";
                    }

                    ///nokia-conf/configure/system/security/pki/common-name-list/common-name/apply-groups
                    leaf-list apply-groups {
                        type leafref {
                            path "../../../../../../groups/group/name";
                        }
                        max-elements 8;
                        ordered-by user;
                        description "Apply a configuration group at this level";
                    }

                    ///nokia-conf/configure/system/security/pki/common-name-list/common-name/apply-groups-exclude
                    leaf-list apply-groups-exclude {
                        type leafref {
                            path "../../../../../../groups/group/name";
                        }
                        max-elements 8;
                        ordered-by user;
                        description "Exclude a configuration group at this level";
                    }

                } // list common-name

            } // list common-name-list



            ///nokia-conf/configure/system/security/pki/est-profile
            list est-profile {
                key "name";
                max-elements 128;
                description "Enter the est-profile list instance";

                ///nokia-conf/configure/system/security/pki/est-profile/name
                leaf name {
                    type types-sros:named-item;
                    description "Enrollment over Secured Transport profile name";
                }

                ///nokia-conf/configure/system/security/pki/est-profile/transmission-profile
                leaf transmission-profile {
                    type types-sros:named-item;
                    description "Transmission profile name for EST";
                }

                ///nokia-conf/configure/system/security/pki/est-profile/client-tls-profile
                leaf client-tls-profile {
                    type types-sros:named-item;
                    description "TLS client profile assigned to applications";
                }

                ///nokia-conf/configure/system/security/pki/est-profile/check-id-kp-cmcra-only
                leaf check-id-kp-cmcra-only {
                    type boolean;
                    default "false";
                    description "Check id-kp-cmcra in the EST certificate";
                }

                ///nokia-conf/configure/system/security/pki/est-profile/apply-groups
                leaf-list apply-groups {
                    type leafref {
                        path "../../../../../groups/group/name";
                    }
                    max-elements 8;
                    ordered-by user;
                    description "Apply a configuration group at this level";
                }

                ///nokia-conf/configure/system/security/pki/est-profile/apply-groups-exclude
                leaf-list apply-groups-exclude {
                    type leafref {
                        path "../../../../../groups/group/name";
                    }
                    max-elements 8;
                    ordered-by user;
                    description "Exclude a configuration group at this level";
                }

                ///nokia-conf/configure/system/security/pki/est-profile/server
                container server {
                    description "Enter the server context";

                    ///nokia-conf/configure/system/security/pki/est-profile/server/port
                    leaf port {
                        type types-sros:tcp-udp-port-non-zero;
                        default "443";
                        description "Port number of the EST server";
                    }

                    ///nokia-conf/configure/system/security/pki/est-profile/server/address
                    choice address {
                        ///nokia-conf/configure/system/security/pki/est-profile/server/address/ipv4
                        case ipv4 {

                            ///nokia-conf/configure/system/security/pki/est-profile/server/address/ipv4/ipv4
                            leaf ipv4 {
                                type types-sros:ipv4-unicast-address;
                                description "IPv4 address of the EST server";
                            }

                        }
                        ///nokia-conf/configure/system/security/pki/est-profile/server/address/ipv6
                        case ipv6 {

                            ///nokia-conf/configure/system/security/pki/est-profile/server/address/ipv6/ipv6
                            leaf ipv6 {
                                type types-sros:ip-address;
                                description "IPv6 address of the EST server";
                            }

                        }
                        ///nokia-conf/configure/system/security/pki/est-profile/server/address/fqdn
                        case fqdn {

                            ///nokia-conf/configure/system/security/pki/est-profile/server/address/fqdn/fqdn
                            leaf fqdn {
                                type types-sros:fully-qualified-domain-name;
                                description "Fully Qualified Domain Name (FQDN) of the EST server";
                            }

                        }
                    }
                } // container server

                ///nokia-conf/configure/system/security/pki/est-profile/http-authentication
                container http-authentication {
                    description "Enter the http-authentication context";

                    ///nokia-conf/configure/system/security/pki/est-profile/http-authentication/username
                    leaf username {
                        type string {
                            length "1..32";
                        }
                        description "Username for the EST authentication";
                    }

                    ///nokia-conf/configure/system/security/pki/est-profile/http-authentication/password
                    leaf password {
                        type types-sros:encrypted-leaf {
                            length "1..115";
                        }
                        description "Password for EST authentication";
                    }

                } // container http-authentication

            } // list est-profile

            ///nokia-conf/configure/system/security/pki/certificate-update-profile
            list certificate-update-profile {
                key "name";
                max-elements 256;
                description "Enter the certificate-update-profile list instance";

                ///nokia-conf/configure/system/security/pki/certificate-update-profile/name
                leaf name {
                    type types-sros:named-item;
                    description "Certificate update profile name";
                }

                ///nokia-conf/configure/system/security/pki/certificate-update-profile/hash-algorithm
                leaf hash-algorithm {
                    type types-security:hash-algorithm;
                    default "sha256";
                    description "Hash algorithm for a certificate request";
                }

                ///nokia-conf/configure/system/security/pki/certificate-update-profile/retry-interval
                leaf retry-interval {
                    type uint32 {
                        range "60..36000";
                    }
                    units "seconds";
                    default "3600";
                    description "Retry interval after a failed update";
                }

                ///nokia-conf/configure/system/security/pki/certificate-update-profile/apply-groups
                leaf-list apply-groups {
                    type leafref {
                        path "../../../../../groups/group/name";
                    }
                    max-elements 8;
                    ordered-by user;
                    description "Apply a configuration group at this level";
                }

                ///nokia-conf/configure/system/security/pki/certificate-update-profile/apply-groups-exclude
                leaf-list apply-groups-exclude {
                    type leafref {
                        path "../../../../../groups/group/name";
                    }
                    max-elements 8;
                    ordered-by user;
                    description "Exclude a configuration group at this level";
                }

                ///nokia-conf/configure/system/security/pki/certificate-update-profile/protocol
                choice protocol {
                    default "cmpv2";
                    ///nokia-conf/configure/system/security/pki/certificate-update-profile/protocol/cmpv2
                    case cmpv2 {

                        ///nokia-conf/configure/system/security/pki/certificate-update-profile/protocol/cmpv2/cmpv2
                        container cmpv2 {
                            description "Enter the cmpv2 context";

                            ///nokia-conf/configure/system/security/pki/certificate-update-profile/protocol/cmpv2/cmpv2/ca-profile
                            leaf ca-profile {
                                type leafref {
                                    path "../../../ca-profile/ca-profile-name";
                                }
                                description "CA profile name";
                            }

                        } // container cmpv2

                    }
                    ///nokia-conf/configure/system/security/pki/certificate-update-profile/protocol/est
                    case est {

                        ///nokia-conf/configure/system/security/pki/certificate-update-profile/protocol/est/est
                        container est {
                            description "Enter the est context";

                            ///nokia-conf/configure/system/security/pki/certificate-update-profile/protocol/est/est/est-profile
                            leaf est-profile {
                                type leafref {
                                    path "../../../est-profile/name";
                                }
                                description "EST profile name";
                            }

                        } // container est

                    }
                }
                ///nokia-conf/configure/system/security/pki/certificate-update-profile/key-generation
                choice key-generation {
                    default "same-as-existing-key";
                    ///nokia-conf/configure/system/security/pki/certificate-update-profile/key-generation/same-as-existing-key
                    case same-as-existing-key {

                        ///nokia-conf/configure/system/security/pki/certificate-update-profile/key-generation/same-as-existing-key/same-as-existing-key
                        leaf same-as-existing-key {
                            type empty;
                            description "Generate the new key to same type and key length";
                        }

                    }
                    ///nokia-conf/configure/system/security/pki/certificate-update-profile/key-generation/rsa
                    case rsa {

                        ///nokia-conf/configure/system/security/pki/certificate-update-profile/key-generation/rsa/rsa
                        container rsa {
                            description "Enter the rsa context";

                            ///nokia-conf/configure/system/security/pki/certificate-update-profile/key-generation/rsa/rsa/key-size
                            leaf key-size {
                                type uint32 {
                                    range "512..8192";
                                }
                                default "2048";
                                description "Length of the generated RSA key";
                            }

                        } // container rsa

                    }
                    ///nokia-conf/configure/system/security/pki/certificate-update-profile/key-generation/dsa
                    case dsa {

                        ///nokia-conf/configure/system/security/pki/certificate-update-profile/key-generation/dsa/dsa
                        container dsa {
                            description "Enter the dsa context";

                            ///nokia-conf/configure/system/security/pki/certificate-update-profile/key-generation/dsa/dsa/key-size
                            leaf key-size {
                                type uint32 {
                                    range "512..8192";
                                }
                                default "2048";
                                description "Length of the generated DSA key";
                            }

                        } // container dsa

                    }
                    ///nokia-conf/configure/system/security/pki/certificate-update-profile/key-generation/ecdsa
                    case ecdsa {

                        ///nokia-conf/configure/system/security/pki/certificate-update-profile/key-generation/ecdsa/ecdsa
                        container ecdsa {
                            description "Enter the ecdsa context";

                            ///nokia-conf/configure/system/security/pki/certificate-update-profile/key-generation/ecdsa/ecdsa/curve
                            leaf curve {
                                type types-security:ecdsa-curve;
                                default "secp256r1";
                                description "Elliptic curve to be used in ECDSA key generation";
                            }

                        } // container ecdsa

                    }
                }
                ///nokia-conf/configure/system/security/pki/certificate-update-profile/schedule
                choice schedule {
                    default "before-expiry";
                    ///nokia-conf/configure/system/security/pki/certificate-update-profile/schedule/before-expiry
                    case before-expiry {

                        ///nokia-conf/configure/system/security/pki/certificate-update-profile/schedule/before-expiry/before-expiry
                        leaf before-expiry {
                            type uint32 {
                                range "3600..157680000";
                            }
                            units "seconds";
                            default "86400";
                            description "Time scheduler updates before certificate expiry";
                        }

                    }
                    ///nokia-conf/configure/system/security/pki/certificate-update-profile/schedule/after-issue
                    case after-issue {

                        ///nokia-conf/configure/system/security/pki/certificate-update-profile/schedule/after-issue/after-issue
                        leaf after-issue {
                            type uint32 {
                                range "864000..157680000";
                            }
                            units "seconds";
                            description "Time for scheduler updates after certificate issuance";
                        }

                    }
                }
            } // list certificate-update-profile

            ///nokia-conf/configure/system/security/pki/certificate-auto-update
            list certificate-auto-update {
                key "certificate-file-name";
                max-elements 256;
                description "Enter the certificate-auto-update list instance";

                ///nokia-conf/configure/system/security/pki/certificate-auto-update/certificate-file-name
                leaf certificate-file-name {
                    type types-security:pki-file-name;
                    description "Certificate file name";
                }

                ///nokia-conf/configure/system/security/pki/certificate-auto-update/key-file-name
                leaf key-file-name {
                    type types-security:pki-file-name;
                    description "Imported key filename";
                }

                ///nokia-conf/configure/system/security/pki/certificate-auto-update/profile
                leaf profile {
                    type leafref {
                        path "../../certificate-update-profile/name";
                    }
                    description "Certificate update profile name";
                }

                ///nokia-conf/configure/system/security/pki/certificate-auto-update/apply-groups
                leaf-list apply-groups {
                    type leafref {
                        path "../../../../../groups/group/name";
                    }
                    max-elements 8;
                    ordered-by user;
                    description "Apply a configuration group at this level";
                }

                ///nokia-conf/configure/system/security/pki/certificate-auto-update/apply-groups-exclude
                leaf-list apply-groups-exclude {
                    type leafref {
                        path "../../../../../groups/group/name";
                    }
                    max-elements 8;
                    ordered-by user;
                    description "Exclude a configuration group at this level";
                }

            } // list certificate-auto-update

        } // container pki

    } // grouping conf-system-security-pki

}
