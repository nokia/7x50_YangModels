submodule nokia-conf-router-rip {

    yang-version "1.1";

    belongs-to nokia-conf { prefix "conf"; }

    import nokia-sros-yang-extensions     { prefix "sros-ext"; }
    import nokia-types-rip                { prefix "types-rip"; }
    import nokia-types-sros               { prefix "types-sros"; }

    include nokia-conf-groups;
    include nokia-conf-policy-options;

    sros-ext:sros-major-release "rel23";
    organization "Nokia";
    contact
        "Nokia SR OS Support
         Web: <http://www.nokia.com>";
    description
        "Nokia YANG Data model to configure router rip protocol attributes on SR OS based routers.

         Copyright 2016 Nokia. All rights reserved. Reproduction of this document
         is authorized on the condition that the foregoing copyright notice is included.

         This nokia-conf-router-rip YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping conf-router-rip {
        ///nokia-conf/configure/router/rip
        container rip {
            presence "Enable the rip context";
            description "Enable the rip context";

            ///nokia-conf/configure/router/rip/admin-state
            leaf admin-state {
                type types-sros:admin-state;
                default "enable";
                description "Administrative state of the RIP instance";
            }

            ///nokia-conf/configure/router/rip/description
            leaf description {
                type types-sros:description;
                description "Text description";
            }

            ///nokia-conf/configure/router/rip/authentication-key
            leaf authentication-key {
                type types-sros:encrypted-leaf {
                    length "1..51";
                }
                description "Authentication password passed between RIP neighbors";
            }

            ///nokia-conf/configure/router/rip/authentication-type
            leaf authentication-type {
                type types-rip:auth-type;
                default "none";
                description "Authentication type used between RIP neighbors";
            }

            ///nokia-conf/configure/router/rip/bfd-liveness
            leaf bfd-liveness {
                type boolean;
                default "false";
                description "Enable BFD to control the state of protocol adjacency";
            }

            ///nokia-conf/configure/router/rip/check-zero
            leaf check-zero {
                type boolean;
                default "false";
                description "Enable checking of mandatory zero fields";
            }

            ///nokia-conf/configure/router/rip/export-policy
            leaf-list export-policy {
                type leafref {
                    path "../../../policy-options/policy-statement/name";
                }
                max-elements 5;
                ordered-by user;
                description "Policies to determine exported routes";
            }

            ///nokia-conf/configure/router/rip/import-policy
            leaf-list import-policy {
                type leafref {
                    path "../../../policy-options/policy-statement/name";
                }
                max-elements 5;
                ordered-by user;
                description "Import policies to decide routes for routing table";
            }

            ///nokia-conf/configure/router/rip/message-size
            leaf message-size {
                type types-rip:message-size;
                default "25";
                description "Maximum number of routes in the RIP message";
            }

            ///nokia-conf/configure/router/rip/metric-in
            leaf metric-in {
                type types-rip:metric;
                default "1";
                description "Metric added to routes received from a RIP neighbor";
            }

            ///nokia-conf/configure/router/rip/metric-out
            leaf metric-out {
                type types-rip:metric;
                default "1";
                description "Metric added to routes exported into RIP";
            }

            ///nokia-conf/configure/router/rip/preference
            leaf preference {
                type types-rip:preference;
                default "100";
                description "Route preference";
            }

            ///nokia-conf/configure/router/rip/receive
            leaf receive {
                type types-rip:receive;
                default "both";
                description "Accepted version on received packets";
            }

            ///nokia-conf/configure/router/rip/send
            leaf send {
                type enumeration {
                    enum none                           { value 1; }
                    enum version-1                      { value 2; }
                    enum broadcast                      { value 3; }
                    enum multicast                      { value 4; }
                }
                default "broadcast";
                description "RIP version and method used to send RIP updates";
            }

            ///nokia-conf/configure/router/rip/split-horizon
            leaf split-horizon {
                type boolean;
                default "true";
                description "Enable split horizon and poison reverse";
            }

            ///nokia-conf/configure/router/rip/apply-groups
            leaf-list apply-groups {
                type leafref {
                    path "../../../groups/group/name";
                }
                max-elements 8;
                ordered-by user;
                description "Apply a configuration group at this level";
            }

            ///nokia-conf/configure/router/rip/apply-groups-exclude
            leaf-list apply-groups-exclude {
                type leafref {
                    path "../../../groups/group/name";
                }
                max-elements 8;
                ordered-by user;
                description "Exclude a configuration group at this level";
            }

            ///nokia-conf/configure/router/rip/export-limit
            container export-limit {
                presence "Enable the export-limit context";
                description "Enable the export-limit context";

                ///nokia-conf/configure/router/rip/export-limit/number
                leaf number {
                    type uint32 {
                        range "1..max";
                    }
                    mandatory true;
                    description "Maximum routes or prefixes exported from route table";
                }

                ///nokia-conf/configure/router/rip/export-limit/log-percent
                leaf log-percent {
                    type uint32 {
                        range "1..100";
                    }
                    description "Export limit before warning and SNMP notification sent";
                }

            } // container export-limit

            ///nokia-conf/configure/router/rip/timers
            container timers {
                presence "Enable the timers context";
                description "Enable the timers context";

                ///nokia-conf/configure/router/rip/timers/update
                leaf update {
                    type types-rip:timer-update;
                    mandatory true;
                    description "Timer that controls the frequency of updates";
                }

                ///nokia-conf/configure/router/rip/timers/timeout
                leaf timeout {
                    type types-rip:timer-timeout;
                    mandatory true;
                    description "RIP timeout timer";
                }

                ///nokia-conf/configure/router/rip/timers/flush
                leaf flush {
                    type types-rip:timer-flush;
                    mandatory true;
                    description "RIP flush timer";
                }

            } // container timers

            ///nokia-conf/configure/router/rip/group
            list group {
                key "group-name";
                description "Enter the group list instance";

                ///nokia-conf/configure/router/rip/group/group-name
                leaf group-name {
                    type types-sros:named-item;
                    description "RIP group name";
                }

                ///nokia-conf/configure/router/rip/group/admin-state
                leaf admin-state {
                    type types-sros:admin-state;
                    default "enable";
                    description "Administrative state of RIP neighbor interface group";
                }

                ///nokia-conf/configure/router/rip/group/description
                leaf description {
                    type types-sros:description;
                    description "Text description";
                }

                ///nokia-conf/configure/router/rip/group/export-policy
                leaf-list export-policy {
                    type leafref {
                        path "../../../../policy-options/policy-statement/name";
                    }
                    max-elements 5;
                    ordered-by user;
                    description "Policies used to rule which routes are exported to RIP";
                }

                ///nokia-conf/configure/router/rip/group/import-policy
                leaf-list import-policy {
                    type leafref {
                        path "../../../../policy-options/policy-statement/name";
                    }
                    max-elements 5;
                    ordered-by user;
                    description "Policies to decide routes accepted from RIP neighbors";
                }

                ///nokia-conf/configure/router/rip/group/authentication-key
                leaf authentication-key {
                    type types-sros:encrypted-leaf {
                        length "1..51";
                    }
                    description "Authentication password passed between RIP neighbors";
                }

                ///nokia-conf/configure/router/rip/group/authentication-type
                leaf authentication-type {
                    type types-rip:auth-type;
                    description "Authentication type";
                }

                ///nokia-conf/configure/router/rip/group/bfd-liveness
                leaf bfd-liveness {
                    type boolean;
                    description "Enable BFD to control the state of protocol adjacency";
                }

                ///nokia-conf/configure/router/rip/group/check-zero
                leaf check-zero {
                    type boolean;
                    description "Enable checking of mandatory zero fields";
                }

                ///nokia-conf/configure/router/rip/group/message-size
                leaf message-size {
                    type types-rip:message-size;
                    description "Maximum number of routes per RIP update message";
                }

                ///nokia-conf/configure/router/rip/group/metric-in
                leaf metric-in {
                    type types-rip:metric;
                    description "Metric added to routes received from a RIP neighbor";
                }

                ///nokia-conf/configure/router/rip/group/metric-out
                leaf metric-out {
                    type types-rip:metric;
                    description "Metric added to routes exported into RIP";
                }

                ///nokia-conf/configure/router/rip/group/preference
                leaf preference {
                    type types-rip:preference;
                    description "Route preference";
                }

                ///nokia-conf/configure/router/rip/group/receive
                leaf receive {
                    type types-rip:receive;
                    description "Accepted version on received packets";
                }

                ///nokia-conf/configure/router/rip/group/split-horizon
                leaf split-horizon {
                    type boolean;
                    description "Enable split horizon and poison reverse";
                }

                ///nokia-conf/configure/router/rip/group/send
                leaf send {
                    type enumeration {
                        enum none                           { value 1; }
                        enum version-1                      { value 2; }
                        enum broadcast                      { value 3; }
                        enum multicast                      { value 4; }
                    }
                    description "RIP version and method used to send RIP updates";
                }

                ///nokia-conf/configure/router/rip/group/apply-groups
                leaf-list apply-groups {
                    type leafref {
                        path "../../../../groups/group/name";
                    }
                    max-elements 8;
                    ordered-by user;
                    description "Apply a configuration group at this level";
                }

                ///nokia-conf/configure/router/rip/group/apply-groups-exclude
                leaf-list apply-groups-exclude {
                    type leafref {
                        path "../../../../groups/group/name";
                    }
                    max-elements 8;
                    ordered-by user;
                    description "Exclude a configuration group at this level";
                }

                ///nokia-conf/configure/router/rip/group/timers
                container timers {
                    presence "Enable the timers context";
                    description "Enable the timers context";

                    ///nokia-conf/configure/router/rip/group/timers/update
                    leaf update {
                        type types-rip:timer-update;
                        mandatory true;
                        description "Timer that controls the frequency of updates";
                    }

                    ///nokia-conf/configure/router/rip/group/timers/timeout
                    leaf timeout {
                        type types-rip:timer-timeout;
                        mandatory true;
                        description "RIP timeout timer";
                    }

                    ///nokia-conf/configure/router/rip/group/timers/flush
                    leaf flush {
                        type types-rip:timer-flush;
                        mandatory true;
                        description "RIP flush timer";
                    }

                } // container timers

                ///nokia-conf/configure/router/rip/group/neighbor
                list neighbor {
                    key "interface-name";
                    description "Enter the neighbor list instance";

                    ///nokia-conf/configure/router/rip/group/neighbor/interface-name
                    leaf interface-name {
                        type types-sros:interface-name;
                        description "Neighbor added through the interface to the RIP group";
                    }

                    ///nokia-conf/configure/router/rip/group/neighbor/admin-state
                    leaf admin-state {
                        type types-sros:admin-state;
                        default "enable";
                        description "Administrative state of the RIP neighbor interface";
                    }

                    ///nokia-conf/configure/router/rip/group/neighbor/description
                    leaf description {
                        type types-sros:description;
                        description "Text description";
                    }

                    ///nokia-conf/configure/router/rip/group/neighbor/export-policy
                    leaf-list export-policy {
                        type leafref {
                            path "../../../../../policy-options/policy-statement/name";
                        }
                        max-elements 5;
                        ordered-by user;
                        description "Policies used to rule which routes are exported to RIP";
                    }

                    ///nokia-conf/configure/router/rip/group/neighbor/import-policy
                    leaf-list import-policy {
                        type leafref {
                            path "../../../../../policy-options/policy-statement/name";
                        }
                        max-elements 5;
                        ordered-by user;
                        description "Policies to decide routes accepted from RIP neighbors";
                    }

                    ///nokia-conf/configure/router/rip/group/neighbor/authentication-key
                    leaf authentication-key {
                        type types-sros:encrypted-leaf {
                            length "1..51";
                        }
                        description "Authentication password passed between RIP neighbors";
                    }

                    ///nokia-conf/configure/router/rip/group/neighbor/authentication-type
                    leaf authentication-type {
                        type types-rip:auth-type;
                        description "Authentication type";
                    }

                    ///nokia-conf/configure/router/rip/group/neighbor/bfd-liveness
                    leaf bfd-liveness {
                        type boolean;
                        description "Enable BFD to control the state of protocol adjacency";
                    }

                    ///nokia-conf/configure/router/rip/group/neighbor/check-zero
                    leaf check-zero {
                        type boolean;
                        description "Enable checking of mandatory zero fields";
                    }

                    ///nokia-conf/configure/router/rip/group/neighbor/message-size
                    leaf message-size {
                        type types-rip:message-size;
                        description "Maximum number of routes per RIP update message";
                    }

                    ///nokia-conf/configure/router/rip/group/neighbor/metric-in
                    leaf metric-in {
                        type types-rip:metric;
                        description "Metric added to routes received from a RIP neighbor";
                    }

                    ///nokia-conf/configure/router/rip/group/neighbor/metric-out
                    leaf metric-out {
                        type types-rip:metric;
                        description "Metric added to routes exported into RIP";
                    }

                    ///nokia-conf/configure/router/rip/group/neighbor/preference
                    leaf preference {
                        type types-rip:preference;
                        description "Route preference";
                    }

                    ///nokia-conf/configure/router/rip/group/neighbor/receive
                    leaf receive {
                        type types-rip:receive;
                        description "Accepted version on received packets";
                    }

                    ///nokia-conf/configure/router/rip/group/neighbor/split-horizon
                    leaf split-horizon {
                        type boolean;
                        description "Enable split horizon and poison reverse";
                    }

                    ///nokia-conf/configure/router/rip/group/neighbor/send
                    leaf send {
                        type enumeration {
                            enum none                           { value 1; }
                            enum version-1                      { value 2; }
                            enum broadcast                      { value 3; }
                            enum multicast                      { value 4; }
                            enum unicast                        { value 6; }
                        }
                        description "RIP version and method used to send RIP updates";
                    }

                    ///nokia-conf/configure/router/rip/group/neighbor/apply-groups
                    leaf-list apply-groups {
                        type leafref {
                            path "../../../../../groups/group/name";
                        }
                        max-elements 8;
                        ordered-by user;
                        description "Apply a configuration group at this level";
                    }

                    ///nokia-conf/configure/router/rip/group/neighbor/apply-groups-exclude
                    leaf-list apply-groups-exclude {
                        type leafref {
                            path "../../../../../groups/group/name";
                        }
                        max-elements 8;
                        ordered-by user;
                        description "Exclude a configuration group at this level";
                    }

                    ///nokia-conf/configure/router/rip/group/neighbor/timers
                    container timers {
                        presence "Enable the timers context";
                        description "Enable the timers context";

                        ///nokia-conf/configure/router/rip/group/neighbor/timers/update
                        leaf update {
                            type types-rip:timer-update;
                            mandatory true;
                            description "Timer that controls the frequency of updates";
                        }

                        ///nokia-conf/configure/router/rip/group/neighbor/timers/timeout
                        leaf timeout {
                            type types-rip:timer-timeout;
                            mandatory true;
                            description "RIP timeout timer";
                        }

                        ///nokia-conf/configure/router/rip/group/neighbor/timers/flush
                        leaf flush {
                            type types-rip:timer-flush;
                            mandatory true;
                            description "RIP flush timer";
                        }

                    } // container timers

                    ///nokia-conf/configure/router/rip/group/neighbor/unicast-address
                    list unicast-address {
                        key "address";
                        description "Add a list entry for unicast-address";

                        ///nokia-conf/configure/router/rip/group/neighbor/unicast-address/address
                        leaf address {
                            type types-sros:ipv4-unicast-address;
                            description "Unicast address for the neighbor";
                        }

                    } // list unicast-address

                } // list neighbor

            } // list group

        } // container rip

    } // grouping conf-router-rip

}
