submodule nokia-conf-filter {

    yang-version "1.1";

    belongs-to nokia-conf { prefix "conf"; }

    import ietf-yang-types                { prefix "yang"; }
    import nokia-sros-yang-extensions     { prefix "sros-ext"; }
    import nokia-types-filter             { prefix "types-filter"; }
    import nokia-types-qos                { prefix "types-qos"; }
    import nokia-types-services           { prefix "types-services"; }
    import nokia-types-sros               { prefix "types-sros"; }
    import nokia-types-subscriber-mgmt    { prefix "types-submgt"; }

    include nokia-conf-cflowd;
    include nokia-conf-filter-dhcp;
    include nokia-conf-filter-ip-exception;
    include nokia-conf-groups;
    include nokia-conf-log;
    include nokia-conf-openflow;
    include nokia-conf-service;
    include nokia-conf-svc-nat;
    include nokia-conf-svc-vpls;
    include nokia-conf-svc-vprn;

    sros-ext:sros-major-release "rel23";
    organization "Nokia";
    contact
        "Nokia SR OS Support
         Web: <http://www.nokia.com>";
    description
        "Nokia YANG Data model to configure line card ACL filters on SR OS based routers.

         Copyright 2016 Nokia. All rights reserved. Reproduction of this document
         is authorized on the condition that the foregoing copyright notice is included.

         This nokia-conf-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-31";

    grouping conf-filter {
        ///nokia-conf/configure/filter
        container filter {
            description "Enter the filter context";

            ///nokia-conf/configure/filter/apply-groups
            leaf-list apply-groups {
                type leafref {
                    path "../../groups/group/name";
                }
                max-elements 8;
                ordered-by user;
                description "Apply a configuration group at this level";
            }

            ///nokia-conf/configure/filter/apply-groups-exclude
            leaf-list apply-groups-exclude {
                type leafref {
                    path "../../groups/group/name";
                }
                max-elements 8;
                ordered-by user;
                description "Exclude a configuration group at this level";
            }

            ///nokia-conf/configure/filter/redirect-policy
            list redirect-policy {
                key "redirect-policy-name";
                description "Enter the redirect-policy list instance";

                ///nokia-conf/configure/filter/redirect-policy/redirect-policy-name
                leaf redirect-policy-name {
                    type types-sros:named-item;
                    description "Redirect policy name";
                }

                ///nokia-conf/configure/filter/redirect-policy/admin-state
                leaf admin-state {
                    type types-sros:admin-state;
                    default "disable";
                    description "Administrative state of the redirect policy";
                }

                ///nokia-conf/configure/filter/redirect-policy/description
                leaf description {
                    type types-sros:description;
                    description "Text description";
                }

                ///nokia-conf/configure/filter/redirect-policy/router-instance
                leaf router-instance {
                    type string;
                    description "Routing context to use for route lookup";
                }

                ///nokia-conf/configure/filter/redirect-policy/sticky-dest
                leaf sticky-dest {
                    type types-filter:filter-sticky-dest;
                    units "seconds";
                    description "Time required by system before applying the current best destination as active destination";
                }

                ///nokia-conf/configure/filter/redirect-policy/notify-dest-change
                leaf notify-dest-change {
                    type boolean;
                    default "false";
                    description "Send notifications when the active destination changes";
                }

                ///nokia-conf/configure/filter/redirect-policy/apply-groups
                leaf-list apply-groups {
                    type leafref {
                        path "../../../groups/group/name";
                    }
                    max-elements 8;
                    ordered-by user;
                    description "Apply a configuration group at this level";
                }

                ///nokia-conf/configure/filter/redirect-policy/apply-groups-exclude
                leaf-list apply-groups-exclude {
                    type leafref {
                        path "../../../groups/group/name";
                    }
                    max-elements 8;
                    ordered-by user;
                    description "Exclude a configuration group at this level";
                }

                ///nokia-conf/configure/filter/redirect-policy/destination
                list destination {
                    key "destination-address";
                    description "Enter the destination list instance";

                    ///nokia-conf/configure/filter/redirect-policy/destination/destination-address
                    leaf destination-address {
                        type types-sros:ip-unicast-address;
                        description "IP address and type of destination";
                    }

                    ///nokia-conf/configure/filter/redirect-policy/destination/admin-state
                    leaf admin-state {
                        type types-sros:admin-state;
                        default "disable";
                        description "Administrative state of the destination";
                    }

                    ///nokia-conf/configure/filter/redirect-policy/destination/description
                    leaf description {
                        type types-sros:description;
                        description "Text description";
                    }

                    ///nokia-conf/configure/filter/redirect-policy/destination/priority
                    leaf priority {
                        type uint32 {
                            range "1..255";
                        }
                        default "100";
                        description "Priority for this destination";
                    }

                    ///nokia-conf/configure/filter/redirect-policy/destination/apply-groups
                    leaf-list apply-groups {
                        type leafref {
                            path "../../../../groups/group/name";
                        }
                        max-elements 8;
                        ordered-by user;
                        description "Apply a configuration group at this level";
                    }

                    ///nokia-conf/configure/filter/redirect-policy/destination/apply-groups-exclude
                    leaf-list apply-groups-exclude {
                        type leafref {
                            path "../../../../groups/group/name";
                        }
                        max-elements 8;
                        ordered-by user;
                        description "Exclude a configuration group at this level";
                    }

                    ///nokia-conf/configure/filter/redirect-policy/destination/ping-test
                    container ping-test {
                        presence "Enable the ping-test context";
                        description "Enable the ping-test context";

                        ///nokia-conf/configure/filter/redirect-policy/destination/ping-test/source-address
                        leaf source-address {
                            type types-sros:ip-address;
                            description "Source address to use in the IP packet of the ping test";
                        }

                        ///nokia-conf/configure/filter/redirect-policy/destination/ping-test/interval
                        leaf interval {
                            type uint32 {
                                range "1..60";
                            }
                            units "seconds";
                            default "1";
                            description "Time between consecutive requests which are sent to the far end host";
                        }

                        ///nokia-conf/configure/filter/redirect-policy/destination/ping-test/timeout
                        leaf timeout {
                            type uint32 {
                                range "1..60";
                            }
                            units "seconds";
                            default "1";
                            description "Time required to receive a response from the far end host";
                        }

                        ///nokia-conf/configure/filter/redirect-policy/destination/ping-test/drop-count
                        leaf drop-count {
                            type uint32 {
                                range "1..60";
                            }
                            default "3";
                            description "Number of consecutive requests that fail before destination is declared unreachable";
                        }

                        ///nokia-conf/configure/filter/redirect-policy/destination/ping-test/hold-down
                        leaf hold-down {
                            type uint32 {
                                range "0..86400";
                            }
                            units "seconds";
                            default "0";
                            description "Time for the system to be held down if this test has marked it unreachable";
                        }

                        ///nokia-conf/configure/filter/redirect-policy/destination/ping-test/apply-groups
                        leaf-list apply-groups {
                            type leafref {
                                path "../../../../../groups/group/name";
                            }
                            max-elements 8;
                            ordered-by user;
                            description "Apply a configuration group at this level";
                        }

                        ///nokia-conf/configure/filter/redirect-policy/destination/ping-test/apply-groups-exclude
                        leaf-list apply-groups-exclude {
                            type leafref {
                                path "../../../../../groups/group/name";
                            }
                            max-elements 8;
                            ordered-by user;
                            description "Exclude a configuration group at this level";
                        }

                    } // container ping-test

                    ///nokia-conf/configure/filter/redirect-policy/destination/unicast-rt-test
                    container unicast-rt-test {
                        presence "Enable the unicast-rt-test context";
                        description "Enable the unicast-rt-test context";

                    } // container unicast-rt-test

                } // list destination

            } // list redirect-policy

            ///nokia-conf/configure/filter/redirect-policy-binding
            list redirect-policy-binding {
                key "binding-name";
                max-elements 16;
                description "Enter the redirect-policy-binding list instance";

                ///nokia-conf/configure/filter/redirect-policy-binding/binding-name
                leaf binding-name {
                    type types-sros:named-item;
                    description "Binding name";
                }

                ///nokia-conf/configure/filter/redirect-policy-binding/binding-operator
                leaf binding-operator {
                    type types-filter:filter-binding-operator;
                    default "and";
                    description "Logical operator used to obtain the master test result";
                }

                ///nokia-conf/configure/filter/redirect-policy-binding/apply-groups
                leaf-list apply-groups {
                    type leafref {
                        path "../../../groups/group/name";
                    }
                    max-elements 8;
                    ordered-by user;
                    description "Apply a configuration group at this level";
                }

                ///nokia-conf/configure/filter/redirect-policy-binding/apply-groups-exclude
                leaf-list apply-groups-exclude {
                    type leafref {
                        path "../../../groups/group/name";
                    }
                    max-elements 8;
                    ordered-by user;
                    description "Exclude a configuration group at this level";
                }

                ///nokia-conf/configure/filter/redirect-policy-binding/redirect-policy
                list redirect-policy {
                    key "redirect-policy-name";
                    description "Enter the redirect-policy list instance";

                    ///nokia-conf/configure/filter/redirect-policy-binding/redirect-policy/redirect-policy-name
                    leaf redirect-policy-name {
                        type leafref {
                            path "../../../redirect-policy/redirect-policy-name";
                        }
                        description "Redirect policy name";
                    }

                    ///nokia-conf/configure/filter/redirect-policy-binding/redirect-policy/apply-groups
                    leaf-list apply-groups {
                        type leafref {
                            path "../../../../groups/group/name";
                        }
                        max-elements 8;
                        ordered-by user;
                        description "Apply a configuration group at this level";
                    }

                    ///nokia-conf/configure/filter/redirect-policy-binding/redirect-policy/apply-groups-exclude
                    leaf-list apply-groups-exclude {
                        type leafref {
                            path "../../../../groups/group/name";
                        }
                        max-elements 8;
                        ordered-by user;
                        description "Exclude a configuration group at this level";
                    }

                    ///nokia-conf/configure/filter/redirect-policy-binding/redirect-policy/destination
                    list destination {
                        key "destination-address";
                        min-elements 1;
                        description "Add a list entry for destination";

                        ///nokia-conf/configure/filter/redirect-policy-binding/redirect-policy/destination/destination-address
                        leaf destination-address {
                            type leafref {
                                path "../../../../redirect-policy[redirect-policy-name=current()/../../redirect-policy-name]/destination/destination-address";
                            }
                            description "IP address of redirect policy destination to binding";
                        }

                    } // list destination

                } // list redirect-policy

            } // list redirect-policy-binding

            ///nokia-conf/configure/filter/log
            list log {
                key "log-id";
                description "Enter the log list instance";

                ///nokia-conf/configure/filter/log/log-id
                leaf log-id {
                    type types-filter:filter-log-id;
                    description "Filter log identifier";
                }

                ///nokia-conf/configure/filter/log/description
                leaf description {
                    type types-sros:description-or-empty;
                    description "Text description";
                }

                ///nokia-conf/configure/filter/log/admin-state
                leaf admin-state {
                    type types-sros:admin-state;
                    default "enable";
                    description "Administrative state of filter logging";
                }

                ///nokia-conf/configure/filter/log/apply-groups
                leaf-list apply-groups {
                    type leafref {
                        path "../../../groups/group/name";
                    }
                    max-elements 8;
                    ordered-by user;
                    description "Apply a configuration group at this level";
                }

                ///nokia-conf/configure/filter/log/apply-groups-exclude
                leaf-list apply-groups-exclude {
                    type leafref {
                        path "../../../groups/group/name";
                    }
                    max-elements 8;
                    ordered-by user;
                    description "Exclude a configuration group at this level";
                }

                ///nokia-conf/configure/filter/log/destination
                container destination {
                    description "Enter the destination context";

                    ///nokia-conf/configure/filter/log/destination/destination
                    choice destination {
                        default "memory";
                        ///nokia-conf/configure/filter/log/destination/destination/memory
                        case memory {

                            ///nokia-conf/configure/filter/log/destination/destination/memory/memory
                            container memory {
                                description "Enter the memory context";

                                ///nokia-conf/configure/filter/log/destination/destination/memory/memory/max-entries
                                leaf max-entries {
                                    type uint32 {
                                        range "1..50000";
                                    }
                                    default "1000";
                                    description "Maximum number of memory entries that the log can store";
                                }

                                ///nokia-conf/configure/filter/log/destination/destination/memory/memory/stop-on-full
                                leaf stop-on-full {
                                    type boolean;
                                    default "false";
                                    description "Stop logging when maximum number of memory entries is reached or wrap-around is used";
                                }

                            } // container memory

                        }
                        ///nokia-conf/configure/filter/log/destination/destination/syslog
                        case syslog {

                            ///nokia-conf/configure/filter/log/destination/destination/syslog/syslog
                            container syslog {
                                description "Enter the syslog context";

                                ///nokia-conf/configure/filter/log/destination/destination/syslog/syslog/syslog-id
                                leaf syslog-id {
                                    status obsolete;
                                    type leafref {
                                        path "../../../../../log/syslog/syslog-name";
                                    }
                                    description "ID of the Syslog server definition for filter logs";
                                }

                                ///nokia-conf/configure/filter/log/destination/destination/syslog/syslog/name
                                leaf name {
                                    type leafref {
                                        path "../../../../../log/syslog/syslog-name";
                                    }
                                    description "Syslog server definition ID";
                                }

                                ///nokia-conf/configure/filter/log/destination/destination/syslog/syslog/summary
                                container summary {
                                    description "Enter the summary context";

                                    ///nokia-conf/configure/filter/log/destination/destination/syslog/syslog/summary/admin-state
                                    leaf admin-state {
                                        type types-sros:admin-state;
                                        default "disable";
                                        description "Administrative state of filter log summarization";
                                    }

                                    ///nokia-conf/configure/filter/log/destination/destination/syslog/syslog/summary/summary-crit
                                    leaf summary-crit {
                                        type types-filter:filter-log-summary-criterion;
                                        default "src-addr";
                                        description "Summary for filter log entries";
                                    }

                                } // container summary

                            } // container syslog

                        }
                    }
                } // container destination

            } // list log

            ///nokia-conf/configure/filter/match-list
            container match-list {
                description "Enter the match-list context";

                ///nokia-conf/configure/filter/match-list/apply-groups
                leaf-list apply-groups {
                    type leafref {
                        path "../../../groups/group/name";
                    }
                    max-elements 8;
                    ordered-by user;
                    description "Apply a configuration group at this level";
                }

                ///nokia-conf/configure/filter/match-list/apply-groups-exclude
                leaf-list apply-groups-exclude {
                    type leafref {
                        path "../../../groups/group/name";
                    }
                    max-elements 8;
                    ordered-by user;
                    description "Exclude a configuration group at this level";
                }

                ///nokia-conf/configure/filter/match-list/protocol-list
                list protocol-list {
                    key "protocol-list-name";
                    max-elements 512;
                    description "Enter the protocol-list list instance";

                    ///nokia-conf/configure/filter/match-list/protocol-list/protocol-list-name
                    leaf protocol-list-name {
                        type types-sros:named-item;
                        description "Protocol list name";
                    }

                    ///nokia-conf/configure/filter/match-list/protocol-list/description
                    leaf description {
                        type types-sros:description;
                        description "Text description";
                    }

                    ///nokia-conf/configure/filter/match-list/protocol-list/apply-groups
                    leaf-list apply-groups {
                        type leafref {
                            path "../../../../groups/group/name";
                        }
                        max-elements 8;
                        ordered-by user;
                        description "Apply a configuration group at this level";
                    }

                    ///nokia-conf/configure/filter/match-list/protocol-list/apply-groups-exclude
                    leaf-list apply-groups-exclude {
                        type leafref {
                            path "../../../../groups/group/name";
                        }
                        max-elements 8;
                        ordered-by user;
                        description "Exclude a configuration group at this level";
                    }

                    ///nokia-conf/configure/filter/match-list/protocol-list/protocol
                    list protocol {
                        key "protocol-id";
                        max-elements 32;
                        description "Add a list entry for protocol";

                        ///nokia-conf/configure/filter/match-list/protocol-list/protocol/protocol-id
                        leaf protocol-id {
                            type types-sros:ip-protocol;
                            description "IP protocol identifier";
                        }

                    } // list protocol

                } // list protocol-list

                ///nokia-conf/configure/filter/match-list/ip-prefix-list
                list ip-prefix-list {
                    key "prefix-list-name";
                    description "Enter the ip-prefix-list list instance";

                    ///nokia-conf/configure/filter/match-list/ip-prefix-list/prefix-list-name
                    leaf prefix-list-name {
                        type types-sros:named-item;
                        description "IP prefix list name";
                    }

                    ///nokia-conf/configure/filter/match-list/ip-prefix-list/description
                    leaf description {
                        type types-sros:description;
                        description "Text description";
                    }

                    ///nokia-conf/configure/filter/match-list/ip-prefix-list/apply-groups
                    leaf-list apply-groups {
                        type leafref {
                            path "../../../../groups/group/name";
                        }
                        max-elements 8;
                        ordered-by user;
                        description "Apply a configuration group at this level";
                    }

                    ///nokia-conf/configure/filter/match-list/ip-prefix-list/apply-groups-exclude
                    leaf-list apply-groups-exclude {
                        type leafref {
                            path "../../../../groups/group/name";
                        }
                        max-elements 8;
                        ordered-by user;
                        description "Exclude a configuration group at this level";
                    }

                    ///nokia-conf/configure/filter/match-list/ip-prefix-list/apply-path
                    container apply-path {
                        description "Enter the apply-path context";

                        ///nokia-conf/configure/filter/match-list/ip-prefix-list/apply-path/bgp-peers
                        list bgp-peers {
                            key "criterion-index";
                            description "Enter the bgp-peers list instance";

                            ///nokia-conf/configure/filter/match-list/ip-prefix-list/apply-path/bgp-peers/criterion-index
                            leaf criterion-index {
                                type uint32 {
                                    range "1..255";
                                }
                                description "BGP peers auto-generation configuration index";
                            }

                            ///nokia-conf/configure/filter/match-list/ip-prefix-list/apply-path/bgp-peers/group
                            leaf group {
                                type types-sros:regular-expression-not-all-spaces;
                                sros-ext:immutable;
                                mandatory true;
                                description "Regular expression to match against the base router BGP instance group configuration";
                            }

                            ///nokia-conf/configure/filter/match-list/ip-prefix-list/apply-path/bgp-peers/neighbor
                            leaf neighbor {
                                type types-sros:regular-expression-not-all-spaces;
                                sros-ext:immutable;
                                mandatory true;
                                description "Regular expression to match against the base router BGP instance neighbor configuration";
                            }

                            ///nokia-conf/configure/filter/match-list/ip-prefix-list/apply-path/bgp-peers/router-instance
                            leaf router-instance {
                                type string;
                                sros-ext:immutable;
                                default "Base";
                                description "Target routing instance";
                            }

                            ///nokia-conf/configure/filter/match-list/ip-prefix-list/apply-path/bgp-peers/apply-groups
                            leaf-list apply-groups {
                                type leafref {
                                    path "../../../../../../groups/group/name";
                                }
                                max-elements 8;
                                ordered-by user;
                                description "Apply a configuration group at this level";
                            }

                            ///nokia-conf/configure/filter/match-list/ip-prefix-list/apply-path/bgp-peers/apply-groups-exclude
                            leaf-list apply-groups-exclude {
                                type leafref {
                                    path "../../../../../../groups/group/name";
                                }
                                max-elements 8;
                                ordered-by user;
                                description "Exclude a configuration group at this level";
                            }

                        } // list bgp-peers



                    } // container apply-path

                    ///nokia-conf/configure/filter/match-list/ip-prefix-list/prefix
                    list prefix {
                        key "ip-prefix";
                        max-elements 8192;
                        description "Add a list entry for prefix";

                        ///nokia-conf/configure/filter/match-list/ip-prefix-list/prefix/ip-prefix
                        leaf ip-prefix {
                            type types-sros:ipv4-prefix;
                            description "IPv4 prefix to be added to the prefix list";
                        }

                    } // list prefix

                    ///nokia-conf/configure/filter/match-list/ip-prefix-list/prefix-exclude
                    list prefix-exclude {
                        key "ip-prefix";
                        max-elements 512;
                        description "Add a list entry for prefix-exclude";

                        ///nokia-conf/configure/filter/match-list/ip-prefix-list/prefix-exclude/ip-prefix
                        leaf ip-prefix {
                            type types-sros:ipv4-prefix;
                            description "IPv4 prefix to be added to the prefix list";
                        }

                    } // list prefix-exclude

                } // list ip-prefix-list

                ///nokia-conf/configure/filter/match-list/ipv6-prefix-list
                list ipv6-prefix-list {
                    key "prefix-list-name";
                    description "Enter the ipv6-prefix-list list instance";

                    ///nokia-conf/configure/filter/match-list/ipv6-prefix-list/prefix-list-name
                    leaf prefix-list-name {
                        type types-sros:named-item;
                        description "IP prefix list name";
                    }

                    ///nokia-conf/configure/filter/match-list/ipv6-prefix-list/description
                    leaf description {
                        type types-sros:description;
                        description "Text description";
                    }

                    ///nokia-conf/configure/filter/match-list/ipv6-prefix-list/apply-groups
                    leaf-list apply-groups {
                        type leafref {
                            path "../../../../groups/group/name";
                        }
                        max-elements 8;
                        ordered-by user;
                        description "Apply a configuration group at this level";
                    }

                    ///nokia-conf/configure/filter/match-list/ipv6-prefix-list/apply-groups-exclude
                    leaf-list apply-groups-exclude {
                        type leafref {
                            path "../../../../groups/group/name";
                        }
                        max-elements 8;
                        ordered-by user;
                        description "Exclude a configuration group at this level";
                    }

                    ///nokia-conf/configure/filter/match-list/ipv6-prefix-list/apply-path
                    container apply-path {
                        description "Enter the apply-path context";

                        ///nokia-conf/configure/filter/match-list/ipv6-prefix-list/apply-path/bgp-peers
                        list bgp-peers {
                            key "criterion-index";
                            description "Enter the bgp-peers list instance";

                            ///nokia-conf/configure/filter/match-list/ipv6-prefix-list/apply-path/bgp-peers/criterion-index
                            leaf criterion-index {
                                type uint32 {
                                    range "1..255";
                                }
                                description "BGP peers auto-generation configuration index";
                            }

                            ///nokia-conf/configure/filter/match-list/ipv6-prefix-list/apply-path/bgp-peers/group
                            leaf group {
                                type types-sros:regular-expression-not-all-spaces;
                                sros-ext:immutable;
                                mandatory true;
                                description "Regular expression to match against the base router BGP instance group configuration";
                            }

                            ///nokia-conf/configure/filter/match-list/ipv6-prefix-list/apply-path/bgp-peers/neighbor
                            leaf neighbor {
                                type types-sros:regular-expression-not-all-spaces;
                                sros-ext:immutable;
                                mandatory true;
                                description "Regular expression to match against the base router BGP instance neighbor configuration";
                            }

                            ///nokia-conf/configure/filter/match-list/ipv6-prefix-list/apply-path/bgp-peers/router-instance
                            leaf router-instance {
                                type string;
                                sros-ext:immutable;
                                default "Base";
                                description "Target routing instance";
                            }

                            ///nokia-conf/configure/filter/match-list/ipv6-prefix-list/apply-path/bgp-peers/apply-groups
                            leaf-list apply-groups {
                                type leafref {
                                    path "../../../../../../groups/group/name";
                                }
                                max-elements 8;
                                ordered-by user;
                                description "Apply a configuration group at this level";
                            }

                            ///nokia-conf/configure/filter/match-list/ipv6-prefix-list/apply-path/bgp-peers/apply-groups-exclude
                            leaf-list apply-groups-exclude {
                                type leafref {
                                    path "../../../../../../groups/group/name";
                                }
                                max-elements 8;
                                ordered-by user;
                                description "Exclude a configuration group at this level";
                            }

                        } // list bgp-peers


                    } // container apply-path

                    ///nokia-conf/configure/filter/match-list/ipv6-prefix-list/prefix
                    list prefix {
                        key "ipv6-prefix";
                        max-elements 8192;
                        description "Add a list entry for prefix";

                        ///nokia-conf/configure/filter/match-list/ipv6-prefix-list/prefix/ipv6-prefix
                        leaf ipv6-prefix {
                            type types-sros:ipv6-prefix;
                            description "IPv6 prefix to be added to the prefix list";
                        }

                    } // list prefix

                    ///nokia-conf/configure/filter/match-list/ipv6-prefix-list/prefix-exclude
                    list prefix-exclude {
                        key "ipv6-prefix";
                        max-elements 512;
                        description "Add a list entry for prefix-exclude";

                        ///nokia-conf/configure/filter/match-list/ipv6-prefix-list/prefix-exclude/ipv6-prefix
                        leaf ipv6-prefix {
                            type types-sros:ipv6-prefix;
                            description "IPv6 prefix to be added to the prefix list";
                        }

                    } // list prefix-exclude

                } // list ipv6-prefix-list

                ///nokia-conf/configure/filter/match-list/port-list
                list port-list {
                    key "port-list-name";
                    max-elements 5120;
                    description "Enter the port-list list instance";

                    ///nokia-conf/configure/filter/match-list/port-list/port-list-name
                    leaf port-list-name {
                        type types-sros:named-item;
                        description "Port list name";
                    }

                    ///nokia-conf/configure/filter/match-list/port-list/description
                    leaf description {
                        type types-sros:description;
                        description "Text description";
                    }

                    ///nokia-conf/configure/filter/match-list/port-list/apply-groups
                    leaf-list apply-groups {
                        type leafref {
                            path "../../../../groups/group/name";
                        }
                        max-elements 8;
                        ordered-by user;
                        description "Apply a configuration group at this level";
                    }

                    ///nokia-conf/configure/filter/match-list/port-list/apply-groups-exclude
                    leaf-list apply-groups-exclude {
                        type leafref {
                            path "../../../../groups/group/name";
                        }
                        max-elements 8;
                        ordered-by user;
                        description "Exclude a configuration group at this level";
                    }

                    ///nokia-conf/configure/filter/match-list/port-list/port
                    list port {
                        key "value";
                        description "Add a list entry for port";

                        ///nokia-conf/configure/filter/match-list/port-list/port/value
                        leaf value {
                            type int32 {
                                range "0..65535";
                            }
                            description "Port value";
                        }

                    } // list port

                    ///nokia-conf/configure/filter/match-list/port-list/range
                    list range {
                        key "start end";
                        description "Add a list entry for range";

                        ///nokia-conf/configure/filter/match-list/port-list/range/start
                        leaf start {
                            type int32 {
                                range "0..65534";
                            }
                            description "Lower bound of the port list range";
                        }

                        ///nokia-conf/configure/filter/match-list/port-list/range/end
                        leaf end {
                            type int32 {
                                range "1..65535";
                            }
                            description "Upper bound of the port list range";
                        }

                    } // list range

                } // list port-list

            } // container match-list

            ///nokia-conf/configure/filter/ip-filter
            list ip-filter {
                key "filter-name";
                description "Enter the ip-filter list instance";

                ///nokia-conf/configure/filter/ip-filter/filter-name
                leaf filter-name {
                    type types-filter:filter-name;
                    description "Filter name";
                }

                ///nokia-conf/configure/filter/ip-filter/default-action
                leaf default-action {
                    type types-filter:filter-default-action;
                    default "drop";
                    description "Action for packets that do not match any entry";
                }

                ///nokia-conf/configure/filter/ip-filter/description
                leaf description {
                    type types-sros:description;
                    description "Text description";
                }

                ///nokia-conf/configure/filter/ip-filter/scope
                leaf scope {
                    type types-filter:filter-scope;
                    default "template";
                    description "Scope of the filter defintion";
                }

                ///nokia-conf/configure/filter/ip-filter/type
                leaf type {
                    type enumeration {
                        enum normal                         { value 0; }
                        enum src-mac                        { value 1; }
                        enum packet-length                  { value 2; }
                        enum destination-class              { value 3; }
                    }
                    default "normal";
                    description "Set of match criteria for the filter policy";
                }

                ///nokia-conf/configure/filter/ip-filter/chain-to-system-filter
                leaf chain-to-system-filter {
                    type boolean;
                    default "false";
                    description "Chain filter policy to the active IPvX system filter policy";
                }

                ///nokia-conf/configure/filter/ip-filter/shared-policer
                leaf shared-policer {
                    type boolean;
                    default "false";
                    description "Share policer among active ports in the LAG";
                }

                ///nokia-conf/configure/filter/ip-filter/filter-id
                leaf filter-id {
                    type types-filter:filter-id;
                    sros-ext:immutable;
                    description "IP filter ID";
                }

                ///nokia-conf/configure/filter/ip-filter/apply-groups
                leaf-list apply-groups {
                    type leafref {
                        path "../../../groups/group/name";
                    }
                    max-elements 8;
                    ordered-by user;
                    description "Apply a configuration group at this level";
                }

                ///nokia-conf/configure/filter/ip-filter/apply-groups-exclude
                leaf-list apply-groups-exclude {
                    type leafref {
                        path "../../../groups/group/name";
                    }
                    max-elements 8;
                    ordered-by user;
                    description "Exclude a configuration group at this level";
                }

                ///nokia-conf/configure/filter/ip-filter/subscriber-mgmt
                container subscriber-mgmt {
                    description "Enter the subscriber-mgmt context";

                    ///nokia-conf/configure/filter/ip-filter/subscriber-mgmt/host-specific-entry
                    container host-specific-entry {
                        description "Enter the host-specific-entry context";

                        ///nokia-conf/configure/filter/ip-filter/subscriber-mgmt/host-specific-entry/filter-rule
                        container filter-rule {
                            description "Enter the filter-rule context";

                            ///nokia-conf/configure/filter/ip-filter/subscriber-mgmt/host-specific-entry/filter-rule/range
                            container range {
                                presence "Enable the range context";
                                description "Enable the range context";

                                ///nokia-conf/configure/filter/ip-filter/subscriber-mgmt/host-specific-entry/filter-rule/range/start
                                leaf start {
                                    type types-filter:entry-id;
                                    mandatory true;
                                    description "Lower bound of range for inserting filter rule entries";
                                }

                                ///nokia-conf/configure/filter/ip-filter/subscriber-mgmt/host-specific-entry/filter-rule/range/end
                                leaf end {
                                    type types-filter:entry-id;
                                    mandatory true;
                                    description "Upper bound of range for inserting filter rule entries";
                                }

                            } // container range

                        } // container filter-rule

                        ///nokia-conf/configure/filter/ip-filter/subscriber-mgmt/host-specific-entry/credit-control
                        container credit-control {
                            description "Enter the credit-control context";

                            ///nokia-conf/configure/filter/ip-filter/subscriber-mgmt/host-specific-entry/credit-control/range
                            container range {
                                presence "Enable the range context";
                                description "Enable the range context";

                                ///nokia-conf/configure/filter/ip-filter/subscriber-mgmt/host-specific-entry/credit-control/range/start
                                leaf start {
                                    type types-filter:entry-id;
                                    mandatory true;
                                    description "Lower bound of range for credit control filter entries";
                                }

                                ///nokia-conf/configure/filter/ip-filter/subscriber-mgmt/host-specific-entry/credit-control/range/end
                                leaf end {
                                    type types-filter:entry-id;
                                    mandatory true;
                                    description "Upper bound of range for credit control filter entries";
                                }

                            } // container range

                        } // container credit-control

                        ///nokia-conf/configure/filter/ip-filter/subscriber-mgmt/host-specific-entry/watermark
                        container watermark {
                            description "Enter the watermark context";

                            ///nokia-conf/configure/filter/ip-filter/subscriber-mgmt/host-specific-entry/watermark/low
                            leaf low {
                                type int32 {
                                    range "0..100";
                                }
                                default "90";
                                description "Low watermark for host-specific entries, to clear a table full alarm";
                            }

                            ///nokia-conf/configure/filter/ip-filter/subscriber-mgmt/host-specific-entry/watermark/high
                            leaf high {
                                type int32 {
                                    range "0..100";
                                }
                                default "95";
                                description "High watermark for host-specific entries, to raise a table full alarm";
                            }

                        } // container watermark

                    } // container host-specific-entry

                    ///nokia-conf/configure/filter/ip-filter/subscriber-mgmt/shared-entry
                    container shared-entry {
                        description "Enter the shared-entry context";

                        ///nokia-conf/configure/filter/ip-filter/subscriber-mgmt/shared-entry/filter-rule
                        container filter-rule {
                            description "Enter the filter-rule context";

                            ///nokia-conf/configure/filter/ip-filter/subscriber-mgmt/shared-entry/filter-rule/range
                            container range {
                                presence "Enable the range context";
                                description "Enable the range context";

                                ///nokia-conf/configure/filter/ip-filter/subscriber-mgmt/shared-entry/filter-rule/range/start
                                leaf start {
                                    type types-filter:entry-id;
                                    mandatory true;
                                    description "Lower bound of range for inserting shared host rules";
                                }

                                ///nokia-conf/configure/filter/ip-filter/subscriber-mgmt/shared-entry/filter-rule/range/end
                                leaf end {
                                    type types-filter:entry-id;
                                    mandatory true;
                                    description "Upper bound of range for inserting shared host rules";
                                }

                            } // container range

                        } // container filter-rule

                        ///nokia-conf/configure/filter/ip-filter/subscriber-mgmt/shared-entry/pcc-rule
                        container pcc-rule {
                            description "Enter the pcc-rule context";

                            ///nokia-conf/configure/filter/ip-filter/subscriber-mgmt/shared-entry/pcc-rule/range
                            container range {
                                presence "Enable the range context";
                                description "Enable the range context";

                                ///nokia-conf/configure/filter/ip-filter/subscriber-mgmt/shared-entry/pcc-rule/range/start
                                leaf start {
                                    type types-filter:entry-id;
                                    mandatory true;
                                    description "Lower bound of the range for PCC rule filter entries";
                                }

                                ///nokia-conf/configure/filter/ip-filter/subscriber-mgmt/shared-entry/pcc-rule/range/end
                                leaf end {
                                    type types-filter:entry-id;
                                    mandatory true;
                                    description "Upper bound of the range for PCC rule filter entries";
                                }

                            } // container range

                        } // container pcc-rule

                        ///nokia-conf/configure/filter/ip-filter/subscriber-mgmt/shared-entry/watermark
                        container watermark {
                            presence "Enable the watermark context";
                            description "Enable the watermark context";

                            ///nokia-conf/configure/filter/ip-filter/subscriber-mgmt/shared-entry/watermark/low
                            leaf low {
                                type int32 {
                                    range "0..7999";
                                }
                                mandatory true;
                                description "Limit of RADIUS or Diameter shared filters before clearing high watermark notification";
                            }

                            ///nokia-conf/configure/filter/ip-filter/subscriber-mgmt/shared-entry/watermark/high
                            leaf high {
                                type int32 {
                                    range "1..8000";
                                }
                                mandatory true;
                                description "Limit of RADIUS shared filters before generating high watermark notification";
                            }

                        } // container watermark

                    } // container shared-entry

                } // container subscriber-mgmt

                ///nokia-conf/configure/filter/ip-filter/entry
                list entry {
                    key "entry-id";
                    description "Enter the entry list instance";

                    ///nokia-conf/configure/filter/ip-filter/entry/entry-id
                    leaf entry-id {
                        type types-filter:entry-id;
                        description "ID for a match criteria and the corresponding action";
                    }

                    ///nokia-conf/configure/filter/ip-filter/entry/description
                    leaf description {
                        type types-sros:description;
                        description "Text description";
                    }

                    ///nokia-conf/configure/filter/ip-filter/entry/pbr-down-action-override
                    leaf pbr-down-action-override {
                        type types-filter:filter-pbr-down-action-ovr;
                        description "Action when PBR or PBF target for this entry is not available";
                    }

                    ///nokia-conf/configure/filter/ip-filter/entry/sticky-dest
                    leaf sticky-dest {
                        type types-filter:filter-sticky-dest;
                        units "seconds";
                        description "Time before action with available PBR or PBF destination and highest priority";
                    }

                    ///nokia-conf/configure/filter/ip-filter/entry/log
                    leaf log {
                        type leafref {
                            path "../../../log/log-id";
                        }
                        description "Log that is used for packets matching this entry";
                    }

                    ///nokia-conf/configure/filter/ip-filter/entry/collect-stats
                    leaf collect-stats {
                        type boolean;
                        default "false";
                        description "Enable statistics collection for an entry";
                    }

                    ///nokia-conf/configure/filter/ip-filter/entry/egress-pbr
                    leaf egress-pbr {
                        type types-filter:filter-egress-pbr;
                        sros-ext:immutable;
                        description "PBR that has an effect when this filter is applied on egress";
                    }

                    ///nokia-conf/configure/filter/ip-filter/entry/filter-sample
                    leaf filter-sample {
                        type boolean;
                        default "false";
                        description "Sample matching traffic if IP interface is set to cflowd ACL mode";
                    }

                    ///nokia-conf/configure/filter/ip-filter/entry/interface-sample
                    leaf interface-sample {
                        type boolean;
                        default "true";
                        description "Sample matching traffic if IP interface is set to cflowd interface mode";
                    }

                    ///nokia-conf/configure/filter/ip-filter/entry/sample-profile
                    leaf sample-profile {
                        type leafref {
                            path "../../../../cflowd/sample-profile/profile-id";
                        }
                        description "Cflowd sample profile ID to match packets";
                    }

                    ///nokia-conf/configure/filter/ip-filter/entry/apply-groups
                    leaf-list apply-groups {
                        type leafref {
                            path "../../../../groups/group/name";
                        }
                        max-elements 8;
                        ordered-by user;
                        description "Apply a configuration group at this level";
                    }

                    ///nokia-conf/configure/filter/ip-filter/entry/apply-groups-exclude
                    leaf-list apply-groups-exclude {
                        type leafref {
                            path "../../../../groups/group/name";
                        }
                        max-elements 8;
                        ordered-by user;
                        description "Exclude a configuration group at this level";
                    }

                    ///nokia-conf/configure/filter/ip-filter/entry/match
                    container match {
                        description "Enter the match context";

                        ///nokia-conf/configure/filter/ip-filter/entry/match/dscp
                        leaf dscp {
                            type types-qos:dscp-name;
                            description "DSCP used as an IP filter match criterion";
                        }

                        ///nokia-conf/configure/filter/ip-filter/entry/match/fragment
                        leaf fragment {
                            type enumeration {
                                enum false                          { value 2; }
                                enum true                           { value 3; }
                                enum first-only                     { value 4; }
                                enum non-first-only                 { value 5; }
                            }
                            description "Match criterion for fragmented packets";
                        }

                        ///nokia-conf/configure/filter/ip-filter/entry/match/multiple-option
                        leaf multiple-option {
                            type boolean;
                            description "Match based on presence of multiple options in header";
                        }

                        ///nokia-conf/configure/filter/ip-filter/entry/match/option-present
                        leaf option-present {
                            type boolean;
                            description "Match on the presence of any IP option in the packet";
                        }

                        ///nokia-conf/configure/filter/ip-filter/entry/match/src-route-option
                        leaf src-route-option {
                            type boolean;
                            description "Match based on presence of source route option";
                        }

                        ///nokia-conf/configure/filter/ip-filter/entry/match/destination-class
                        leaf destination-class {
                            type types-sros:class-index;
                            description "Destination class as a match criterion";
                        }

                        ///nokia-conf/configure/filter/ip-filter/entry/match/match-protocol-choice
                        choice match-protocol-choice {
                            ///nokia-conf/configure/filter/ip-filter/entry/match/match-protocol-choice/protocol
                            case protocol {

                                ///nokia-conf/configure/filter/ip-filter/entry/match/match-protocol-choice/protocol/protocol
                                leaf protocol {
                                    type types-sros:match-ip-protocol;
                                    description "IP protocol identifier as a match criterion";
                                }

                            }
                            ///nokia-conf/configure/filter/ip-filter/entry/match/match-protocol-choice/protocol-list
                            case protocol-list {

                                ///nokia-conf/configure/filter/ip-filter/entry/match/match-protocol-choice/protocol-list/protocol-list
                                leaf protocol-list {
                                    type leafref {
                                        path "../../../../match-list/protocol-list/protocol-list-name";
                                    }
                                    description "Name of the protocol list as a match criterion";
                                }

                            }
                        }
                        ///nokia-conf/configure/filter/ip-filter/entry/match/ip-selector
                        choice ip-selector {
                            ///nokia-conf/configure/filter/ip-filter/entry/match/ip-selector/src-dst-ip
                            case src-dst-ip {

                                ///nokia-conf/configure/filter/ip-filter/entry/match/ip-selector/src-dst-ip/src-ip
                                container src-ip {
                                    description "Enter the src-ip context";

                                    ///nokia-conf/configure/filter/ip-filter/entry/match/ip-selector/src-dst-ip/src-ip/match-address-choice
                                    choice match-address-choice {
                                        ///nokia-conf/configure/filter/ip-filter/entry/match/ip-selector/src-dst-ip/src-ip/match-address-choice/address-and-prefix-or-mask
                                        case address-and-prefix-or-mask {

                                            ///nokia-conf/configure/filter/ip-filter/entry/match/ip-selector/src-dst-ip/src-ip/match-address-choice/address-and-prefix-or-mask/address
                                            leaf address {
                                                type union {
                                                    type types-sros:ipv4-prefix-with-host-bits;
                                                    type types-sros:ipv4-address;
                                                }
                                                description "IPv4 address used as the match criterion";
                                            }

                                            ///nokia-conf/configure/filter/ip-filter/entry/match/ip-selector/src-dst-ip/src-ip/match-address-choice/address-and-prefix-or-mask/mask
                                            leaf mask {
                                                type types-sros:ipv4-address;
                                                description "IPv4 address mask used as the match criterion";
                                            }

                                        }
                                        ///nokia-conf/configure/filter/ip-filter/entry/match/ip-selector/src-dst-ip/src-ip/match-address-choice/ip-prefix-list
                                        case ip-prefix-list {

                                            ///nokia-conf/configure/filter/ip-filter/entry/match/ip-selector/src-dst-ip/src-ip/match-address-choice/ip-prefix-list/ip-prefix-list
                                            leaf ip-prefix-list {
                                                type leafref {
                                                    path "../../../../../match-list/ip-prefix-list/prefix-list-name";
                                                }
                                                description "IP4 address prefix list used as match criterion";
                                            }

                                        }
                                    }
                                } // container src-ip

                                ///nokia-conf/configure/filter/ip-filter/entry/match/ip-selector/src-dst-ip/dst-ip
                                container dst-ip {
                                    description "Enter the dst-ip context";

                                    ///nokia-conf/configure/filter/ip-filter/entry/match/ip-selector/src-dst-ip/dst-ip/match-address-choice
                                    choice match-address-choice {
                                        ///nokia-conf/configure/filter/ip-filter/entry/match/ip-selector/src-dst-ip/dst-ip/match-address-choice/address-and-prefix-or-mask
                                        case address-and-prefix-or-mask {

                                            ///nokia-conf/configure/filter/ip-filter/entry/match/ip-selector/src-dst-ip/dst-ip/match-address-choice/address-and-prefix-or-mask/address
                                            leaf address {
                                                type union {
                                                    type types-sros:ipv4-prefix-with-host-bits;
                                                    type types-sros:ipv4-address;
                                                }
                                                description "IPv4 address used as the match criterion";
                                            }

                                            ///nokia-conf/configure/filter/ip-filter/entry/match/ip-selector/src-dst-ip/dst-ip/match-address-choice/address-and-prefix-or-mask/mask
                                            leaf mask {
                                                type types-sros:ipv4-address;
                                                description "IPv4 address mask used as the match criterion";
                                            }

                                        }
                                        ///nokia-conf/configure/filter/ip-filter/entry/match/ip-selector/src-dst-ip/dst-ip/match-address-choice/ip-prefix-list
                                        case ip-prefix-list {

                                            ///nokia-conf/configure/filter/ip-filter/entry/match/ip-selector/src-dst-ip/dst-ip/match-address-choice/ip-prefix-list/ip-prefix-list
                                            leaf ip-prefix-list {
                                                type leafref {
                                                    path "../../../../../match-list/ip-prefix-list/prefix-list-name";
                                                }
                                                description "IP4 address prefix list used as match criterion";
                                            }

                                        }
                                    }
                                } // container dst-ip

                            }
                            ///nokia-conf/configure/filter/ip-filter/entry/match/ip-selector/ip
                            case ip {

                                ///nokia-conf/configure/filter/ip-filter/entry/match/ip-selector/ip/ip
                                container ip {
                                    description "Enter the ip context";

                                    ///nokia-conf/configure/filter/ip-filter/entry/match/ip-selector/ip/ip/match-address-choice
                                    choice match-address-choice {
                                        ///nokia-conf/configure/filter/ip-filter/entry/match/ip-selector/ip/ip/match-address-choice/address-and-prefix-or-mask
                                        case address-and-prefix-or-mask {

                                            ///nokia-conf/configure/filter/ip-filter/entry/match/ip-selector/ip/ip/match-address-choice/address-and-prefix-or-mask/address
                                            leaf address {
                                                type union {
                                                    type types-sros:ipv4-prefix-with-host-bits;
                                                    type types-sros:ipv4-address;
                                                }
                                                description "IPv4 address used as the match criterion";
                                            }

                                            ///nokia-conf/configure/filter/ip-filter/entry/match/ip-selector/ip/ip/match-address-choice/address-and-prefix-or-mask/mask
                                            leaf mask {
                                                type types-sros:ipv4-address;
                                                description "IPv4 address mask used as the match criterion";
                                            }

                                        }
                                        ///nokia-conf/configure/filter/ip-filter/entry/match/ip-selector/ip/ip/match-address-choice/ip-prefix-list
                                        case ip-prefix-list {

                                            ///nokia-conf/configure/filter/ip-filter/entry/match/ip-selector/ip/ip/match-address-choice/ip-prefix-list/ip-prefix-list
                                            leaf ip-prefix-list {
                                                type leafref {
                                                    path "../../../../../match-list/ip-prefix-list/prefix-list-name";
                                                }
                                                description "IP4 address prefix list used as match criterion";
                                            }

                                        }
                                    }
                                } // container ip

                            }
                        }
                        ///nokia-conf/configure/filter/ip-filter/entry/match/port-selector
                        choice port-selector {
                            ///nokia-conf/configure/filter/ip-filter/entry/match/port-selector/src-dst-port
                            case src-dst-port {

                                ///nokia-conf/configure/filter/ip-filter/entry/match/port-selector/src-dst-port/src-port
                                container src-port {
                                    description "Enter the src-port context";

                                    ///nokia-conf/configure/filter/ip-filter/entry/match/port-selector/src-dst-port/src-port/port
                                    choice port {
                                        ///nokia-conf/configure/filter/ip-filter/entry/match/port-selector/src-dst-port/src-port/port/eq
                                        case eq {

                                            ///nokia-conf/configure/filter/ip-filter/entry/match/port-selector/src-dst-port/src-port/port/eq/eq
                                            leaf eq {
                                                type uint16 {
                                                    range "0..65535";
                                                }
                                                description "Exact match criterion for the port number";
                                            }

                                        }
                                        ///nokia-conf/configure/filter/ip-filter/entry/match/port-selector/src-dst-port/src-port/port/lt
                                        case lt {

                                            ///nokia-conf/configure/filter/ip-filter/entry/match/port-selector/src-dst-port/src-port/port/lt/lt
                                            leaf lt {
                                                type uint16 {
                                                    range "1..65535";
                                                }
                                                description "Less than match criterion for the port number";
                                            }

                                        }
                                        ///nokia-conf/configure/filter/ip-filter/entry/match/port-selector/src-dst-port/src-port/port/gt
                                        case gt {

                                            ///nokia-conf/configure/filter/ip-filter/entry/match/port-selector/src-dst-port/src-port/port/gt/gt
                                            leaf gt {
                                                type uint16 {
                                                    range "0..65534";
                                                }
                                                description "Greater than match criterion for the port number";
                                            }

                                        }
                                        ///nokia-conf/configure/filter/ip-filter/entry/match/port-selector/src-dst-port/src-port/port/range
                                        case range {

                                            ///nokia-conf/configure/filter/ip-filter/entry/match/port-selector/src-dst-port/src-port/port/range/range
                                            container range {
                                                presence "Enable the range context";
                                                description "Enable the range context";

                                                ///nokia-conf/configure/filter/ip-filter/entry/match/port-selector/src-dst-port/src-port/port/range/range/start
                                                leaf start {
                                                    type uint16 {
                                                        range "0..65534";
                                                    }
                                                    mandatory true;
                                                    description "Lower bound of the port range as port match criterion";
                                                }

                                                ///nokia-conf/configure/filter/ip-filter/entry/match/port-selector/src-dst-port/src-port/port/range/range/end
                                                leaf end {
                                                    type uint16 {
                                                        range "1..65535";
                                                    }
                                                    mandatory true;
                                                    description "Upper bound of the port range as port match criterion";
                                                }

                                            } // container range

                                        }
                                        ///nokia-conf/configure/filter/ip-filter/entry/match/port-selector/src-dst-port/src-port/port/port-list
                                        case port-list {

                                            ///nokia-conf/configure/filter/ip-filter/entry/match/port-selector/src-dst-port/src-port/port/port-list/port-list
                                            leaf port-list {
                                                type leafref {
                                                    path "../../../../../match-list/port-list/port-list-name";
                                                }
                                                description "Name of the port list as the match criterion";
                                            }

                                        }
                                    }
                                } // container src-port

                                ///nokia-conf/configure/filter/ip-filter/entry/match/port-selector/src-dst-port/dst-port
                                container dst-port {
                                    description "Enter the dst-port context";

                                    ///nokia-conf/configure/filter/ip-filter/entry/match/port-selector/src-dst-port/dst-port/port
                                    choice port {
                                        ///nokia-conf/configure/filter/ip-filter/entry/match/port-selector/src-dst-port/dst-port/port/eq
                                        case eq {

                                            ///nokia-conf/configure/filter/ip-filter/entry/match/port-selector/src-dst-port/dst-port/port/eq/eq
                                            leaf eq {
                                                type uint16 {
                                                    range "0..65535";
                                                }
                                                description "Exact match criterion for the port number";
                                            }

                                        }
                                        ///nokia-conf/configure/filter/ip-filter/entry/match/port-selector/src-dst-port/dst-port/port/lt
                                        case lt {

                                            ///nokia-conf/configure/filter/ip-filter/entry/match/port-selector/src-dst-port/dst-port/port/lt/lt
                                            leaf lt {
                                                type uint16 {
                                                    range "1..65535";
                                                }
                                                description "Less than match criterion for the port number";
                                            }

                                        }
                                        ///nokia-conf/configure/filter/ip-filter/entry/match/port-selector/src-dst-port/dst-port/port/gt
                                        case gt {

                                            ///nokia-conf/configure/filter/ip-filter/entry/match/port-selector/src-dst-port/dst-port/port/gt/gt
                                            leaf gt {
                                                type uint16 {
                                                    range "0..65534";
                                                }
                                                description "Greater than match criterion for the port number";
                                            }

                                        }
                                        ///nokia-conf/configure/filter/ip-filter/entry/match/port-selector/src-dst-port/dst-port/port/range
                                        case range {

                                            ///nokia-conf/configure/filter/ip-filter/entry/match/port-selector/src-dst-port/dst-port/port/range/range
                                            container range {
                                                presence "Enable the range context";
                                                description "Enable the range context";

                                                ///nokia-conf/configure/filter/ip-filter/entry/match/port-selector/src-dst-port/dst-port/port/range/range/start
                                                leaf start {
                                                    type uint16 {
                                                        range "0..65534";
                                                    }
                                                    mandatory true;
                                                    description "Lower bound of the port range as port match criterion";
                                                }

                                                ///nokia-conf/configure/filter/ip-filter/entry/match/port-selector/src-dst-port/dst-port/port/range/range/end
                                                leaf end {
                                                    type uint16 {
                                                        range "1..65535";
                                                    }
                                                    mandatory true;
                                                    description "Upper bound of the port range as port match criterion";
                                                }

                                            } // container range

                                        }
                                        ///nokia-conf/configure/filter/ip-filter/entry/match/port-selector/src-dst-port/dst-port/port/port-list
                                        case port-list {

                                            ///nokia-conf/configure/filter/ip-filter/entry/match/port-selector/src-dst-port/dst-port/port/port-list/port-list
                                            leaf port-list {
                                                type leafref {
                                                    path "../../../../../match-list/port-list/port-list-name";
                                                }
                                                description "Name of the port list as the match criterion";
                                            }

                                        }
                                    }
                                } // container dst-port

                            }
                            ///nokia-conf/configure/filter/ip-filter/entry/match/port-selector/port
                            case port {

                                ///nokia-conf/configure/filter/ip-filter/entry/match/port-selector/port/port
                                container port {
                                    description "Enter the port context";

                                    ///nokia-conf/configure/filter/ip-filter/entry/match/port-selector/port/port/port
                                    choice port {
                                        ///nokia-conf/configure/filter/ip-filter/entry/match/port-selector/port/port/port/eq
                                        case eq {

                                            ///nokia-conf/configure/filter/ip-filter/entry/match/port-selector/port/port/port/eq/eq
                                            leaf eq {
                                                type uint16 {
                                                    range "0..65535";
                                                }
                                                description "Exact match criterion for the port number";
                                            }

                                        }
                                        ///nokia-conf/configure/filter/ip-filter/entry/match/port-selector/port/port/port/lt
                                        case lt {

                                            ///nokia-conf/configure/filter/ip-filter/entry/match/port-selector/port/port/port/lt/lt
                                            leaf lt {
                                                type uint16 {
                                                    range "1..65535";
                                                }
                                                description "Less than match criterion for the port number";
                                            }

                                        }
                                        ///nokia-conf/configure/filter/ip-filter/entry/match/port-selector/port/port/port/gt
                                        case gt {

                                            ///nokia-conf/configure/filter/ip-filter/entry/match/port-selector/port/port/port/gt/gt
                                            leaf gt {
                                                type uint16 {
                                                    range "0..65534";
                                                }
                                                description "Greater than match criterion for the port number";
                                            }

                                        }
                                        ///nokia-conf/configure/filter/ip-filter/entry/match/port-selector/port/port/port/range
                                        case range {

                                            ///nokia-conf/configure/filter/ip-filter/entry/match/port-selector/port/port/port/range/range
                                            container range {
                                                presence "Enable the range context";
                                                description "Enable the range context";

                                                ///nokia-conf/configure/filter/ip-filter/entry/match/port-selector/port/port/port/range/range/start
                                                leaf start {
                                                    type uint16 {
                                                        range "0..65534";
                                                    }
                                                    mandatory true;
                                                    description "Lower bound of the port range as port match criterion";
                                                }

                                                ///nokia-conf/configure/filter/ip-filter/entry/match/port-selector/port/port/port/range/range/end
                                                leaf end {
                                                    type uint16 {
                                                        range "1..65535";
                                                    }
                                                    mandatory true;
                                                    description "Upper bound of the port range as port match criterion";
                                                }

                                            } // container range

                                        }
                                        ///nokia-conf/configure/filter/ip-filter/entry/match/port-selector/port/port/port/port-list
                                        case port-list {

                                            ///nokia-conf/configure/filter/ip-filter/entry/match/port-selector/port/port/port/port-list/port-list
                                            leaf port-list {
                                                type leafref {
                                                    path "../../../../../match-list/port-list/port-list-name";
                                                }
                                                description "Name of the port list as the match criterion";
                                            }

                                        }
                                    }
                                } // container port

                            }
                        }
                        ///nokia-conf/configure/filter/ip-filter/entry/match/match-tcp-flags
                        choice match-tcp-flags {
                            ///nokia-conf/configure/filter/ip-filter/entry/match/match-tcp-flags/tcp-established
                            case tcp-established {

                                ///nokia-conf/configure/filter/ip-filter/entry/match/match-tcp-flags/tcp-established/tcp-established
                                leaf tcp-established {
                                    type empty;
                                    description "Match packets containing the TCP flag as ACK or RST";
                                }

                            }
                            ///nokia-conf/configure/filter/ip-filter/entry/match/match-tcp-flags/tcp-flags
                            case tcp-flags {

                                ///nokia-conf/configure/filter/ip-filter/entry/match/match-tcp-flags/tcp-flags/tcp-flags
                                container tcp-flags {
                                    description "Enter the tcp-flags context";

                                    ///nokia-conf/configure/filter/ip-filter/entry/match/match-tcp-flags/tcp-flags/tcp-flags/ack
                                    leaf ack {
                                        type boolean;
                                        description "Match TCP ACK as per value of the ACK TCP flag bit";
                                    }

                                    ///nokia-conf/configure/filter/ip-filter/entry/match/match-tcp-flags/tcp-flags/tcp-flags/syn
                                    leaf syn {
                                        type boolean;
                                        description "Match TCP SYN as per value of the SYN TCP flag bit";
                                    }

                                    ///nokia-conf/configure/filter/ip-filter/entry/match/match-tcp-flags/tcp-flags/tcp-flags/fin
                                    leaf fin {
                                        type boolean;
                                        description "Match TCP FIN as per value of the FIN TCP flag bit";
                                    }

                                    ///nokia-conf/configure/filter/ip-filter/entry/match/match-tcp-flags/tcp-flags/tcp-flags/rst
                                    leaf rst {
                                        type boolean;
                                        description "Match TCP RST as per value of the RST TCP flag bit";
                                    }

                                    ///nokia-conf/configure/filter/ip-filter/entry/match/match-tcp-flags/tcp-flags/tcp-flags/psh
                                    leaf psh {
                                        type boolean;
                                        description "Match TCP PSH as per value of the PSH TCP flag bit";
                                    }

                                    ///nokia-conf/configure/filter/ip-filter/entry/match/match-tcp-flags/tcp-flags/tcp-flags/urg
                                    leaf urg {
                                        type boolean;
                                        description "Match TCP URG as per value of the URG TCP flag bit";
                                    }

                                    ///nokia-conf/configure/filter/ip-filter/entry/match/match-tcp-flags/tcp-flags/tcp-flags/ece
                                    leaf ece {
                                        type boolean;
                                        description "Match TCP ECE as per value of the ECE TCP flag bit";
                                    }

                                    ///nokia-conf/configure/filter/ip-filter/entry/match/match-tcp-flags/tcp-flags/tcp-flags/cwr
                                    leaf cwr {
                                        type boolean;
                                        description "Match TCP CWR as per value of the CWR TCP flag bit";
                                    }

                                    ///nokia-conf/configure/filter/ip-filter/entry/match/match-tcp-flags/tcp-flags/tcp-flags/ns
                                    leaf ns {
                                        type boolean;
                                        description "Match TCP NS as per value of the NS TCP flag bit";
                                    }

                                } // container tcp-flags

                            }
                        }
                        ///nokia-conf/configure/filter/ip-filter/entry/match/ip-option
                        container ip-option {
                            presence "Enable the ip-option context";
                            description "Enable the ip-option context";

                            ///nokia-conf/configure/filter/ip-filter/entry/match/ip-option/type
                            leaf type {
                                type types-filter:filter-match-ip-option;
                                mandatory true;
                                description "Specific IP option to match";
                            }

                            ///nokia-conf/configure/filter/ip-filter/entry/match/ip-option/mask
                            leaf mask {
                                type types-filter:filter-match-ip-option {
                                    range "1..255";
                                }
                                default "255";
                                description "Mask that is ANDed with ip-option value in the packet header";
                            }

                        } // container ip-option

                        ///nokia-conf/configure/filter/ip-filter/entry/match/src-mac
                        container src-mac {
                            presence "Enable the src-mac context";
                            description "Enable the src-mac context";

                            ///nokia-conf/configure/filter/ip-filter/entry/match/src-mac/address
                            leaf address {
                                type yang:mac-address;
                                mandatory true;
                                description "MAC address used as the match criterion";
                            }

                            ///nokia-conf/configure/filter/ip-filter/entry/match/src-mac/mask
                            leaf mask {
                                type yang:mac-address;
                                default "ff:ff:ff:ff:ff:ff";
                                description "MAC address mask as the match criterion";
                            }

                        } // container src-mac

                        ///nokia-conf/configure/filter/ip-filter/entry/match/icmp
                        container icmp {
                            description "Enter the icmp context";

                            ///nokia-conf/configure/filter/ip-filter/entry/match/icmp/icmp-code
                            choice icmp-code {
                                ///nokia-conf/configure/filter/ip-filter/entry/match/icmp/icmp-code/code
                                case code {

                                    ///nokia-conf/configure/filter/ip-filter/entry/match/icmp/icmp-code/code/code
                                    leaf code {
                                        type types-filter:ipv4-match-icmp-codes;
                                        description "ICMP code value to match";
                                    }

                                }
                            }
                            ///nokia-conf/configure/filter/ip-filter/entry/match/icmp/icmp-type
                            choice icmp-type {
                                ///nokia-conf/configure/filter/ip-filter/entry/match/icmp/icmp-type/type
                                case type {

                                    ///nokia-conf/configure/filter/ip-filter/entry/match/icmp/icmp-type/type/type
                                    leaf type {
                                        type types-filter:ipv4-match-icmp-types;
                                        description "ICMP type value to match";
                                    }

                                }
                            }
                        } // container icmp

                        ///nokia-conf/configure/filter/ip-filter/entry/match/packet-length
                        container packet-length {
                            presence "Enable the packet-length context";
                            description "Enable the packet-length context";

                            ///nokia-conf/configure/filter/ip-filter/entry/match/packet-length/packet-length
                            choice packet-length {
                                mandatory true;
                                ///nokia-conf/configure/filter/ip-filter/entry/match/packet-length/packet-length/eq
                                case eq {

                                    ///nokia-conf/configure/filter/ip-filter/entry/match/packet-length/packet-length/eq/eq
                                    leaf eq {
                                        type types-filter:pkt-len-or-payload-len-value;
                                        description "Exact match criterion for the length";
                                    }

                                }
                                ///nokia-conf/configure/filter/ip-filter/entry/match/packet-length/packet-length/lt
                                case lt {

                                    ///nokia-conf/configure/filter/ip-filter/entry/match/packet-length/packet-length/lt/lt
                                    leaf lt {
                                        type types-filter:pkt-len-or-payload-len-lt-value;
                                        description "Less than match criterion for the length";
                                    }

                                }
                                ///nokia-conf/configure/filter/ip-filter/entry/match/packet-length/packet-length/gt
                                case gt {

                                    ///nokia-conf/configure/filter/ip-filter/entry/match/packet-length/packet-length/gt/gt
                                    leaf gt {
                                        type types-filter:pkt-len-or-payload-len-gt-value;
                                        description "Greater than match criterion for the length";
                                    }

                                }
                                ///nokia-conf/configure/filter/ip-filter/entry/match/packet-length/packet-length/range
                                case range {

                                    ///nokia-conf/configure/filter/ip-filter/entry/match/packet-length/packet-length/range/range
                                    container range {
                                        presence "Enable the range context";
                                        description "Enable the range context";

                                        ///nokia-conf/configure/filter/ip-filter/entry/match/packet-length/packet-length/range/range/start
                                        leaf start {
                                            type types-filter:pkt-len-or-payload-len-gt-value;
                                            mandatory true;
                                            description "Lower bound of the length range";
                                        }

                                        ///nokia-conf/configure/filter/ip-filter/entry/match/packet-length/packet-length/range/range/end
                                        leaf end {
                                            type types-filter:pkt-len-or-payload-len-lt-value;
                                            mandatory true;
                                            description "Upper bound of the length range";
                                        }

                                    } // container range

                                }
                            }
                        } // container packet-length

                        ///nokia-conf/configure/filter/ip-filter/entry/match/ttl
                        container ttl {
                            presence "Enable the ttl context";
                            description "Enable the ttl context";

                            ///nokia-conf/configure/filter/ip-filter/entry/match/ttl/ttl
                            choice ttl {
                                mandatory true;
                                ///nokia-conf/configure/filter/ip-filter/entry/match/ttl/ttl/eq
                                case eq {

                                    ///nokia-conf/configure/filter/ip-filter/entry/match/ttl/ttl/eq/eq
                                    leaf eq {
                                        type types-filter:ttl-or-hop-limit-value;
                                        description "Equal to condition match value";
                                    }

                                }
                                ///nokia-conf/configure/filter/ip-filter/entry/match/ttl/ttl/lt
                                case lt {

                                    ///nokia-conf/configure/filter/ip-filter/entry/match/ttl/ttl/lt/lt
                                    leaf lt {
                                        type types-filter:ttl-or-hop-limit-lt-value;
                                        description "Less than condition match value";
                                    }

                                }
                                ///nokia-conf/configure/filter/ip-filter/entry/match/ttl/ttl/gt
                                case gt {

                                    ///nokia-conf/configure/filter/ip-filter/entry/match/ttl/ttl/gt/gt
                                    leaf gt {
                                        type types-filter:ttl-or-hop-limit-gt-value;
                                        description "Greater than condition match value";
                                    }

                                }
                                ///nokia-conf/configure/filter/ip-filter/entry/match/ttl/ttl/range
                                case range {

                                    ///nokia-conf/configure/filter/ip-filter/entry/match/ttl/ttl/range/range
                                    container range {
                                        presence "Enable the range context";
                                        description "Enable the range context";

                                        ///nokia-conf/configure/filter/ip-filter/entry/match/ttl/ttl/range/range/start
                                        leaf start {
                                            type types-filter:ttl-or-hop-limit-gt-value;
                                            mandatory true;
                                            description "Lower bound of the range";
                                        }

                                        ///nokia-conf/configure/filter/ip-filter/entry/match/ttl/ttl/range/range/end
                                        leaf end {
                                            type types-filter:ttl-or-hop-limit-lt-value;
                                            mandatory true;
                                            description "Upper bound of the range";
                                        }

                                    } // container range

                                }
                            }
                        } // container ttl

                    } // container match

                    ///nokia-conf/configure/filter/ip-filter/entry/action
                    container action {
                        presence "Enable the action context";
                        description "Enable the action context";

                        ///nokia-conf/configure/filter/ip-filter/entry/action/fc
                        leaf fc {
                            type types-sros:fc-name;
                            description "Class name to be forwarded for matching packets";
                        }

                        ///nokia-conf/configure/filter/ip-filter/entry/action/l2-aware-nat-bypass
                        leaf l2-aware-nat-bypass {
                            type boolean;
                            default "false";
                            description "Divert traffic from an L2-Aware NAT subscriber";
                        }

                        ///nokia-conf/configure/filter/ip-filter/entry/action/apply-groups
                        leaf-list apply-groups {
                            type leafref {
                                path "../../../../../groups/group/name";
                            }
                            max-elements 8;
                            ordered-by user;
                            description "Apply a configuration group at this level";
                        }

                        ///nokia-conf/configure/filter/ip-filter/entry/action/apply-groups-exclude
                        leaf-list apply-groups-exclude {
                            type leafref {
                                path "../../../../../groups/group/name";
                            }
                            max-elements 8;
                            ordered-by user;
                            description "Exclude a configuration group at this level";
                        }

                        ///nokia-conf/configure/filter/ip-filter/entry/action/action
                        choice action {
                            mandatory true;
                            ///nokia-conf/configure/filter/ip-filter/entry/action/action/ignore-match
                            case ignore-match {

                                ///nokia-conf/configure/filter/ip-filter/entry/action/action/ignore-match/ignore-match
                                leaf ignore-match {
                                    type empty;
                                    description "Ignore match criteria for the entry";
                                }

                            }
                            ///nokia-conf/configure/filter/ip-filter/entry/action/action/drop
                            case drop {

                                ///nokia-conf/configure/filter/ip-filter/entry/action/action/drop/drop
                                leaf drop {
                                    type empty;
                                    description "Drop a packet matching this entry";
                                }

                            }
                            ///nokia-conf/configure/filter/ip-filter/entry/action/action/forward
                            case forward {

                                ///nokia-conf/configure/filter/ip-filter/entry/action/action/forward/forward
                                container forward {
                                    description "Enter the forward context";

                                    ///nokia-conf/configure/filter/ip-filter/entry/action/action/forward/forward/forward-action
                                    choice forward-action {
                                        ///nokia-conf/configure/filter/ip-filter/entry/action/action/forward/forward/forward-action/bonding-connection
                                        case bonding-connection {

                                            ///nokia-conf/configure/filter/ip-filter/entry/action/action/forward/forward/forward-action/bonding-connection/bonding-connection
                                            leaf bonding-connection {
                                                type types-submgt:bonding-connection-index;
                                                description "Connection ID over which packet is forwarded";
                                            }

                                        }
                                        ///nokia-conf/configure/filter/ip-filter/entry/action/action/forward/forward/forward-action/esi-l2
                                        case esi-l2 {

                                            ///nokia-conf/configure/filter/ip-filter/entry/action/action/forward/forward/forward-action/esi-l2/esi-l2
                                            container esi-l2 {
                                                presence "Enable the esi-l2 context";
                                                description "Enable the esi-l2 context";

                                                ///nokia-conf/configure/filter/ip-filter/entry/action/action/forward/forward/forward-action/esi-l2/esi-l2/esi-value
                                                leaf esi-value {
                                                    type types-services:ethernet-segment-id {
                                                        pattern "(0x[0-9a-fA-F]{20})|([0-9a-fA-F]{2}(:[0-9a-fA-F]{2}){9})|([0-9a-fA-F]{2}(-[0-9a-fA-F]{2}){9})";
                                                    }
                                                    mandatory true;
                                                    description "ESI of the first ESI-identified appliance";
                                                }

                                                ///nokia-conf/configure/filter/ip-filter/entry/action/action/forward/forward/forward-action/esi-l2/esi-l2/vpls
                                                leaf vpls {
                                                    type leafref {
                                                        path "../../../../../../../service/vpls/service-name";
                                                    }
                                                    mandatory true;
                                                    description "VPLS service name";
                                                }

                                            } // container esi-l2

                                        }
                                        ///nokia-conf/configure/filter/ip-filter/entry/action/action/forward/forward/forward-action/esi-l3
                                        case esi-l3 {

                                            ///nokia-conf/configure/filter/ip-filter/entry/action/action/forward/forward/forward-action/esi-l3/esi-l3
                                            container esi-l3 {
                                                presence "Enable the esi-l3 context";
                                                description "Enable the esi-l3 context";

                                                ///nokia-conf/configure/filter/ip-filter/entry/action/action/forward/forward/forward-action/esi-l3/esi-l3/sf-ip
                                                leaf sf-ip {
                                                    type types-sros:ipv4-address;
                                                    sros-ext:immutable;
                                                    mandatory true;
                                                    description "IP address of the service function to forward traffic";
                                                }

                                                ///nokia-conf/configure/filter/ip-filter/entry/action/action/forward/forward/forward-action/esi-l3/esi-l3/esi-value
                                                leaf esi-value {
                                                    type types-services:ethernet-segment-id {
                                                        pattern "(0x[0-9a-fA-F]{20})|([0-9a-fA-F]{2}(:[0-9a-fA-F]{2}){9})|([0-9a-fA-F]{2}(-[0-9a-fA-F]{2}){9})";
                                                    }
                                                    sros-ext:immutable;
                                                    mandatory true;
                                                    description "ESI of the first ESI-identified appliance";
                                                }

                                                ///nokia-conf/configure/filter/ip-filter/entry/action/action/forward/forward/forward-action/esi-l3/esi-l3/vas-interface
                                                leaf vas-interface {
                                                    type leafref {
                                                        path "../../../../../../../service/vprn[service-name=current()/../vprn]/interface/interface-name";
                                                    }
                                                    sros-ext:immutable;
                                                    mandatory true;
                                                    description "Egress R-VPLS IP interface name";
                                                }

                                                ///nokia-conf/configure/filter/ip-filter/entry/action/action/forward/forward/forward-action/esi-l3/esi-l3/vprn
                                                leaf vprn {
                                                    type leafref {
                                                        path "../../../../../../../service/vprn/service-name";
                                                    }
                                                    sros-ext:immutable;
                                                    mandatory true;
                                                    description "VPRN service name";
                                                }

                                            } // container esi-l3

                                        }
                                        ///nokia-conf/configure/filter/ip-filter/entry/action/action/forward/forward/forward-action/router
                                        case router {

                                            ///nokia-conf/configure/filter/ip-filter/entry/action/action/forward/forward/forward-action/router/router-instance
                                            leaf router-instance {
                                                type string;
                                                sros-ext:immutable;
                                                description "Router name or VPRN service name";
                                            }

                                        }
                                        ///nokia-conf/configure/filter/ip-filter/entry/action/action/forward/forward/forward-action/next-hop
                                        case next-hop {

                                            ///nokia-conf/configure/filter/ip-filter/entry/action/action/forward/forward/forward-action/next-hop/next-hop
                                            container next-hop {
                                                presence "Enable the next-hop context";
                                                description "Enable the next-hop context";

                                                ///nokia-conf/configure/filter/ip-filter/entry/action/action/forward/forward/forward-action/next-hop/next-hop/next-hop
                                                choice next-hop {
                                                    mandatory true;
                                                    ///nokia-conf/configure/filter/ip-filter/entry/action/action/forward/forward/forward-action/next-hop/next-hop/next-hop/nh-ip
                                                    case nh-ip {

                                                        ///nokia-conf/configure/filter/ip-filter/entry/action/action/forward/forward/forward-action/next-hop/next-hop/next-hop/nh-ip/nh-ip
                                                        container nh-ip {
                                                            presence "Enable the nh-ip context";
                                                            description "Enable the nh-ip context";

                                                            ///nokia-conf/configure/filter/ip-filter/entry/action/action/forward/forward/forward-action/next-hop/next-hop/next-hop/nh-ip/nh-ip/indirect
                                                            leaf indirect {
                                                                type boolean;
                                                                default "false";
                                                                description "Allow next hop to be indirectly reachable";
                                                            }

                                                            ///nokia-conf/configure/filter/ip-filter/entry/action/action/forward/forward/forward-action/next-hop/next-hop/next-hop/nh-ip/nh-ip/address
                                                            leaf address {
                                                                type types-sros:ipv4-address;
                                                                sros-ext:immutable;
                                                                mandatory true;
                                                                description "IPv4 address of next hop to forward matching packets";
                                                            }

                                                        } // container nh-ip

                                                    }
                                                    ///nokia-conf/configure/filter/ip-filter/entry/action/action/forward/forward/forward-action/next-hop/next-hop/next-hop/nh-interface
                                                    case nh-interface {

                                                        ///nokia-conf/configure/filter/ip-filter/entry/action/action/forward/forward/forward-action/next-hop/next-hop/next-hop/nh-interface/interface-name
                                                        leaf interface-name {
                                                            type types-sros:named-item;
                                                            description "IP interface name that forwards matching packets";
                                                        }

                                                    }
                                                    ///nokia-conf/configure/filter/ip-filter/entry/action/action/forward/forward/forward-action/next-hop/next-hop/next-hop/nh-ip-vrf
                                                    case nh-ip-vrf {

                                                        ///nokia-conf/configure/filter/ip-filter/entry/action/action/forward/forward/forward-action/next-hop/next-hop/next-hop/nh-ip-vrf/nh-ip-vrf
                                                        container nh-ip-vrf {
                                                            presence "Enable the nh-ip-vrf context";
                                                            description "Enable the nh-ip-vrf context";

                                                            ///nokia-conf/configure/filter/ip-filter/entry/action/action/forward/forward/forward-action/next-hop/next-hop/next-hop/nh-ip-vrf/nh-ip-vrf/indirect
                                                            leaf indirect {
                                                                type boolean;
                                                                default "false";
                                                                description "Allow next hop to be indirectly reachable";
                                                            }

                                                            ///nokia-conf/configure/filter/ip-filter/entry/action/action/forward/forward/forward-action/next-hop/next-hop/next-hop/nh-ip-vrf/nh-ip-vrf/router-instance
                                                            leaf router-instance {
                                                                type string;
                                                                sros-ext:immutable;
                                                                mandatory true;
                                                                description "Routing context for route lookup for forwarding packets";
                                                            }

                                                            ///nokia-conf/configure/filter/ip-filter/entry/action/action/forward/forward/forward-action/next-hop/next-hop/next-hop/nh-ip-vrf/nh-ip-vrf/address
                                                            leaf address {
                                                                type types-sros:ipv4-address;
                                                                sros-ext:immutable;
                                                                mandatory true;
                                                                description "IPv4 address of next hop to forward matching packets";
                                                            }

                                                        } // container nh-ip-vrf

                                                    }
                                                }
                                            } // container next-hop

                                        }
                                        ///nokia-conf/configure/filter/ip-filter/entry/action/action/forward/forward/forward-action/lsp
                                        case lsp {

                                            ///nokia-conf/configure/filter/ip-filter/entry/action/action/forward/forward/forward-action/lsp/lsp
                                            leaf lsp {
                                                type types-sros:named-item-64;
                                                description "LSP that is specified to forward a packet matching this entry";
                                            }

                                        }
                                        ///nokia-conf/configure/filter/ip-filter/entry/action/action/forward/forward/forward-action/sdp
                                        case sdp {

                                            ///nokia-conf/configure/filter/ip-filter/entry/action/action/forward/forward/forward-action/sdp/sdp
                                            container sdp {
                                                presence "Enable the sdp context";
                                                description "Enable the sdp context";

                                                ///nokia-conf/configure/filter/ip-filter/entry/action/action/forward/forward/forward-action/sdp/sdp/vpls
                                                leaf vpls {
                                                    type leafref {
                                                        path "../../../../../../../service/vpls/service-name";
                                                    }
                                                    mandatory true;
                                                    description "VPLS associated with the SDP";
                                                }

                                                ///nokia-conf/configure/filter/ip-filter/entry/action/action/forward/forward/forward-action/sdp/sdp/sdp-bind-id
                                                leaf sdp-bind-id {
                                                    type types-services:sdp-bind-id;
                                                    mandatory true;
                                                    description "VPLS SDP bind ID used to forward matching packets";
                                                }

                                            } // container sdp

                                        }
                                        ///nokia-conf/configure/filter/ip-filter/entry/action/action/forward/forward/forward-action/sap
                                        case sap {

                                            ///nokia-conf/configure/filter/ip-filter/entry/action/action/forward/forward/forward-action/sap/sap
                                            container sap {
                                                presence "Enable the sap context";
                                                description "Enable the sap context";

                                                ///nokia-conf/configure/filter/ip-filter/entry/action/action/forward/forward/forward-action/sap/sap/vpls
                                                leaf vpls {
                                                    type leafref {
                                                        path "../../../../../../../service/vpls/service-name";
                                                    }
                                                    mandatory true;
                                                    description "VPLS associated with the SAP";
                                                }

                                                ///nokia-conf/configure/filter/ip-filter/entry/action/action/forward/forward/forward-action/sap/sap/sap-id
                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                        ///nokia-conf/configure/filter/ip-filter/entry/action/action/forward/forward/forward-action/redirect-policy
                                        case redirect-policy {

                                            ///nokia-conf/configure/filter/ip-filter/entry/action/action/forward/forward/forward-action/redirect-policy/redirect-policy
                                            leaf redirect-policy {
                                                type leafref {
                                                    path "../../../../../redirect-policy/redirect-policy-name";
                                                }
                                                sros-ext:immutable;
                                                description "Next hop or forward next hop router that forwards a packet that matches this entry";
                                            }

                                        }
                                        ///nokia-conf/configure/filter/ip-filter/entry/action/action/forward/forward/forward-action/vprn-target
                                        case vprn-target {

                                            ///nokia-conf/configure/filter/ip-filter/entry/action/action/forward/forward/forward-action/vprn-target/vprn-target
                                            container vprn-target {
                                                presence "Enable the vprn-target context";
                                                description "Enable the vprn-target context";

                                                ///nokia-conf/configure/filter/ip-filter/entry/action/action/forward/forward/forward-action/vprn-target/vprn-target/bgp-nh
                                                leaf bgp-nh {
                                                    type types-sros:ipv4-address {
                                                        pattern
                                                            "((([0-9]|[1-9][0-9]|1[0-9][0-9]|2[0-4][0-9]|25[0-5])\\.){3}([1-9]|[1-9][0-9]|1[0-9][0-9]|2[0-4][0-9]|25[0-5]))|
                                                                              ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                              ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                              (([1-9]|[1-9][0-9]|1[0-9][0-9]|2[0-4][0-9]|25[0-5]){1}(\\.([0-9]|[1-9][0-9]|1[0-9][0-9]|2[0-4][0-9]|25[0-5])){3})";
                                                    }
                                                    mandatory true;
                                                    description "Target BGP next hop IP address";
                                                }

                                                ///nokia-conf/configure/filter/ip-filter/entry/action/action/forward/forward/forward-action/vprn-target/vprn-target/vprn
                                                leaf vprn {
                                                    type leafref {
                                                        path "../../../../../../../service/vprn/service-name";
                                                    }
                                                    mandatory true;
                                                    description "Routing context used for route lookup";
                                                }

                                                ///nokia-conf/configure/filter/ip-filter/entry/action/action/forward/forward/forward-action/vprn-target/vprn-target/lsp
                                                leaf lsp {
                                                    type types-sros:named-item-64;
                                                    description "LSP that is specified to forward a packet matching this entry";
                                                }

                                                ///nokia-conf/configure/filter/ip-filter/entry/action/action/forward/forward/forward-action/vprn-target/vprn-target/adv-prefix
                                                leaf adv-prefix {
                                                    type types-sros:ipv4-prefix;
                                                    description "Advertised IP prefix for target destination";
                                                }

                                            } // container vprn-target

                                        }
                                        ///nokia-conf/configure/filter/ip-filter/entry/action/action/forward/forward/forward-action/gre-tunnel
                                        case gre-tunnel {

                                            ///nokia-conf/configure/filter/ip-filter/entry/action/action/forward/forward/forward-action/gre-tunnel/gre-tunnel
                                            leaf gre-tunnel {
                                                type leafref {
                                                    path "../../../../../gre-tunnel-template/gre-tunnel-template-name";
                                                }
                                                description "GRE tunnel template ID that sets the location where an encapsulated matching packet is transported";
                                            }

                                        }
                                        ///nokia-conf/configure/filter/ip-filter/entry/action/action/forward/forward/forward-action/mpls-policy
                                        case mpls-policy {

                                            ///nokia-conf/configure/filter/ip-filter/entry/action/action/forward/forward/forward-action/mpls-policy/mpls-policy
                                            container mpls-policy {
                                                presence "Enable the mpls-policy context";
                                                description "Enable the mpls-policy context";

                                                ///nokia-conf/configure/filter/ip-filter/entry/action/action/forward/forward/forward-action/mpls-policy/mpls-policy/endpoint
                                                leaf endpoint {
                                                    type types-sros:ipv4-unicast-address;
                                                    mandatory true;
                                                    description "MPLS forwarding policy endpoint IPv4 address";
                                                }

                                            } // container mpls-policy

                                        }
                                        ///nokia-conf/configure/filter/ip-filter/entry/action/action/forward/forward/forward-action/srte-policy
                                        case srte-policy {

                                            ///nokia-conf/configure/filter/ip-filter/entry/action/action/forward/forward/forward-action/srte-policy/srte-policy
                                            container srte-policy {
                                                presence "Enable the srte-policy context";
                                                description "Enable the srte-policy context";

                                                ///nokia-conf/configure/filter/ip-filter/entry/action/action/forward/forward/forward-action/srte-policy/srte-policy/endpoint
                                                leaf endpoint {
                                                    type types-sros:ipv4-unicast-or-zero-address;
                                                    mandatory true;
                                                    description "SR-TE policy endpoint IPv4 address";
                                                }

                                                ///nokia-conf/configure/filter/ip-filter/entry/action/action/forward/forward/forward-action/srte-policy/srte-policy/color
                                                leaf color {
                                                    type int64 {
                                                        range "0..4294967295";
                                                    }
                                                    mandatory true;
                                                    description "SR-TE policy color ID";
                                                }

                                            } // container srte-policy

                                        }
                                        ///nokia-conf/configure/filter/ip-filter/entry/action/action/forward/forward/forward-action/srv6-policy
                                        case srv6-policy {

                                            ///nokia-conf/configure/filter/ip-filter/entry/action/action/forward/forward/forward-action/srv6-policy/srv6-policy
                                            container srv6-policy {
                                                presence "Enable the srv6-policy context";
                                                description "Enable the srv6-policy context";

                                                ///nokia-conf/configure/filter/ip-filter/entry/action/action/forward/forward/forward-action/srv6-policy/srv6-policy/endpoint
                                                leaf endpoint {
                                                    type types-sros:ipv6-unicast-or-zero-address;
                                                    mandatory true;
                                                    description "SRv6 policy endpoint IPv6 address";
                                                }

                                                ///nokia-conf/configure/filter/ip-filter/entry/action/action/forward/forward/forward-action/srv6-policy/srv6-policy/color
                                                leaf color {
                                                    type uint32 {
                                                        range "0..4294967295";
                                                    }
                                                    mandatory true;
                                                    description "SRv6 policy color";
                                                }

                                                ///nokia-conf/configure/filter/ip-filter/entry/action/action/forward/forward/forward-action/srv6-policy/srv6-policy/service-sid
                                                leaf service-sid {
                                                    type types-sros:ipv6-unicast-address;
                                                    mandatory true;
                                                    description "SRv6 service segment identifier";
                                                }

                                            } // container srv6-policy

                                        }
                                    }
                                } // container forward

                            }
                            ///nokia-conf/configure/filter/ip-filter/entry/action/action/http-redirect
                            case http-redirect {

                                ///nokia-conf/configure/filter/ip-filter/entry/action/action/http-redirect/http-redirect
                                container http-redirect {
                                    presence "Enable the http-redirect context";
                                    description "Enable the http-redirect context";

                                    ///nokia-conf/configure/filter/ip-filter/entry/action/action/http-redirect/http-redirect/url
                                    leaf url {
                                        type union {
                                            type enumeration {
                                                enum from-cpf                       { value 1; }
                                            }
                                            type types-sros:http-redirect-url;
                                        }
                                        sros-ext:immutable;
                                        mandatory true;
                                        description "URL used for HTTP redirect action";
                                    }

                                    ///nokia-conf/configure/filter/ip-filter/entry/action/action/http-redirect/http-redirect/allow-override
                                    leaf allow-override {
                                        type boolean;
                                        default "false";
                                        description "Override the HTTP redirect URL by a RADIUS VSA";
                                    }

                                } // container http-redirect

                            }
                            ///nokia-conf/configure/filter/ip-filter/entry/action/action/nat
                            case nat {

                                ///nokia-conf/configure/filter/ip-filter/entry/action/action/nat/nat
                                container nat {
                                    presence "Enable the nat context";
                                    description "Enable the nat context";

                                    ///nokia-conf/configure/filter/ip-filter/entry/action/action/nat/nat/nat-policy
                                    leaf nat-policy {
                                        type leafref {
                                            path "../../../../../../service/nat/nat-policy/name";
                                        }
                                        sros-ext:isa-auto-clear-on-modify;
                                        description "NAT policy name when action is NAT";
                                    }

                                } // container nat

                            }
                            ///nokia-conf/configure/filter/ip-filter/entry/action/action/reassemble
                            case reassemble {

                                ///nokia-conf/configure/filter/ip-filter/entry/action/action/reassemble/reassemble
                                leaf reassemble {
                                    type empty;
                                    description "Forward matching packets to reassembly function";
                                }

                            }
                            ///nokia-conf/configure/filter/ip-filter/entry/action/action/gtp-local-breakout
                            case gtp-local-breakout {

                                ///nokia-conf/configure/filter/ip-filter/entry/action/action/gtp-local-breakout/gtp-local-breakout
                                leaf gtp-local-breakout {
                                    type empty;
                                    description "Break out matching traffic locally from a GTP tunnel for GTP-subscriber-hosts, or forward for other entities";
                                }

                            }
                            ///nokia-conf/configure/filter/ip-filter/entry/action/action/tcp-mss-adjust
                            case tcp-mss-adjust {

                                ///nokia-conf/configure/filter/ip-filter/entry/action/action/tcp-mss-adjust/tcp-mss-adjust
                                leaf tcp-mss-adjust {
                                    type empty;
                                    description "Adjust MSS option of TCP matching packets to configured value of tcp-mss in router interface context";
                                }

                            }
                            ///nokia-conf/configure/filter/ip-filter/entry/action/action/accept
                            case accept {

                                ///nokia-conf/configure/filter/ip-filter/entry/action/action/accept/accept
                                leaf accept {
                                    type empty;
                                    description "Accept regular routing to forward a matching packet";
                                }

                            }
                        }
                        ///nokia-conf/configure/filter/ip-filter/entry/action/remark
                        container remark {
                            presence "Enable the remark context";
                            description "Enable the remark context";

                            ///nokia-conf/configure/filter/ip-filter/entry/action/remark/dscp
                            leaf dscp {
                                type types-qos:dscp-name;
                                mandatory true;
                                description "Destination SAP";
                            }

                        } // container remark

                        ///nokia-conf/configure/filter/ip-filter/entry/action/rate-limit
                        container rate-limit {
                            presence "Enable the rate-limit context";
                            description "Enable the rate-limit context";

                            ///nokia-conf/configure/filter/ip-filter/entry/action/rate-limit/pir-choice
                            choice pir-choice {
                                mandatory true;
                                ///nokia-conf/configure/filter/ip-filter/entry/action/rate-limit/pir-choice/pir-case
                                case pir-case {

                                    ///nokia-conf/configure/filter/ip-filter/entry/action/rate-limit/pir-choice/pir-case/pir
                                    leaf pir {
                                        type types-filter:rate-limit-pir-kilobps;
                                        units "kilobps";
                                        description "Peak information rate";
                                    }

                                }
                                ///nokia-conf/configure/filter/ip-filter/entry/action/rate-limit/pir-choice/pps-pir-case
                                case pps-pir-case {

                                    ///nokia-conf/configure/filter/ip-filter/entry/action/rate-limit/pir-choice/pps-pir-case/pps-pir
                                    leaf pps-pir {
                                        type types-filter:rate-limit-pir-pps;
                                        units "packets per second";
                                        description "Peak information rate";
                                    }

                                }
                            }
                            ///nokia-conf/configure/filter/ip-filter/entry/action/rate-limit/criterion-1
                            choice criterion-1 {
                                ///nokia-conf/configure/filter/ip-filter/entry/action/rate-limit/criterion-1/ttl
                                case ttl {

                                    ///nokia-conf/configure/filter/ip-filter/entry/action/rate-limit/criterion-1/ttl/ttl
                                    container ttl {
                                        presence "Enable the ttl context";
                                        description "Enable the ttl context";

                                        ///nokia-conf/configure/filter/ip-filter/entry/action/rate-limit/criterion-1/ttl/ttl/ttl
                                        choice ttl {
                                            mandatory true;
                                            ///nokia-conf/configure/filter/ip-filter/entry/action/rate-limit/criterion-1/ttl/ttl/ttl/eq
                                            case eq {

                                                ///nokia-conf/configure/filter/ip-filter/entry/action/rate-limit/criterion-1/ttl/ttl/ttl/eq/eq
                                                leaf eq {
                                                    type types-filter:ttl-or-hop-limit-value;
                                                    description "Equal to condition match value";
                                                }

                                            }
                                            ///nokia-conf/configure/filter/ip-filter/entry/action/rate-limit/criterion-1/ttl/ttl/ttl/lt
                                            case lt {

                                                ///nokia-conf/configure/filter/ip-filter/entry/action/rate-limit/criterion-1/ttl/ttl/ttl/lt/lt
                                                leaf lt {
                                                    type types-filter:ttl-or-hop-limit-lt-value;
                                                    description "Less than condition match value";
                                                }

                                            }
                                            ///nokia-conf/configure/filter/ip-filter/entry/action/rate-limit/criterion-1/ttl/ttl/ttl/gt
                                            case gt {

                                                ///nokia-conf/configure/filter/ip-filter/entry/action/rate-limit/criterion-1/ttl/ttl/ttl/gt/gt
                                                leaf gt {
                                                    type types-filter:ttl-or-hop-limit-gt-value;
                                                    description "Greater than condition match value";
                                                }

                                            }
                                            ///nokia-conf/configure/filter/ip-filter/entry/action/rate-limit/criterion-1/ttl/ttl/ttl/range
                                            case range {

                                                ///nokia-conf/configure/filter/ip-filter/entry/action/rate-limit/criterion-1/ttl/ttl/ttl/range/range
                                                container range {
                                                    presence "Enable the range context";
                                                    description "Enable the range context";

                                                    ///nokia-conf/configure/filter/ip-filter/entry/action/rate-limit/criterion-1/ttl/ttl/ttl/range/range/start
                                                    leaf start {
                                                        type types-filter:ttl-or-hop-limit-gt-value;
                                                        mandatory true;
                                                        description "Lower bound of the range";
                                                    }

                                                    ///nokia-conf/configure/filter/ip-filter/entry/action/rate-limit/criterion-1/ttl/ttl/ttl/range/range/end
                                                    leaf end {
                                                        type types-filter:ttl-or-hop-limit-lt-value;
                                                        mandatory true;
                                                        description "Upper bound of the range";
                                                    }

                                                } // container range

                                            }
                                        }
                                    } // container ttl

                                }
                                ///nokia-conf/configure/filter/ip-filter/entry/action/rate-limit/criterion-1/packet-length
                                case packet-length {

                                    ///nokia-conf/configure/filter/ip-filter/entry/action/rate-limit/criterion-1/packet-length/packet-length
                                    container packet-length {
                                        presence "Enable the packet-length context";
                                        description "Enable the packet-length context";

                                        ///nokia-conf/configure/filter/ip-filter/entry/action/rate-limit/criterion-1/packet-length/packet-length/packet-length
                                        choice packet-length {
                                            mandatory true;
                                            ///nokia-conf/configure/filter/ip-filter/entry/action/rate-limit/criterion-1/packet-length/packet-length/packet-length/eq
                                            case eq {

                                                ///nokia-conf/configure/filter/ip-filter/entry/action/rate-limit/criterion-1/packet-length/packet-length/packet-length/eq/eq
                                                leaf eq {
                                                    type types-filter:pkt-len-or-payload-len-value;
                                                    description "Exact match criterion for the length";
                                                }

                                            }
                                            ///nokia-conf/configure/filter/ip-filter/entry/action/rate-limit/criterion-1/packet-length/packet-length/packet-length/lt
                                            case lt {

                                                ///nokia-conf/configure/filter/ip-filter/entry/action/rate-limit/criterion-1/packet-length/packet-length/packet-length/lt/lt
                                                leaf lt {
                                                    type types-filter:pkt-len-or-payload-len-lt-value;
                                                    description "Less than match criterion for the length";
                                                }

                                            }
                                            ///nokia-conf/configure/filter/ip-filter/entry/action/rate-limit/criterion-1/packet-length/packet-length/packet-length/gt
                                            case gt {

                                                ///nokia-conf/configure/filter/ip-filter/entry/action/rate-limit/criterion-1/packet-length/packet-length/packet-length/gt/gt
                                                leaf gt {
                                                    type types-filter:pkt-len-or-payload-len-gt-value;
                                                    description "Greater than match criterion for the length";
                                                }

                                            }
                                            ///nokia-conf/configure/filter/ip-filter/entry/action/rate-limit/criterion-1/packet-length/packet-length/packet-length/range
                                            case range {

                                                ///nokia-conf/configure/filter/ip-filter/entry/action/rate-limit/criterion-1/packet-length/packet-length/packet-length/range/range
                                                container range {
                                                    presence "Enable the range context";
                                                    description "Enable the range context";

                                                    ///nokia-conf/configure/filter/ip-filter/entry/action/rate-limit/criterion-1/packet-length/packet-length/packet-length/range/range/start
                                                    leaf start {
                                                        type types-filter:pkt-len-or-payload-len-gt-value;
                                                        mandatory true;
                                                        description "Lower bound of the length range";
                                                    }

                                                    ///nokia-conf/configure/filter/ip-filter/entry/action/rate-limit/criterion-1/packet-length/packet-length/packet-length/range/range/end
                                                    leaf end {
                                                        type types-filter:pkt-len-or-payload-len-lt-value;
                                                        mandatory true;
                                                        description "Upper bound of the length range";
                                                    }

                                                } // container range

                                            }
                                        }
                                    } // container packet-length

                                }
                            }
                            ///nokia-conf/configure/filter/ip-filter/entry/action/rate-limit/choice2
                            choice choice2 {
                                ///nokia-conf/configure/filter/ip-filter/entry/action/rate-limit/choice2/extracted-traffic-case
                                case extracted-traffic-case {

                                    ///nokia-conf/configure/filter/ip-filter/entry/action/rate-limit/choice2/extracted-traffic-case/extracted-traffic
                                    leaf extracted-traffic {
                                        type empty;
                                        description "Limit the rate of traffic extracted to the CPM";
                                    }

                                }
                            }
                            ///nokia-conf/configure/filter/ip-filter/entry/action/rate-limit/pattern
                            container pattern {
                                presence "Enable the pattern context";
                                description "Enable the pattern context";

                                ///nokia-conf/configure/filter/ip-filter/entry/action/rate-limit/pattern/expression
                                leaf expression {
                                    type types-sros:hex-string {
                                        length "3..18";
                                    }
                                    mandatory true;
                                    description "Pattern expression to match";
                                }

                                ///nokia-conf/configure/filter/ip-filter/entry/action/rate-limit/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ip-filter/entry/action/rate-limit/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ip-filter/entry/action/rate-limit/pattern/offset-value
                                leaf offset-value {
                                    type int32 {
                                        range "0..255";
                                    }
                                    mandatory true;
                                    description "Offset value for the pattern expression";
                                }

                            } // container pattern

                        } // container rate-limit

                        ///nokia-conf/configure/filter/ip-filter/entry/action/drop-when
                        container drop-when {
                            presence "Enable the drop-when context";
                            description "Enable the drop-when context";

                            ///nokia-conf/configure/filter/ip-filter/entry/action/drop-when/criterion-1
                            choice criterion-1 {
                                ///nokia-conf/configure/filter/ip-filter/entry/action/drop-when/criterion-1/ttl
                                case ttl {

                                    ///nokia-conf/configure/filter/ip-filter/entry/action/drop-when/criterion-1/ttl/ttl
                                    container ttl {
                                        presence "Enable the ttl context";
                                        description "Enable the ttl context";

                                        ///nokia-conf/configure/filter/ip-filter/entry/action/drop-when/criterion-1/ttl/ttl/ttl
                                        choice ttl {
                                            mandatory true;
                                            ///nokia-conf/configure/filter/ip-filter/entry/action/drop-when/criterion-1/ttl/ttl/ttl/eq
                                            case eq {

                                                ///nokia-conf/configure/filter/ip-filter/entry/action/drop-when/criterion-1/ttl/ttl/ttl/eq/eq
                                                leaf eq {
                                                    type types-filter:ttl-or-hop-limit-value;
                                                    description "Equal to condition match value";
                                                }

                                            }
                                            ///nokia-conf/configure/filter/ip-filter/entry/action/drop-when/criterion-1/ttl/ttl/ttl/lt
                                            case lt {

                                                ///nokia-conf/configure/filter/ip-filter/entry/action/drop-when/criterion-1/ttl/ttl/ttl/lt/lt
                                                leaf lt {
                                                    type types-filter:ttl-or-hop-limit-lt-value;
                                                    description "Less than condition match value";
                                                }

                                            }
                                            ///nokia-conf/configure/filter/ip-filter/entry/action/drop-when/criterion-1/ttl/ttl/ttl/gt
                                            case gt {

                                                ///nokia-conf/configure/filter/ip-filter/entry/action/drop-when/criterion-1/ttl/ttl/ttl/gt/gt
                                                leaf gt {
                                                    type types-filter:ttl-or-hop-limit-gt-value;
                                                    description "Greater than condition match value";
                                                }

                                            }
                                            ///nokia-conf/configure/filter/ip-filter/entry/action/drop-when/criterion-1/ttl/ttl/ttl/range
                                            case range {

                                                ///nokia-conf/configure/filter/ip-filter/entry/action/drop-when/criterion-1/ttl/ttl/ttl/range/range
                                                container range {
                                                    presence "Enable the range context";
                                                    description "Enable the range context";

                                                    ///nokia-conf/configure/filter/ip-filter/entry/action/drop-when/criterion-1/ttl/ttl/ttl/range/range/start
                                                    leaf start {
                                                        type types-filter:ttl-or-hop-limit-gt-value;
                                                        mandatory true;
                                                        description "Lower bound of the range";
                                                    }

                                                    ///nokia-conf/configure/filter/ip-filter/entry/action/drop-when/criterion-1/ttl/ttl/ttl/range/range/end
                                                    leaf end {
                                                        type types-filter:ttl-or-hop-limit-lt-value;
                                                        mandatory true;
                                                        description "Upper bound of the range";
                                                    }

                                                } // container range

                                            }
                                        }
                                    } // container ttl

                                }
                                ///nokia-conf/configure/filter/ip-filter/entry/action/drop-when/criterion-1/packet-length
                                case packet-length {

                                    ///nokia-conf/configure/filter/ip-filter/entry/action/drop-when/criterion-1/packet-length/packet-length
                                    container packet-length {
                                        presence "Enable the packet-length context";
                                        description "Enable the packet-length context";

                                        ///nokia-conf/configure/filter/ip-filter/entry/action/drop-when/criterion-1/packet-length/packet-length/packet-length
                                        choice packet-length {
                                            mandatory true;
                                            ///nokia-conf/configure/filter/ip-filter/entry/action/drop-when/criterion-1/packet-length/packet-length/packet-length/eq
                                            case eq {

                                                ///nokia-conf/configure/filter/ip-filter/entry/action/drop-when/criterion-1/packet-length/packet-length/packet-length/eq/eq
                                                leaf eq {
                                                    type types-filter:pkt-len-or-payload-len-value;
                                                    description "Exact match criterion for the length";
                                                }

                                            }
                                            ///nokia-conf/configure/filter/ip-filter/entry/action/drop-when/criterion-1/packet-length/packet-length/packet-length/lt
                                            case lt {

                                                ///nokia-conf/configure/filter/ip-filter/entry/action/drop-when/criterion-1/packet-length/packet-length/packet-length/lt/lt
                                                leaf lt {
                                                    type types-filter:pkt-len-or-payload-len-lt-value;
                                                    description "Less than match criterion for the length";
                                                }

                                            }
                                            ///nokia-conf/configure/filter/ip-filter/entry/action/drop-when/criterion-1/packet-length/packet-length/packet-length/gt
                                            case gt {

                                                ///nokia-conf/configure/filter/ip-filter/entry/action/drop-when/criterion-1/packet-length/packet-length/packet-length/gt/gt
                                                leaf gt {
                                                    type types-filter:pkt-len-or-payload-len-gt-value;
                                                    description "Greater than match criterion for the length";
                                                }

                                            }
                                            ///nokia-conf/configure/filter/ip-filter/entry/action/drop-when/criterion-1/packet-length/packet-length/packet-length/range
                                            case range {

                                                ///nokia-conf/configure/filter/ip-filter/entry/action/drop-when/criterion-1/packet-length/packet-length/packet-length/range/range
                                                container range {
                                                    presence "Enable the range context";
                                                    description "Enable the range context";

                                                    ///nokia-conf/configure/filter/ip-filter/entry/action/drop-when/criterion-1/packet-length/packet-length/packet-length/range/range/start
                                                    leaf start {
                                                        type types-filter:pkt-len-or-payload-len-gt-value;
                                                        mandatory true;
                                                        description "Lower bound of the length range";
                                                    }

                                                    ///nokia-conf/configure/filter/ip-filter/entry/action/drop-when/criterion-1/packet-length/packet-length/packet-length/range/range/end
                                                    leaf end {
                                                        type types-filter:pkt-len-or-payload-len-lt-value;
                                                        mandatory true;
                                                        description "Upper bound of the length range";
                                                    }

                                                } // container range

                                            }
                                        }
                                    } // container packet-length

                                }
                            }
                            ///nokia-conf/configure/filter/ip-filter/entry/action/drop-when/criterion-2
                            choice criterion-2 {
                                ///nokia-conf/configure/filter/ip-filter/entry/action/drop-when/criterion-2/extracted-traffic
                                case extracted-traffic {

                                    ///nokia-conf/configure/filter/ip-filter/entry/action/drop-when/criterion-2/extracted-traffic/extracted-traffic
                                    leaf extracted-traffic {
                                        type empty;
                                        description "Drop traffic extracted to CPM";
                                    }

                                }
                            }
                            ///nokia-conf/configure/filter/ip-filter/entry/action/drop-when/pattern
                            container pattern {
                                presence "Enable the pattern context";
                                description "Enable the pattern context";

                                ///nokia-conf/configure/filter/ip-filter/entry/action/drop-when/pattern/expression
                                leaf expression {
                                    type types-sros:hex-string {
                                        length "3..18";
                                    }
                                    mandatory true;
                                    description "Pattern expression to match";
                                }

                                ///nokia-conf/configure/filter/ip-filter/entry/action/drop-when/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ip-filter/entry/action/drop-when/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ip-filter/entry/action/drop-when/pattern/offset-value
                                leaf offset-value {
                                    type int32 {
                                        range "0..255";
                                    }
                                    mandatory true;
                                    description "Offset value for the pattern expression";
                                }

                            } // container pattern

                        } // container drop-when

                        ///nokia-conf/configure/filter/ip-filter/entry/action/accept-when
                        container accept-when {
                            presence "Enable the accept-when context";
                            description "Enable the accept-when context";

                            ///nokia-conf/configure/filter/ip-filter/entry/action/accept-when/pattern
                            container pattern {
                                presence "Enable the pattern context";
                                description "Enable the pattern context";

                                ///nokia-conf/configure/filter/ip-filter/entry/action/accept-when/pattern/expression
                                leaf expression {
                                    type types-sros:hex-string {
                                        length "3..18";
                                    }
                                    mandatory true;
                                    description "Pattern expression to match";
                                }

                                ///nokia-conf/configure/filter/ip-filter/entry/action/accept-when/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ip-filter/entry/action/accept-when/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ip-filter/entry/action/accept-when/pattern/offset-value
                                leaf offset-value {
                                    type int32 {
                                        range "0..255";
                                    }
                                    mandatory true;
                                    description "Offset value for the pattern expression";
                                }

                            } // container pattern

                        } // container accept-when

                        ///nokia-conf/configure/filter/ip-filter/entry/action/secondary
                        container secondary {
                            presence "Enable the secondary context";
                            description "Enable the secondary context";

                            ///nokia-conf/configure/filter/ip-filter/entry/action/secondary/apply-groups
                            leaf-list apply-groups {
                                type leafref {
                                    path "../../../../../../groups/group/name";
                                }
                                max-elements 8;
                                ordered-by user;
                                description "Apply a configuration group at this level";
                            }

                            ///nokia-conf/configure/filter/ip-filter/entry/action/secondary/apply-groups-exclude
                            leaf-list apply-groups-exclude {
                                type leafref {
                                    path "../../../../../../groups/group/name";
                                }
                                max-elements 8;
                                ordered-by user;
                                description "Exclude a configuration group at this level";
                            }

                            ///nokia-conf/configure/filter/ip-filter/entry/action/secondary/action
                            choice action {
                                mandatory true;
                                ///nokia-conf/configure/filter/ip-filter/entry/action/secondary/action/forward
                                case forward {

                                    ///nokia-conf/configure/filter/ip-filter/entry/action/secondary/action/forward/forward
                                    container forward {
                                        description "Enter the forward context";

                                        ///nokia-conf/configure/filter/ip-filter/entry/action/secondary/action/forward/forward/forward-action
                                        choice forward-action {
                                            ///nokia-conf/configure/filter/ip-filter/entry/action/secondary/action/forward/forward/forward-action/next-hop
                                            case next-hop {

                                                ///nokia-conf/configure/filter/ip-filter/entry/action/secondary/action/forward/forward/forward-action/next-hop/next-hop
                                                container next-hop {
                                                    presence "Enable the next-hop context";
                                                    description "Enable the next-hop context";

                                                    ///nokia-conf/configure/filter/ip-filter/entry/action/secondary/action/forward/forward/forward-action/next-hop/next-hop/next-hop
                                                    choice next-hop {
                                                        mandatory true;
                                                        ///nokia-conf/configure/filter/ip-filter/entry/action/secondary/action/forward/forward/forward-action/next-hop/next-hop/next-hop/nh-ip-vrf
                                                        case nh-ip-vrf {

                                                            ///nokia-conf/configure/filter/ip-filter/entry/action/secondary/action/forward/forward/forward-action/next-hop/next-hop/next-hop/nh-ip-vrf/nh-ip-vrf
                                                            container nh-ip-vrf {
                                                                presence "Enable the nh-ip-vrf context";
                                                                description "Enable the nh-ip-vrf context";

                                                                ///nokia-conf/configure/filter/ip-filter/entry/action/secondary/action/forward/forward/forward-action/next-hop/next-hop/next-hop/nh-ip-vrf/nh-ip-vrf/indirect
                                                                leaf indirect {
                                                                    type boolean;
                                                                    default "false";
                                                                    description "Allow next hop to be indirectly reachable";
                                                                }

                                                                ///nokia-conf/configure/filter/ip-filter/entry/action/secondary/action/forward/forward/forward-action/next-hop/next-hop/next-hop/nh-ip-vrf/nh-ip-vrf/router-instance
                                                                leaf router-instance {
                                                                    type string;
                                                                    sros-ext:immutable;
                                                                    mandatory true;
                                                                    description "Routing context for route lookup for forwarding packets";
                                                                }

                                                                ///nokia-conf/configure/filter/ip-filter/entry/action/secondary/action/forward/forward/forward-action/next-hop/next-hop/next-hop/nh-ip-vrf/nh-ip-vrf/address
                                                                leaf address {
                                                                    type types-sros:ipv4-address;
                                                                    sros-ext:immutable;
                                                                    mandatory true;
                                                                    description "IPv4 address of next hop to forward matching packets";
                                                                }

                                                            } // container nh-ip-vrf

                                                        }
                                                    }
                                                } // container next-hop

                                            }
                                            ///nokia-conf/configure/filter/ip-filter/entry/action/secondary/action/forward/forward/forward-action/sdp
                                            case sdp {

                                                ///nokia-conf/configure/filter/ip-filter/entry/action/secondary/action/forward/forward/forward-action/sdp/sdp
                                                container sdp {
                                                    presence "Enable the sdp context";
                                                    description "Enable the sdp context";

                                                    ///nokia-conf/configure/filter/ip-filter/entry/action/secondary/action/forward/forward/forward-action/sdp/sdp/vpls
                                                    leaf vpls {
                                                        type leafref {
                                                            path "../../../../../../../../service/vpls/service-name";
                                                        }
                                                        mandatory true;
                                                        description "VPLS associated with the SDP";
                                                    }

                                                    ///nokia-conf/configure/filter/ip-filter/entry/action/secondary/action/forward/forward/forward-action/sdp/sdp/sdp-bind-id
                                                    leaf sdp-bind-id {
                                                        type types-services:sdp-bind-id;
                                                        sros-ext:immutable;
                                                        mandatory true;
                                                        description "VPLS SDP bind ID used to forward matching packets";
                                                    }

                                                } // container sdp

                                            }
                                            ///nokia-conf/configure/filter/ip-filter/entry/action/secondary/action/forward/forward/forward-action/sap
                                            case sap {

                                                ///nokia-conf/configure/filter/ip-filter/entry/action/secondary/action/forward/forward/forward-action/sap/sap
                                                container sap {
                                                    presence "Enable the sap context";
                                                    description "Enable the sap context";

                                                    ///nokia-conf/configure/filter/ip-filter/entry/action/secondary/action/forward/forward/forward-action/sap/sap/vpls
                                                    leaf vpls {
                                                        type leafref {
                                                            path "../../../../../../../../service/vpls/service-name";
                                                        }
                                                        mandatory true;
                                                        description "VPLS the sdp-bind-id belongs to";
                                                    }

                                                    ///nokia-conf/configure/filter/ip-filter/entry/action/secondary/action/forward/forward/forward-action/sap/sap/sap-id
                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                            ///nokia-conf/configure/filter/ip-filter/entry/action/secondary/action/forward/forward/forward-action/vprn-target
                                            case vprn-target {

                                                ///nokia-conf/configure/filter/ip-filter/entry/action/secondary/action/forward/forward/forward-action/vprn-target/vprn-target
                                                container vprn-target {
                                                    presence "Enable the vprn-target context";
                                                    description "Enable the vprn-target context";

                                                    ///nokia-conf/configure/filter/ip-filter/entry/action/secondary/action/forward/forward/forward-action/vprn-target/vprn-target/bgp-nh
                                                    leaf bgp-nh {
                                                        type types-sros:ipv4-address {
                                                            pattern
                                                                "((([0-9]|[1-9][0-9]|1[0-9][0-9]|2[0-4][0-9]|25[0-5])\\.){3}([1-9]|[1-9][0-9]|1[0-9][0-9]|2[0-4][0-9]|25[0-5]))|
                                                                                  ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                                  ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                                  (([1-9]|[1-9][0-9]|1[0-9][0-9]|2[0-4][0-9]|25[0-5]){1}(\\.([0-9]|[1-9][0-9]|1[0-9][0-9]|2[0-4][0-9]|25[0-5])){3})";
                                                        }
                                                        mandatory true;
                                                        description "Target BGP next hop IP address";
                                                    }

                                                    ///nokia-conf/configure/filter/ip-filter/entry/action/secondary/action/forward/forward/forward-action/vprn-target/vprn-target/vprn
                                                    leaf vprn {
                                                        type leafref {
                                                            path "../../../../../../../../service/vprn/service-name";
                                                        }
                                                        mandatory true;
                                                        description "Routing context used for route lookup";
                                                    }

                                                    ///nokia-conf/configure/filter/ip-filter/entry/action/secondary/action/forward/forward/forward-action/vprn-target/vprn-target/lsp
                                                    leaf lsp {
                                                        type types-sros:named-item-64;
                                                        description "LSP that is specified to forward a packet matching this entry";
                                                    }

                                                    ///nokia-conf/configure/filter/ip-filter/entry/action/secondary/action/forward/forward/forward-action/vprn-target/vprn-target/adv-prefix
                                                    leaf adv-prefix {
                                                        type types-sros:ipv4-prefix;
                                                        description "Advertised IP prefix for the target destination";
                                                    }

                                                } // container vprn-target

                                            }
                                        }
                                    } // container forward

                                }
                            }
                            ///nokia-conf/configure/filter/ip-filter/entry/action/secondary/remark
                            container remark {
                                presence "Enable the remark context";
                                description "Enable the remark context";

                                ///nokia-conf/configure/filter/ip-filter/entry/action/secondary/remark/dscp
                                leaf dscp {
                                    type types-qos:dscp-name;
                                    mandatory true;
                                    description "Destination SAP";
                                }

                            } // container remark

                        } // container secondary

                    } // container action

                } // list entry

                ///nokia-conf/configure/filter/ip-filter/embed
                container embed {
                    description "Enter the embed context";

                    ///nokia-conf/configure/filter/ip-filter/embed/filter
                    list filter {
                        key "name offset";
                        description "Enter the filter list instance";

                        ///nokia-conf/configure/filter/ip-filter/embed/filter/name
                        leaf name {
                            type leafref {
                                path "../../../../ip-filter/filter-name";
                            }
                            description "IPv4 policy to be embedded in the filter";
                        }

                        ///nokia-conf/configure/filter/ip-filter/embed/filter/offset
                        leaf offset {
                            type types-filter:embed-offset {
                                range "0..2097150";
                            }
                            description "Offset of the inserted entries";
                        }

                        ///nokia-conf/configure/filter/ip-filter/embed/filter/admin-state
                        leaf admin-state {
                            type types-sros:admin-state;
                            default "enable";
                            description "Administrative state of the embedded filter";
                        }

                        ///nokia-conf/configure/filter/ip-filter/embed/filter/apply-groups
                        leaf-list apply-groups {
                            type leafref {
                                path "../../../../../groups/group/name";
                            }
                            max-elements 8;
                            ordered-by user;
                            description "Apply a configuration group at this level";
                        }

                        ///nokia-conf/configure/filter/ip-filter/embed/filter/apply-groups-exclude
                        leaf-list apply-groups-exclude {
                            type leafref {
                                path "../../../../../groups/group/name";
                            }
                            max-elements 8;
                            ordered-by user;
                            description "Exclude a configuration group at this level";
                        }

                    } // list filter

                    ///nokia-conf/configure/filter/ip-filter/embed/flowspec
                    list flowspec {
                        key "offset";
                        description "Enter the flowspec list instance";

                        ///nokia-conf/configure/filter/ip-filter/embed/flowspec/offset
                        leaf offset {
                            type types-filter:embed-offset;
                            description "Offset of the inserted entries";
                        }

                        ///nokia-conf/configure/filter/ip-filter/embed/flowspec/group
                        leaf group {
                            type uint32 {
                                range "0..16383";
                            }
                            sros-ext:immutable;
                            description "Interface group ID for an external configured set of flowspec rules";
                        }

                        ///nokia-conf/configure/filter/ip-filter/embed/flowspec/router-instance
                        leaf router-instance {
                            type string;
                            sros-ext:immutable;
                            mandatory true;
                            description "Virtual router for an external configured set of flowspec rules";
                        }

                        ///nokia-conf/configure/filter/ip-filter/embed/flowspec/admin-state
                        leaf admin-state {
                            type types-sros:admin-state;
                            default "enable";
                            description "Administrative state of the embedded filter";
                        }

                        ///nokia-conf/configure/filter/ip-filter/embed/flowspec/apply-groups
                        leaf-list apply-groups {
                            type leafref {
                                path "../../../../../groups/group/name";
                            }
                            max-elements 8;
                            ordered-by user;
                            description "Apply a configuration group at this level";
                        }

                        ///nokia-conf/configure/filter/ip-filter/embed/flowspec/apply-groups-exclude
                        leaf-list apply-groups-exclude {
                            type leafref {
                                path "../../../../../groups/group/name";
                            }
                            max-elements 8;
                            ordered-by user;
                            description "Exclude a configuration group at this level";
                        }

                    } // list flowspec

                    ///nokia-conf/configure/filter/ip-filter/embed/openflow
                    list openflow {
                        key "of-switch offset";
                        description "Enter the openflow list instance";

                        ///nokia-conf/configure/filter/ip-filter/embed/openflow/of-switch
                        leaf of-switch {
                            type leafref {
                                path "../../../../../openflow/of-switch/name";
                            }
                            description "Referenced Hybrid OpenFlow Switch (OFS) name";
                        }

                        ///nokia-conf/configure/filter/ip-filter/embed/openflow/offset
                        leaf offset {
                            type types-filter:embed-offset {
                                range "0..2097150";
                            }
                            description "Offset of the inserted entries";
                        }

                        ///nokia-conf/configure/filter/ip-filter/embed/openflow/admin-state
                        leaf admin-state {
                            type types-sros:admin-state;
                            default "enable";
                            description "Administrative state of the embedded filter";
                        }

                        ///nokia-conf/configure/filter/ip-filter/embed/openflow/apply-groups
                        leaf-list apply-groups {
                            type leafref {
                                path "../../../../../groups/group/name";
                            }
                            max-elements 8;
                            ordered-by user;
                            description "Apply a configuration group at this level";
                        }

                        ///nokia-conf/configure/filter/ip-filter/embed/openflow/apply-groups-exclude
                        leaf-list apply-groups-exclude {
                            type leafref {
                                path "../../../../../groups/group/name";
                            }
                            max-elements 8;
                            ordered-by user;
                            description "Exclude a configuration group at this level";
                        }

                        ///nokia-conf/configure/filter/ip-filter/embed/openflow/context
                        choice context {
                            default "grt";
                            description
                                "Specifies the context in which the openflow embedding is inserted into filter.
                                 When no context is present, this object is set to grt value.";
                            ///nokia-conf/configure/filter/ip-filter/embed/openflow/context/grt
                            case grt {

                                ///nokia-conf/configure/filter/ip-filter/embed/openflow/context/grt/grt
                                leaf grt {
                                    type empty;
                                    sros-ext:immutable;
                                    description "Global routing context";
                                }

                            }
                            ///nokia-conf/configure/filter/ip-filter/embed/openflow/context/system
                            case system {

                                ///nokia-conf/configure/filter/ip-filter/embed/openflow/context/system/system
                                leaf system {
                                    type empty;
                                    sros-ext:immutable;
                                    description "System context";
                                }

                            }
                            ///nokia-conf/configure/filter/ip-filter/embed/openflow/context/vprn
                            case vprn {

                                ///nokia-conf/configure/filter/ip-filter/embed/openflow/context/vprn/vprn
                                leaf vprn {
                                    type leafref {
                                        path "../../../../../service/vprn/service-name";
                                    }
                                    sros-ext:immutable;
                                    description "VPRN context";
                                }

                            }
                            ///nokia-conf/configure/filter/ip-filter/embed/openflow/context/vpls
                            case vpls {

                                ///nokia-conf/configure/filter/ip-filter/embed/openflow/context/vpls/vpls
                                leaf vpls {
                                    type leafref {
                                        path "../../../../../service/vpls/service-name";
                                    }
                                    sros-ext:immutable;
                                    description "VPLS context";
                                }

                                ///nokia-conf/configure/filter/ip-filter/embed/openflow/context/vpls/sap
                                leaf sap {
                                    type leafref {
                                        path "../../../../../service/vpls[service-name=current()/../vpls]/sap/sap-id";
                                    }
                                    sros-ext:immutable;
                                    description "SAP context";
                                }

                            }
                        }
                    } // list openflow

                    ///nokia-conf/configure/filter/ip-filter/embed/vsd
                    list vsd {
                        status obsolete;
                        key "name offset";
                        description "Enter the vsd list instance";

                        ///nokia-conf/configure/filter/ip-filter/embed/vsd/name
                        leaf name {
                            status obsolete;
                            type types-sros:named-item {
                                pattern "_tmnx_vsd_([1-9]|[1-9][0-9]|[1-9][0-9][0-9]|[1-9][0-9][0-9][0-9]|[1-5][0-9][0-9][0-9][0-9]|6[0-4][0-9][0-9][0-9]|65[0-4][0-9][0-9]|655[0-2][0-9]|6553[0-5])";
                            }
                            description "Specifies the name of the filter to be inserted in this filter";
                        }

                        ///nokia-conf/configure/filter/ip-filter/embed/vsd/offset
                        leaf offset {
                            status obsolete;
                            type types-filter:embed-offset {
                                range "0..2097150";
                            }
                            description "Offset of the inserted entries";
                        }

                        ///nokia-conf/configure/filter/ip-filter/embed/vsd/admin-state
                        leaf admin-state {
                            status obsolete;
                            type types-sros:admin-state;
                            default "enable";
                            description "Administrative state of the embedded filter";
                        }

                        ///nokia-conf/configure/filter/ip-filter/embed/vsd/apply-groups
                        leaf-list apply-groups {
                            status obsolete;
                            type leafref {
                                path "../../../../../groups/group/name";
                            }
                            max-elements 8;
                            ordered-by user;
                            description "Apply a configuration group at this level";
                        }

                        ///nokia-conf/configure/filter/ip-filter/embed/vsd/apply-groups-exclude
                        leaf-list apply-groups-exclude {
                            status obsolete;
                            type leafref {
                                path "../../../../../groups/group/name";
                            }
                            max-elements 8;
                            ordered-by user;
                            description "Exclude a configuration group at this level";
                        }

                    } // list vsd

                } // container embed

            } // list ip-filter

            ///nokia-conf/configure/filter/ipv6-filter
            list ipv6-filter {
                key "filter-name";
                description "Enter the ipv6-filter list instance";

                ///nokia-conf/configure/filter/ipv6-filter/filter-name
                leaf filter-name {
                    type types-filter:filter-name;
                    description "Filter name";
                }

                ///nokia-conf/configure/filter/ipv6-filter/default-action
                leaf default-action {
                    type types-filter:filter-default-action;
                    default "drop";
                    description "Action for packets that do not match any entry";
                }

                ///nokia-conf/configure/filter/ipv6-filter/description
                leaf description {
                    type types-sros:description;
                    description "Text description";
                }

                ///nokia-conf/configure/filter/ipv6-filter/scope
                leaf scope {
                    type types-filter:filter-scope;
                    default "template";
                    description "Scope of the filter defintion";
                }

                ///nokia-conf/configure/filter/ipv6-filter/type
                leaf type {
                    type enumeration {
                        enum normal                         { value 0; }
                        enum src-mac                        { value 1; }
                        enum packet-length                  { value 2; }
                        enum destination-class              { value 3; }
                    }
                    default "normal";
                    description "Set of match criteria for the filter policy";
                }

                ///nokia-conf/configure/filter/ipv6-filter/chain-to-system-filter
                leaf chain-to-system-filter {
                    type boolean;
                    default "false";
                    description "Chain filter policy to the active IPvX system filter policy";
                }

                ///nokia-conf/configure/filter/ipv6-filter/shared-policer
                leaf shared-policer {
                    type boolean;
                    default "false";
                    description "Share policer among active ports in the LAG";
                }

                ///nokia-conf/configure/filter/ipv6-filter/filter-id
                leaf filter-id {
                    type types-filter:filter-id;
                    sros-ext:immutable;
                    description "IPv6 filter identifier";
                }

                ///nokia-conf/configure/filter/ipv6-filter/apply-groups
                leaf-list apply-groups {
                    type leafref {
                        path "../../../groups/group/name";
                    }
                    max-elements 8;
                    ordered-by user;
                    description "Apply a configuration group at this level";
                }

                ///nokia-conf/configure/filter/ipv6-filter/apply-groups-exclude
                leaf-list apply-groups-exclude {
                    type leafref {
                        path "../../../groups/group/name";
                    }
                    max-elements 8;
                    ordered-by user;
                    description "Exclude a configuration group at this level";
                }

                ///nokia-conf/configure/filter/ipv6-filter/subscriber-mgmt
                container subscriber-mgmt {
                    description "Enter the subscriber-mgmt context";

                    ///nokia-conf/configure/filter/ipv6-filter/subscriber-mgmt/host-specific-entry
                    container host-specific-entry {
                        description "Enter the host-specific-entry context";

                        ///nokia-conf/configure/filter/ipv6-filter/subscriber-mgmt/host-specific-entry/filter-rule
                        container filter-rule {
                            description "Enter the filter-rule context";

                            ///nokia-conf/configure/filter/ipv6-filter/subscriber-mgmt/host-specific-entry/filter-rule/range
                            container range {
                                presence "Enable the range context";
                                description "Enable the range context";

                                ///nokia-conf/configure/filter/ipv6-filter/subscriber-mgmt/host-specific-entry/filter-rule/range/start
                                leaf start {
                                    type types-filter:entry-id;
                                    mandatory true;
                                    description "Lower bound of range for inserting filter rule entries";
                                }

                                ///nokia-conf/configure/filter/ipv6-filter/subscriber-mgmt/host-specific-entry/filter-rule/range/end
                                leaf end {
                                    type types-filter:entry-id;
                                    mandatory true;
                                    description "Upper bound of range for inserting filter rule entries";
                                }

                            } // container range

                        } // container filter-rule

                        ///nokia-conf/configure/filter/ipv6-filter/subscriber-mgmt/host-specific-entry/credit-control
                        container credit-control {
                            description "Enter the credit-control context";

                            ///nokia-conf/configure/filter/ipv6-filter/subscriber-mgmt/host-specific-entry/credit-control/range
                            container range {
                                presence "Enable the range context";
                                description "Enable the range context";

                                ///nokia-conf/configure/filter/ipv6-filter/subscriber-mgmt/host-specific-entry/credit-control/range/start
                                leaf start {
                                    type types-filter:entry-id;
                                    mandatory true;
                                    description "Lower bound of range for credit control filter entries";
                                }

                                ///nokia-conf/configure/filter/ipv6-filter/subscriber-mgmt/host-specific-entry/credit-control/range/end
                                leaf end {
                                    type types-filter:entry-id;
                                    mandatory true;
                                    description "Upper bound of range for credit control filter entries";
                                }

                            } // container range

                        } // container credit-control

                        ///nokia-conf/configure/filter/ipv6-filter/subscriber-mgmt/host-specific-entry/watermark
                        container watermark {
                            description "Enter the watermark context";

                            ///nokia-conf/configure/filter/ipv6-filter/subscriber-mgmt/host-specific-entry/watermark/low
                            leaf low {
                                type int32 {
                                    range "0..100";
                                }
                                default "90";
                                description "Low watermark for host-specific entries, to clear a table full alarm";
                            }

                            ///nokia-conf/configure/filter/ipv6-filter/subscriber-mgmt/host-specific-entry/watermark/high
                            leaf high {
                                type int32 {
                                    range "0..100";
                                }
                                default "95";
                                description "High watermark for host-specific entries, to raise a table full alarm";
                            }

                        } // container watermark

                    } // container host-specific-entry

                    ///nokia-conf/configure/filter/ipv6-filter/subscriber-mgmt/shared-entry
                    container shared-entry {
                        description "Enter the shared-entry context";

                        ///nokia-conf/configure/filter/ipv6-filter/subscriber-mgmt/shared-entry/filter-rule
                        container filter-rule {
                            description "Enter the filter-rule context";

                            ///nokia-conf/configure/filter/ipv6-filter/subscriber-mgmt/shared-entry/filter-rule/range
                            container range {
                                presence "Enable the range context";
                                description "Enable the range context";

                                ///nokia-conf/configure/filter/ipv6-filter/subscriber-mgmt/shared-entry/filter-rule/range/start
                                leaf start {
                                    type types-filter:entry-id;
                                    mandatory true;
                                    description "Lower bound of range for inserting shared host rules";
                                }

                                ///nokia-conf/configure/filter/ipv6-filter/subscriber-mgmt/shared-entry/filter-rule/range/end
                                leaf end {
                                    type types-filter:entry-id;
                                    mandatory true;
                                    description "Upper bound of range for inserting shared host rules";
                                }

                            } // container range

                        } // container filter-rule

                        ///nokia-conf/configure/filter/ipv6-filter/subscriber-mgmt/shared-entry/pcc-rule
                        container pcc-rule {
                            description "Enter the pcc-rule context";

                            ///nokia-conf/configure/filter/ipv6-filter/subscriber-mgmt/shared-entry/pcc-rule/range
                            container range {
                                presence "Enable the range context";
                                description "Enable the range context";

                                ///nokia-conf/configure/filter/ipv6-filter/subscriber-mgmt/shared-entry/pcc-rule/range/start
                                leaf start {
                                    type types-filter:entry-id;
                                    mandatory true;
                                    description "Lower bound of the range for PCC rule filter entries";
                                }

                                ///nokia-conf/configure/filter/ipv6-filter/subscriber-mgmt/shared-entry/pcc-rule/range/end
                                leaf end {
                                    type types-filter:entry-id;
                                    mandatory true;
                                    description "Upper bound of the range for PCC rule filter entries";
                                }

                            } // container range

                        } // container pcc-rule

                        ///nokia-conf/configure/filter/ipv6-filter/subscriber-mgmt/shared-entry/watermark
                        container watermark {
                            presence "Enable the watermark context";
                            description "Enable the watermark context";

                            ///nokia-conf/configure/filter/ipv6-filter/subscriber-mgmt/shared-entry/watermark/low
                            leaf low {
                                type int32 {
                                    range "0..7999";
                                }
                                mandatory true;
                                description "Limit of RADIUS or Diameter shared filters before clearing high watermark notification";
                            }

                            ///nokia-conf/configure/filter/ipv6-filter/subscriber-mgmt/shared-entry/watermark/high
                            leaf high {
                                type int32 {
                                    range "1..8000";
                                }
                                mandatory true;
                                description "Limit of RADIUS shared filters before generating high watermark notification";
                            }

                        } // container watermark

                    } // container shared-entry

                } // container subscriber-mgmt

                ///nokia-conf/configure/filter/ipv6-filter/entry
                list entry {
                    key "entry-id";
                    description "Enter the entry list instance";

                    ///nokia-conf/configure/filter/ipv6-filter/entry/entry-id
                    leaf entry-id {
                        type types-filter:entry-id;
                        description "ID for a match criteria and the corresponding action";
                    }

                    ///nokia-conf/configure/filter/ipv6-filter/entry/description
                    leaf description {
                        type types-sros:description;
                        description "Text description";
                    }

                    ///nokia-conf/configure/filter/ipv6-filter/entry/pbr-down-action-override
                    leaf pbr-down-action-override {
                        type types-filter:filter-pbr-down-action-ovr;
                        description "Action when PBR or PBF target for this entry is not available";
                    }

                    ///nokia-conf/configure/filter/ipv6-filter/entry/sticky-dest
                    leaf sticky-dest {
                        type types-filter:filter-sticky-dest;
                        units "seconds";
                        description "Time before action with available PBR or PBF destination and highest priority";
                    }

                    ///nokia-conf/configure/filter/ipv6-filter/entry/log
                    leaf log {
                        type leafref {
                            path "../../../log/log-id";
                        }
                        description "Log that is used for packets matching this entry";
                    }

                    ///nokia-conf/configure/filter/ipv6-filter/entry/collect-stats
                    leaf collect-stats {
                        type boolean;
                        default "false";
                        description "Enable statistics collection for an entry";
                    }

                    ///nokia-conf/configure/filter/ipv6-filter/entry/egress-pbr
                    leaf egress-pbr {
                        type types-filter:filter-egress-pbr;
                        sros-ext:immutable;
                        description "PBR that has an effect when this filter is applied on egress";
                    }

                    ///nokia-conf/configure/filter/ipv6-filter/entry/filter-sample
                    leaf filter-sample {
                        type boolean;
                        default "false";
                        description "Sample matching traffic if IP interface is set to cflowd ACL mode";
                    }

                    ///nokia-conf/configure/filter/ipv6-filter/entry/interface-sample
                    leaf interface-sample {
                        type boolean;
                        default "true";
                        description "Sample matching traffic if IP interface is set to cflowd interface mode";
                    }

                    ///nokia-conf/configure/filter/ipv6-filter/entry/sample-profile
                    leaf sample-profile {
                        type leafref {
                            path "../../../../cflowd/sample-profile/profile-id";
                        }
                        description "Cflowd sample profile ID to match packets";
                    }

                    ///nokia-conf/configure/filter/ipv6-filter/entry/apply-groups
                    leaf-list apply-groups {
                        type leafref {
                            path "../../../../groups/group/name";
                        }
                        max-elements 8;
                        ordered-by user;
                        description "Apply a configuration group at this level";
                    }

                    ///nokia-conf/configure/filter/ipv6-filter/entry/apply-groups-exclude
                    leaf-list apply-groups-exclude {
                        type leafref {
                            path "../../../../groups/group/name";
                        }
                        max-elements 8;
                        ordered-by user;
                        description "Exclude a configuration group at this level";
                    }

                    ///nokia-conf/configure/filter/ipv6-filter/entry/match
                    container match {
                        description "Enter the match context";

                        ///nokia-conf/configure/filter/ipv6-filter/entry/match/dscp
                        leaf dscp {
                            type types-qos:dscp-name;
                            description "DSCP used as an IP filter match criterion";
                        }

                        ///nokia-conf/configure/filter/ipv6-filter/entry/match/fragment
                        leaf fragment {
                            type enumeration {
                                enum false                          { value 2; }
                                enum true                           { value 3; }
                                enum first-only                     { value 4; }
                                enum non-first-only                 { value 5; }
                            }
                            description "Match criterion for fragmented packages";
                        }

                        ///nokia-conf/configure/filter/ipv6-filter/entry/match/destination-class
                        leaf destination-class {
                            type types-sros:class-index;
                            description "Destination class as a match criterion";
                        }

                        ///nokia-conf/configure/filter/ipv6-filter/entry/match/match-next-header-choice
                        choice match-next-header-choice {
                            ///nokia-conf/configure/filter/ipv6-filter/entry/match/match-next-header-choice/next-header
                            case next-header {

                                ///nokia-conf/configure/filter/ipv6-filter/entry/match/match-next-header-choice/next-header/next-header
                                leaf next-header {
                                    type types-sros:match-ip-protocol;
                                    description "IP protocol to match";
                                }

                            }
                            ///nokia-conf/configure/filter/ipv6-filter/entry/match/match-next-header-choice/next-header-list
                            case next-header-list {

                                ///nokia-conf/configure/filter/ipv6-filter/entry/match/match-next-header-choice/next-header-list/next-header-list
                                leaf next-header-list {
                                    type leafref {
                                        path "../../../../match-list/protocol-list/protocol-list-name";
                                    }
                                    description "Name of the protocol list as a match criterion";
                                }

                            }
                        }
                        ///nokia-conf/configure/filter/ipv6-filter/entry/match/ip-selector
                        choice ip-selector {
                            ///nokia-conf/configure/filter/ipv6-filter/entry/match/ip-selector/src-dst-ip
                            case src-dst-ip {

                                ///nokia-conf/configure/filter/ipv6-filter/entry/match/ip-selector/src-dst-ip/src-ip
                                container src-ip {
                                    description "Enter the src-ip context";

                                    ///nokia-conf/configure/filter/ipv6-filter/entry/match/ip-selector/src-dst-ip/src-ip/match-address-choice
                                    choice match-address-choice {
                                        ///nokia-conf/configure/filter/ipv6-filter/entry/match/ip-selector/src-dst-ip/src-ip/match-address-choice/address-and-prefix-or-mask
                                        case address-and-prefix-or-mask {

                                            ///nokia-conf/configure/filter/ipv6-filter/entry/match/ip-selector/src-dst-ip/src-ip/match-address-choice/address-and-prefix-or-mask/address
                                            leaf address {
                                                type union {
                                                    type types-sros:ipv6-prefix-with-host-bits;
                                                    type types-sros:ipv6-address;
                                                }
                                                description "IPv6 address used as the match criterion";
                                            }

                                            ///nokia-conf/configure/filter/ipv6-filter/entry/match/ip-selector/src-dst-ip/src-ip/match-address-choice/address-and-prefix-or-mask/mask
                                            leaf mask {
                                                type types-sros:ipv6-address;
                                                description "IPv6 address mask used as the match criterion";
                                            }

                                        }
                                        ///nokia-conf/configure/filter/ipv6-filter/entry/match/ip-selector/src-dst-ip/src-ip/match-address-choice/ipv6-prefix-list
                                        case ipv6-prefix-list {

                                            ///nokia-conf/configure/filter/ipv6-filter/entry/match/ip-selector/src-dst-ip/src-ip/match-address-choice/ipv6-prefix-list/ipv6-prefix-list
                                            leaf ipv6-prefix-list {
                                                type leafref {
                                                    path "../../../../../match-list/ipv6-prefix-list/prefix-list-name";
                                                }
                                                description "IPv6 address prefix list used as match criterion";
                                            }

                                        }
                                    }
                                } // container src-ip

                                ///nokia-conf/configure/filter/ipv6-filter/entry/match/ip-selector/src-dst-ip/dst-ip
                                container dst-ip {
                                    description "Enter the dst-ip context";

                                    ///nokia-conf/configure/filter/ipv6-filter/entry/match/ip-selector/src-dst-ip/dst-ip/match-address-choice
                                    choice match-address-choice {
                                        ///nokia-conf/configure/filter/ipv6-filter/entry/match/ip-selector/src-dst-ip/dst-ip/match-address-choice/address-and-prefix-or-mask
                                        case address-and-prefix-or-mask {

                                            ///nokia-conf/configure/filter/ipv6-filter/entry/match/ip-selector/src-dst-ip/dst-ip/match-address-choice/address-and-prefix-or-mask/address
                                            leaf address {
                                                type union {
                                                    type types-sros:ipv6-prefix-with-host-bits;
                                                    type types-sros:ipv6-address;
                                                }
                                                description "IPv6 address used as the match criterion";
                                            }

                                            ///nokia-conf/configure/filter/ipv6-filter/entry/match/ip-selector/src-dst-ip/dst-ip/match-address-choice/address-and-prefix-or-mask/mask
                                            leaf mask {
                                                type types-sros:ipv6-address;
                                                description "IPv6 address mask used as the match criterion";
                                            }

                                        }
                                        ///nokia-conf/configure/filter/ipv6-filter/entry/match/ip-selector/src-dst-ip/dst-ip/match-address-choice/ipv6-prefix-list
                                        case ipv6-prefix-list {

                                            ///nokia-conf/configure/filter/ipv6-filter/entry/match/ip-selector/src-dst-ip/dst-ip/match-address-choice/ipv6-prefix-list/ipv6-prefix-list
                                            leaf ipv6-prefix-list {
                                                type leafref {
                                                    path "../../../../../match-list/ipv6-prefix-list/prefix-list-name";
                                                }
                                                description "IPv6 address prefix list used as match criterion";
                                            }

                                        }
                                    }
                                } // container dst-ip

                            }
                            ///nokia-conf/configure/filter/ipv6-filter/entry/match/ip-selector/ip
                            case ip {

                                ///nokia-conf/configure/filter/ipv6-filter/entry/match/ip-selector/ip/ip
                                container ip {
                                    description "Enter the ip context";

                                    ///nokia-conf/configure/filter/ipv6-filter/entry/match/ip-selector/ip/ip/match-address-choice
                                    choice match-address-choice {
                                        ///nokia-conf/configure/filter/ipv6-filter/entry/match/ip-selector/ip/ip/match-address-choice/address-and-prefix-or-mask
                                        case address-and-prefix-or-mask {

                                            ///nokia-conf/configure/filter/ipv6-filter/entry/match/ip-selector/ip/ip/match-address-choice/address-and-prefix-or-mask/address
                                            leaf address {
                                                type union {
                                                    type types-sros:ipv6-prefix-with-host-bits;
                                                    type types-sros:ipv6-address;
                                                }
                                                description "IPv6 address used as the match criterion";
                                            }

                                            ///nokia-conf/configure/filter/ipv6-filter/entry/match/ip-selector/ip/ip/match-address-choice/address-and-prefix-or-mask/mask
                                            leaf mask {
                                                type types-sros:ipv6-address;
                                                description "IPv6 address mask used as the match criterion";
                                            }

                                        }
                                        ///nokia-conf/configure/filter/ipv6-filter/entry/match/ip-selector/ip/ip/match-address-choice/ipv6-prefix-list
                                        case ipv6-prefix-list {

                                            ///nokia-conf/configure/filter/ipv6-filter/entry/match/ip-selector/ip/ip/match-address-choice/ipv6-prefix-list/ipv6-prefix-list
                                            leaf ipv6-prefix-list {
                                                type leafref {
                                                    path "../../../../../match-list/ipv6-prefix-list/prefix-list-name";
                                                }
                                                description "IPv6 address prefix list used as match criterion";
                                            }

                                        }
                                    }
                                } // container ip

                            }
                        }
                        ///nokia-conf/configure/filter/ipv6-filter/entry/match/port-selector
                        choice port-selector {
                            ///nokia-conf/configure/filter/ipv6-filter/entry/match/port-selector/src-dst-port
                            case src-dst-port {

                                ///nokia-conf/configure/filter/ipv6-filter/entry/match/port-selector/src-dst-port/src-port
                                container src-port {
                                    description "Enter the src-port context";

                                    ///nokia-conf/configure/filter/ipv6-filter/entry/match/port-selector/src-dst-port/src-port/port
                                    choice port {
                                        ///nokia-conf/configure/filter/ipv6-filter/entry/match/port-selector/src-dst-port/src-port/port/eq
                                        case eq {

                                            ///nokia-conf/configure/filter/ipv6-filter/entry/match/port-selector/src-dst-port/src-port/port/eq/eq
                                            leaf eq {
                                                type uint16 {
                                                    range "0..65535";
                                                }
                                                description "Exact match criterion for the port number";
                                            }

                                        }
                                        ///nokia-conf/configure/filter/ipv6-filter/entry/match/port-selector/src-dst-port/src-port/port/lt
                                        case lt {

                                            ///nokia-conf/configure/filter/ipv6-filter/entry/match/port-selector/src-dst-port/src-port/port/lt/lt
                                            leaf lt {
                                                type uint16 {
                                                    range "1..65535";
                                                }
                                                description "Less than match criterion for the port number";
                                            }

                                        }
                                        ///nokia-conf/configure/filter/ipv6-filter/entry/match/port-selector/src-dst-port/src-port/port/gt
                                        case gt {

                                            ///nokia-conf/configure/filter/ipv6-filter/entry/match/port-selector/src-dst-port/src-port/port/gt/gt
                                            leaf gt {
                                                type uint16 {
                                                    range "0..65534";
                                                }
                                                description "Greater than match criterion for the port number";
                                            }

                                        }
                                        ///nokia-conf/configure/filter/ipv6-filter/entry/match/port-selector/src-dst-port/src-port/port/range
                                        case range {

                                            ///nokia-conf/configure/filter/ipv6-filter/entry/match/port-selector/src-dst-port/src-port/port/range/range
                                            container range {
                                                presence "Enable the range context";
                                                description "Enable the range context";

                                                ///nokia-conf/configure/filter/ipv6-filter/entry/match/port-selector/src-dst-port/src-port/port/range/range/start
                                                leaf start {
                                                    type uint16 {
                                                        range "0..65534";
                                                    }
                                                    mandatory true;
                                                    description "Lower bound of the port range as port match criterion";
                                                }

                                                ///nokia-conf/configure/filter/ipv6-filter/entry/match/port-selector/src-dst-port/src-port/port/range/range/end
                                                leaf end {
                                                    type uint16 {
                                                        range "1..65535";
                                                    }
                                                    mandatory true;
                                                    description "Upper bound of the port range as port match criterion";
                                                }

                                            } // container range

                                        }
                                        ///nokia-conf/configure/filter/ipv6-filter/entry/match/port-selector/src-dst-port/src-port/port/port-list
                                        case port-list {

                                            ///nokia-conf/configure/filter/ipv6-filter/entry/match/port-selector/src-dst-port/src-port/port/port-list/port-list
                                            leaf port-list {
                                                type leafref {
                                                    path "../../../../../match-list/port-list/port-list-name";
                                                }
                                                description "Name of the port list as the match criterion";
                                            }

                                        }
                                    }
                                } // container src-port

                                ///nokia-conf/configure/filter/ipv6-filter/entry/match/port-selector/src-dst-port/dst-port
                                container dst-port {
                                    description "Enter the dst-port context";

                                    ///nokia-conf/configure/filter/ipv6-filter/entry/match/port-selector/src-dst-port/dst-port/port
                                    choice port {
                                        ///nokia-conf/configure/filter/ipv6-filter/entry/match/port-selector/src-dst-port/dst-port/port/eq
                                        case eq {

                                            ///nokia-conf/configure/filter/ipv6-filter/entry/match/port-selector/src-dst-port/dst-port/port/eq/eq
                                            leaf eq {
                                                type uint16 {
                                                    range "0..65535";
                                                }
                                                description "Exact match criterion for the port number";
                                            }

                                        }
                                        ///nokia-conf/configure/filter/ipv6-filter/entry/match/port-selector/src-dst-port/dst-port/port/lt
                                        case lt {

                                            ///nokia-conf/configure/filter/ipv6-filter/entry/match/port-selector/src-dst-port/dst-port/port/lt/lt
                                            leaf lt {
                                                type uint16 {
                                                    range "1..65535";
                                                }
                                                description "Less than match criterion for the port number";
                                            }

                                        }
                                        ///nokia-conf/configure/filter/ipv6-filter/entry/match/port-selector/src-dst-port/dst-port/port/gt
                                        case gt {

                                            ///nokia-conf/configure/filter/ipv6-filter/entry/match/port-selector/src-dst-port/dst-port/port/gt/gt
                                            leaf gt {
                                                type uint16 {
                                                    range "0..65534";
                                                }
                                                description "Greater than match criterion for the port number";
                                            }

                                        }
                                        ///nokia-conf/configure/filter/ipv6-filter/entry/match/port-selector/src-dst-port/dst-port/port/range
                                        case range {

                                            ///nokia-conf/configure/filter/ipv6-filter/entry/match/port-selector/src-dst-port/dst-port/port/range/range
                                            container range {
                                                presence "Enable the range context";
                                                description "Enable the range context";

                                                ///nokia-conf/configure/filter/ipv6-filter/entry/match/port-selector/src-dst-port/dst-port/port/range/range/start
                                                leaf start {
                                                    type uint16 {
                                                        range "0..65534";
                                                    }
                                                    mandatory true;
                                                    description "Lower bound of the port range as port match criterion";
                                                }

                                                ///nokia-conf/configure/filter/ipv6-filter/entry/match/port-selector/src-dst-port/dst-port/port/range/range/end
                                                leaf end {
                                                    type uint16 {
                                                        range "1..65535";
                                                    }
                                                    mandatory true;
                                                    description "Upper bound of the port range as port match criterion";
                                                }

                                            } // container range

                                        }
                                        ///nokia-conf/configure/filter/ipv6-filter/entry/match/port-selector/src-dst-port/dst-port/port/port-list
                                        case port-list {

                                            ///nokia-conf/configure/filter/ipv6-filter/entry/match/port-selector/src-dst-port/dst-port/port/port-list/port-list
                                            leaf port-list {
                                                type leafref {
                                                    path "../../../../../match-list/port-list/port-list-name";
                                                }
                                                description "Name of the port list as the match criterion";
                                            }

                                        }
                                    }
                                } // container dst-port

                            }
                            ///nokia-conf/configure/filter/ipv6-filter/entry/match/port-selector/port
                            case port {

                                ///nokia-conf/configure/filter/ipv6-filter/entry/match/port-selector/port/port
                                container port {
                                    description "Enter the port context";

                                    ///nokia-conf/configure/filter/ipv6-filter/entry/match/port-selector/port/port/port
                                    choice port {
                                        ///nokia-conf/configure/filter/ipv6-filter/entry/match/port-selector/port/port/port/eq
                                        case eq {

                                            ///nokia-conf/configure/filter/ipv6-filter/entry/match/port-selector/port/port/port/eq/eq
                                            leaf eq {
                                                type uint16 {
                                                    range "0..65535";
                                                }
                                                description "Exact match criterion for the port number";
                                            }

                                        }
                                        ///nokia-conf/configure/filter/ipv6-filter/entry/match/port-selector/port/port/port/lt
                                        case lt {

                                            ///nokia-conf/configure/filter/ipv6-filter/entry/match/port-selector/port/port/port/lt/lt
                                            leaf lt {
                                                type uint16 {
                                                    range "1..65535";
                                                }
                                                description "Less than match criterion for the port number";
                                            }

                                        }
                                        ///nokia-conf/configure/filter/ipv6-filter/entry/match/port-selector/port/port/port/gt
                                        case gt {

                                            ///nokia-conf/configure/filter/ipv6-filter/entry/match/port-selector/port/port/port/gt/gt
                                            leaf gt {
                                                type uint16 {
                                                    range "0..65534";
                                                }
                                                description "Greater than match criterion for the port number";
                                            }

                                        }
                                        ///nokia-conf/configure/filter/ipv6-filter/entry/match/port-selector/port/port/port/range
                                        case range {

                                            ///nokia-conf/configure/filter/ipv6-filter/entry/match/port-selector/port/port/port/range/range
                                            container range {
                                                presence "Enable the range context";
                                                description "Enable the range context";

                                                ///nokia-conf/configure/filter/ipv6-filter/entry/match/port-selector/port/port/port/range/range/start
                                                leaf start {
                                                    type uint16 {
                                                        range "0..65534";
                                                    }
                                                    mandatory true;
                                                    description "Lower bound of the port range as port match criterion";
                                                }

                                                ///nokia-conf/configure/filter/ipv6-filter/entry/match/port-selector/port/port/port/range/range/end
                                                leaf end {
                                                    type uint16 {
                                                        range "1..65535";
                                                    }
                                                    mandatory true;
                                                    description "Upper bound of the port range as port match criterion";
                                                }

                                            } // container range

                                        }
                                        ///nokia-conf/configure/filter/ipv6-filter/entry/match/port-selector/port/port/port/port-list
                                        case port-list {

                                            ///nokia-conf/configure/filter/ipv6-filter/entry/match/port-selector/port/port/port/port-list/port-list
                                            leaf port-list {
                                                type leafref {
                                                    path "../../../../../match-list/port-list/port-list-name";
                                                }
                                                description "Name of the port list as the match criterion";
                                            }

                                        }
                                    }
                                } // container port

                            }
                        }
                        ///nokia-conf/configure/filter/ipv6-filter/entry/match/match-tcp-flags
                        choice match-tcp-flags {
                            ///nokia-conf/configure/filter/ipv6-filter/entry/match/match-tcp-flags/tcp-established
                            case tcp-established {

                                ///nokia-conf/configure/filter/ipv6-filter/entry/match/match-tcp-flags/tcp-established/tcp-established
                                leaf tcp-established {
                                    type empty;
                                    description "Match packets containing the TCP flag as ACK or RST";
                                }

                            }
                            ///nokia-conf/configure/filter/ipv6-filter/entry/match/match-tcp-flags/tcp-flags
                            case tcp-flags {

                                ///nokia-conf/configure/filter/ipv6-filter/entry/match/match-tcp-flags/tcp-flags/tcp-flags
                                container tcp-flags {
                                    description "Enter the tcp-flags context";

                                    ///nokia-conf/configure/filter/ipv6-filter/entry/match/match-tcp-flags/tcp-flags/tcp-flags/ack
                                    leaf ack {
                                        type boolean;
                                        description "Match TCP ACK as per value of the ACK TCP flag bit";
                                    }

                                    ///nokia-conf/configure/filter/ipv6-filter/entry/match/match-tcp-flags/tcp-flags/tcp-flags/syn
                                    leaf syn {
                                        type boolean;
                                        description "Match TCP SYN as per value of the SYN TCP flag bit";
                                    }

                                    ///nokia-conf/configure/filter/ipv6-filter/entry/match/match-tcp-flags/tcp-flags/tcp-flags/fin
                                    leaf fin {
                                        type boolean;
                                        description "Match TCP FIN as per value of the FIN TCP flag bit";
                                    }

                                    ///nokia-conf/configure/filter/ipv6-filter/entry/match/match-tcp-flags/tcp-flags/tcp-flags/rst
                                    leaf rst {
                                        type boolean;
                                        description "Match TCP RST as per value of the RST TCP flag bit";
                                    }

                                    ///nokia-conf/configure/filter/ipv6-filter/entry/match/match-tcp-flags/tcp-flags/tcp-flags/psh
                                    leaf psh {
                                        type boolean;
                                        description "Match TCP PSH as per value of the PSH TCP flag bit";
                                    }

                                    ///nokia-conf/configure/filter/ipv6-filter/entry/match/match-tcp-flags/tcp-flags/tcp-flags/urg
                                    leaf urg {
                                        type boolean;
                                        description "Match TCP URG as per value of the URG TCP flag bit";
                                    }

                                    ///nokia-conf/configure/filter/ipv6-filter/entry/match/match-tcp-flags/tcp-flags/tcp-flags/ece
                                    leaf ece {
                                        type boolean;
                                        description "Match TCP ECE as per value of the ECE TCP flag bit";
                                    }

                                    ///nokia-conf/configure/filter/ipv6-filter/entry/match/match-tcp-flags/tcp-flags/tcp-flags/cwr
                                    leaf cwr {
                                        type boolean;
                                        description "Match TCP CWR as per value of the CWR TCP flag bit";
                                    }

                                    ///nokia-conf/configure/filter/ipv6-filter/entry/match/match-tcp-flags/tcp-flags/tcp-flags/ns
                                    leaf ns {
                                        type boolean;
                                        description "Match TCP NS as per value of the NS TCP flag bit";
                                    }

                                } // container tcp-flags

                            }
                        }
                        ///nokia-conf/configure/filter/ipv6-filter/entry/match/src-mac
                        container src-mac {
                            presence "Enable the src-mac context";
                            description "Enable the src-mac context";

                            ///nokia-conf/configure/filter/ipv6-filter/entry/match/src-mac/address
                            leaf address {
                                type yang:mac-address;
                                mandatory true;
                                description "MAC address used as the match criterion";
                            }

                            ///nokia-conf/configure/filter/ipv6-filter/entry/match/src-mac/mask
                            leaf mask {
                                type yang:mac-address;
                                default "ff:ff:ff:ff:ff:ff";
                                description "MAC address mask as the match criterion";
                            }

                        } // container src-mac

                        ///nokia-conf/configure/filter/ipv6-filter/entry/match/extension-header
                        container extension-header {
                            description "Enter the extension-header context";

                            ///nokia-conf/configure/filter/ipv6-filter/entry/match/extension-header/ah
                            leaf ah {
                                type boolean;
                                description "Match a packet as per the existence of an AH Extension Header";
                            }

                            ///nokia-conf/configure/filter/ipv6-filter/entry/match/extension-header/esp
                            leaf esp {
                                type boolean;
                                description "Match a packet as per the existence of an Encapsulation security payload extension header";
                            }

                            ///nokia-conf/configure/filter/ipv6-filter/entry/match/extension-header/hop-by-hop
                            leaf hop-by-hop {
                                type boolean;
                                description "Match on Hop-by-Hop Options Extension Header existence";
                            }

                            ///nokia-conf/configure/filter/ipv6-filter/entry/match/extension-header/routing-type0
                            leaf routing-type0 {
                                type boolean;
                                description "Match a packet as per the existence of a routing Extension Header";
                            }

                        } // container extension-header

                        ///nokia-conf/configure/filter/ipv6-filter/entry/match/flow-label
                        container flow-label {
                            presence "Enable the flow-label context";
                            description "Enable the flow-label context";

                            ///nokia-conf/configure/filter/ipv6-filter/entry/match/flow-label/value
                            leaf value {
                                type types-filter:filter-match-flow-label;
                                mandatory true;
                                description "Flow label as a match criterion";
                            }

                            ///nokia-conf/configure/filter/ipv6-filter/entry/match/flow-label/mask
                            leaf mask {
                                type types-filter:filter-match-flow-label {
                                    range "1..1048575";
                                }
                                default "1048575";
                                description "Flow label mask for the IPv6 filter entry";
                            }

                        } // container flow-label

                        ///nokia-conf/configure/filter/ipv6-filter/entry/match/icmp
                        container icmp {
                            description "Enter the icmp context";

                            ///nokia-conf/configure/filter/ipv6-filter/entry/match/icmp/icmp-code
                            choice icmp-code {
                                ///nokia-conf/configure/filter/ipv6-filter/entry/match/icmp/icmp-code/code
                                case code {

                                    ///nokia-conf/configure/filter/ipv6-filter/entry/match/icmp/icmp-code/code/code
                                    leaf code {
                                        type types-filter:ipv6-match-icmp-codes;
                                        description "ICMPv6 code value to match";
                                    }

                                }
                            }
                            ///nokia-conf/configure/filter/ipv6-filter/entry/match/icmp/icmp-type
                            choice icmp-type {
                                ///nokia-conf/configure/filter/ipv6-filter/entry/match/icmp/icmp-type/type
                                case type {

                                    ///nokia-conf/configure/filter/ipv6-filter/entry/match/icmp/icmp-type/type/type
                                    leaf type {
                                        type types-filter:ipv6-match-icmp-types;
                                        description "ICMPv6 type value to match";
                                    }

                                }
                            }
                        } // container icmp

                        ///nokia-conf/configure/filter/ipv6-filter/entry/match/packet-length
                        container packet-length {
                            presence "Enable the packet-length context";
                            description "Enable the packet-length context";

                            ///nokia-conf/configure/filter/ipv6-filter/entry/match/packet-length/packet-length
                            choice packet-length {
                                mandatory true;
                                ///nokia-conf/configure/filter/ipv6-filter/entry/match/packet-length/packet-length/eq
                                case eq {

                                    ///nokia-conf/configure/filter/ipv6-filter/entry/match/packet-length/packet-length/eq/eq
                                    leaf eq {
                                        type types-filter:ipv6-match-packet-length-value;
                                        description "Exact match criterion for the length";
                                    }

                                }
                                ///nokia-conf/configure/filter/ipv6-filter/entry/match/packet-length/packet-length/lt
                                case lt {

                                    ///nokia-conf/configure/filter/ipv6-filter/entry/match/packet-length/packet-length/lt/lt
                                    leaf lt {
                                        type types-filter:ipv6-match-packet-length-lt-value;
                                        description "Less than match criterion for the length";
                                    }

                                }
                                ///nokia-conf/configure/filter/ipv6-filter/entry/match/packet-length/packet-length/gt
                                case gt {

                                    ///nokia-conf/configure/filter/ipv6-filter/entry/match/packet-length/packet-length/gt/gt
                                    leaf gt {
                                        type types-filter:ipv6-match-packet-length-gt-value;
                                        description "Greater than match criterion for the length";
                                    }

                                }
                                ///nokia-conf/configure/filter/ipv6-filter/entry/match/packet-length/packet-length/range
                                case range {

                                    ///nokia-conf/configure/filter/ipv6-filter/entry/match/packet-length/packet-length/range/range
                                    container range {
                                        presence "Enable the range context";
                                        description "Enable the range context";

                                        ///nokia-conf/configure/filter/ipv6-filter/entry/match/packet-length/packet-length/range/range/start
                                        leaf start {
                                            type types-filter:ipv6-match-packet-length-gt-value;
                                            mandatory true;
                                            description "Lower bound of packet length range as match criterion";
                                        }

                                        ///nokia-conf/configure/filter/ipv6-filter/entry/match/packet-length/packet-length/range/range/end
                                        leaf end {
                                            type types-filter:ipv6-match-packet-length-lt-value;
                                            mandatory true;
                                            description "Upper bound of packet length range as match criterion";
                                        }

                                    } // container range

                                }
                            }
                        } // container packet-length

                        ///nokia-conf/configure/filter/ipv6-filter/entry/match/hop-limit
                        container hop-limit {
                            presence "Enable the hop-limit context";
                            description "Enable the hop-limit context";

                            ///nokia-conf/configure/filter/ipv6-filter/entry/match/hop-limit/hop-limit
                            choice hop-limit {
                                mandatory true;
                                ///nokia-conf/configure/filter/ipv6-filter/entry/match/hop-limit/hop-limit/eq
                                case eq {

                                    ///nokia-conf/configure/filter/ipv6-filter/entry/match/hop-limit/hop-limit/eq/eq
                                    leaf eq {
                                        type types-filter:ttl-or-hop-limit-value;
                                        description "Equal to condition match value";
                                    }

                                }
                                ///nokia-conf/configure/filter/ipv6-filter/entry/match/hop-limit/hop-limit/lt
                                case lt {

                                    ///nokia-conf/configure/filter/ipv6-filter/entry/match/hop-limit/hop-limit/lt/lt
                                    leaf lt {
                                        type types-filter:ttl-or-hop-limit-lt-value;
                                        description "Less than condition match value";
                                    }

                                }
                                ///nokia-conf/configure/filter/ipv6-filter/entry/match/hop-limit/hop-limit/gt
                                case gt {

                                    ///nokia-conf/configure/filter/ipv6-filter/entry/match/hop-limit/hop-limit/gt/gt
                                    leaf gt {
                                        type types-filter:ttl-or-hop-limit-gt-value;
                                        description "Greater than condition match value";
                                    }

                                }
                                ///nokia-conf/configure/filter/ipv6-filter/entry/match/hop-limit/hop-limit/range
                                case range {

                                    ///nokia-conf/configure/filter/ipv6-filter/entry/match/hop-limit/hop-limit/range/range
                                    container range {
                                        presence "Enable the range context";
                                        description "Enable the range context";

                                        ///nokia-conf/configure/filter/ipv6-filter/entry/match/hop-limit/hop-limit/range/range/start
                                        leaf start {
                                            type types-filter:ttl-or-hop-limit-gt-value;
                                            mandatory true;
                                            description "Lower bound of the range";
                                        }

                                        ///nokia-conf/configure/filter/ipv6-filter/entry/match/hop-limit/hop-limit/range/range/end
                                        leaf end {
                                            type types-filter:ttl-or-hop-limit-lt-value;
                                            mandatory true;
                                            description "Upper bound of the range";
                                        }

                                    } // container range

                                }
                            }
                        } // container hop-limit

                    } // container match

                    ///nokia-conf/configure/filter/ipv6-filter/entry/action
                    container action {
                        presence "Enable the action context";
                        description "Enable the action context";

                        ///nokia-conf/configure/filter/ipv6-filter/entry/action/fc
                        leaf fc {
                            type types-sros:fc-name;
                            description "Class name to be forwarded for matching packets";
                        }

                        ///nokia-conf/configure/filter/ipv6-filter/entry/action/apply-groups
                        leaf-list apply-groups {
                            type leafref {
                                path "../../../../../groups/group/name";
                            }
                            max-elements 8;
                            ordered-by user;
                            description "Apply a configuration group at this level";
                        }

                        ///nokia-conf/configure/filter/ipv6-filter/entry/action/apply-groups-exclude
                        leaf-list apply-groups-exclude {
                            type leafref {
                                path "../../../../../groups/group/name";
                            }
                            max-elements 8;
                            ordered-by user;
                            description "Exclude a configuration group at this level";
                        }

                        ///nokia-conf/configure/filter/ipv6-filter/entry/action/action
                        choice action {
                            mandatory true;
                            ///nokia-conf/configure/filter/ipv6-filter/entry/action/action/ignore-match
                            case ignore-match {

                                ///nokia-conf/configure/filter/ipv6-filter/entry/action/action/ignore-match/ignore-match
                                leaf ignore-match {
                                    type empty;
                                    description "Ignore match criteria for the entry";
                                }

                            }
                            ///nokia-conf/configure/filter/ipv6-filter/entry/action/action/drop
                            case drop {

                                ///nokia-conf/configure/filter/ipv6-filter/entry/action/action/drop/drop
                                leaf drop {
                                    type empty;
                                    description "Drop a packet matching this entry";
                                }

                            }
                            ///nokia-conf/configure/filter/ipv6-filter/entry/action/action/forward
                            case forward {

                                ///nokia-conf/configure/filter/ipv6-filter/entry/action/action/forward/forward
                                container forward {
                                    description "Enter the forward context";

                                    ///nokia-conf/configure/filter/ipv6-filter/entry/action/action/forward/forward/forward-action
                                    choice forward-action {
                                        ///nokia-conf/configure/filter/ipv6-filter/entry/action/action/forward/forward/forward-action/bonding-connection
                                        case bonding-connection {

                                            ///nokia-conf/configure/filter/ipv6-filter/entry/action/action/forward/forward/forward-action/bonding-connection/bonding-connection
                                            leaf bonding-connection {
                                                type types-submgt:bonding-connection-index;
                                                description "Connection ID over which packet is forwarded";
                                            }

                                        }
                                        ///nokia-conf/configure/filter/ipv6-filter/entry/action/action/forward/forward/forward-action/esi-l2
                                        case esi-l2 {

                                            ///nokia-conf/configure/filter/ipv6-filter/entry/action/action/forward/forward/forward-action/esi-l2/esi-l2
                                            container esi-l2 {
                                                presence "Enable the esi-l2 context";
                                                description "Enable the esi-l2 context";

                                                ///nokia-conf/configure/filter/ipv6-filter/entry/action/action/forward/forward/forward-action/esi-l2/esi-l2/esi-value
                                                leaf esi-value {
                                                    type types-services:ethernet-segment-id {
                                                        pattern "(0x[0-9a-fA-F]{20})|([0-9a-fA-F]{2}(:[0-9a-fA-F]{2}){9})|([0-9a-fA-F]{2}(-[0-9a-fA-F]{2}){9})";
                                                    }
                                                    mandatory true;
                                                    description "ESI of the first ESI-identified appliance";
                                                }

                                                ///nokia-conf/configure/filter/ipv6-filter/entry/action/action/forward/forward/forward-action/esi-l2/esi-l2/vpls
                                                leaf vpls {
                                                    type leafref {
                                                        path "../../../../../../../service/vpls/service-name";
                                                    }
                                                    mandatory true;
                                                    description "VPLS service name";
                                                }

                                            } // container esi-l2

                                        }
                                        ///nokia-conf/configure/filter/ipv6-filter/entry/action/action/forward/forward/forward-action/esi-l3
                                        case esi-l3 {

                                            ///nokia-conf/configure/filter/ipv6-filter/entry/action/action/forward/forward/forward-action/esi-l3/esi-l3
                                            container esi-l3 {
                                                presence "Enable the esi-l3 context";
                                                description "Enable the esi-l3 context";

                                                ///nokia-conf/configure/filter/ipv6-filter/entry/action/action/forward/forward/forward-action/esi-l3/esi-l3/sf-ip
                                                leaf sf-ip {
                                                    type types-sros:ipv6-address;
                                                    sros-ext:immutable;
                                                    mandatory true;
                                                    description "IP address of the service function to forward traffic";
                                                }

                                                ///nokia-conf/configure/filter/ipv6-filter/entry/action/action/forward/forward/forward-action/esi-l3/esi-l3/esi-value
                                                leaf esi-value {
                                                    type types-services:ethernet-segment-id {
                                                        pattern "(0x[0-9a-fA-F]{20})|([0-9a-fA-F]{2}(:[0-9a-fA-F]{2}){9})|([0-9a-fA-F]{2}(-[0-9a-fA-F]{2}){9})";
                                                    }
                                                    sros-ext:immutable;
                                                    mandatory true;
                                                    description "ESI of the first ESI-identified appliance";
                                                }

                                                ///nokia-conf/configure/filter/ipv6-filter/entry/action/action/forward/forward/forward-action/esi-l3/esi-l3/vas-interface
                                                leaf vas-interface {
                                                    type leafref {
                                                        path "../../../../../../../service/vprn[service-name=current()/../vprn]/interface/interface-name";
                                                    }
                                                    sros-ext:immutable;
                                                    mandatory true;
                                                    description "Egress R-VPLS IP interface name";
                                                }

                                                ///nokia-conf/configure/filter/ipv6-filter/entry/action/action/forward/forward/forward-action/esi-l3/esi-l3/vprn
                                                leaf vprn {
                                                    type leafref {
                                                        path "../../../../../../../service/vprn/service-name";
                                                    }
                                                    sros-ext:immutable;
                                                    mandatory true;
                                                    description "VPRN service name";
                                                }

                                            } // container esi-l3

                                        }
                                        ///nokia-conf/configure/filter/ipv6-filter/entry/action/action/forward/forward/forward-action/router
                                        case router {

                                            ///nokia-conf/configure/filter/ipv6-filter/entry/action/action/forward/forward/forward-action/router/router-instance
                                            leaf router-instance {
                                                type string;
                                                sros-ext:immutable;
                                                description "Router name or VPRN service name";
                                            }

                                        }
                                        ///nokia-conf/configure/filter/ipv6-filter/entry/action/action/forward/forward/forward-action/next-hop
                                        case next-hop {

                                            ///nokia-conf/configure/filter/ipv6-filter/entry/action/action/forward/forward/forward-action/next-hop/next-hop
                                            container next-hop {
                                                presence "Enable the next-hop context";
                                                description "Enable the next-hop context";

                                                ///nokia-conf/configure/filter/ipv6-filter/entry/action/action/forward/forward/forward-action/next-hop/next-hop/next-hop
                                                choice next-hop {
                                                    mandatory true;
                                                    ///nokia-conf/configure/filter/ipv6-filter/entry/action/action/forward/forward/forward-action/next-hop/next-hop/next-hop/nh-ip
                                                    case nh-ip {

                                                        ///nokia-conf/configure/filter/ipv6-filter/entry/action/action/forward/forward/forward-action/next-hop/next-hop/next-hop/nh-ip/nh-ip
                                                        container nh-ip {
                                                            presence "Enable the nh-ip context";
                                                            description "Enable the nh-ip context";

                                                            ///nokia-conf/configure/filter/ipv6-filter/entry/action/action/forward/forward/forward-action/next-hop/next-hop/next-hop/nh-ip/nh-ip/indirect
                                                            leaf indirect {
                                                                type boolean;
                                                                default "false";
                                                                description "Allow next hop to be indirectly reachable";
                                                            }

                                                            ///nokia-conf/configure/filter/ipv6-filter/entry/action/action/forward/forward/forward-action/next-hop/next-hop/next-hop/nh-ip/nh-ip/address
                                                            leaf address {
                                                                type types-sros:ipv6-address;
                                                                mandatory true;
                                                                description "IPv6 address of next hop to forward matching packets";
                                                            }

                                                        } // container nh-ip

                                                    }
                                                    ///nokia-conf/configure/filter/ipv6-filter/entry/action/action/forward/forward/forward-action/next-hop/next-hop/next-hop/nh-ip-vrf
                                                    case nh-ip-vrf {

                                                        ///nokia-conf/configure/filter/ipv6-filter/entry/action/action/forward/forward/forward-action/next-hop/next-hop/next-hop/nh-ip-vrf/nh-ip-vrf
                                                        container nh-ip-vrf {
                                                            presence "Enable the nh-ip-vrf context";
                                                            description "Enable the nh-ip-vrf context";

                                                            ///nokia-conf/configure/filter/ipv6-filter/entry/action/action/forward/forward/forward-action/next-hop/next-hop/next-hop/nh-ip-vrf/nh-ip-vrf/indirect
                                                            leaf indirect {
                                                                type boolean;
                                                                default "false";
                                                                description "Allow next hop to be indirectly reachable";
                                                            }

                                                            ///nokia-conf/configure/filter/ipv6-filter/entry/action/action/forward/forward/forward-action/next-hop/next-hop/next-hop/nh-ip-vrf/nh-ip-vrf/router-instance
                                                            leaf router-instance {
                                                                type string;
                                                                sros-ext:immutable;
                                                                mandatory true;
                                                                description "Routing context for route lookup for forwarding packets";
                                                            }

                                                            ///nokia-conf/configure/filter/ipv6-filter/entry/action/action/forward/forward/forward-action/next-hop/next-hop/next-hop/nh-ip-vrf/nh-ip-vrf/address
                                                            leaf address {
                                                                type types-sros:ipv6-address;
                                                                mandatory true;
                                                                description "IPv6 address of next hop to forward matching packets";
                                                            }

                                                        } // container nh-ip-vrf

                                                    }
                                                }
                                            } // container next-hop

                                        }
                                        ///nokia-conf/configure/filter/ipv6-filter/entry/action/action/forward/forward/forward-action/lsp
                                        case lsp {

                                            ///nokia-conf/configure/filter/ipv6-filter/entry/action/action/forward/forward/forward-action/lsp/lsp
                                            leaf lsp {
                                                type types-sros:named-item-64;
                                                description "LSP that is specified to forward a packet matching this entry";
                                            }

                                        }
                                        ///nokia-conf/configure/filter/ipv6-filter/entry/action/action/forward/forward/forward-action/sdp
                                        case sdp {

                                            ///nokia-conf/configure/filter/ipv6-filter/entry/action/action/forward/forward/forward-action/sdp/sdp
                                            container sdp {
                                                presence "Enable the sdp context";
                                                description "Enable the sdp context";

                                                ///nokia-conf/configure/filter/ipv6-filter/entry/action/action/forward/forward/forward-action/sdp/sdp/vpls
                                                leaf vpls {
                                                    type leafref {
                                                        path "../../../../../../../service/vpls/service-name";
                                                    }
                                                    mandatory true;
                                                    description "VPLS associated with the SDP";
                                                }

                                                ///nokia-conf/configure/filter/ipv6-filter/entry/action/action/forward/forward/forward-action/sdp/sdp/sdp-bind-id
                                                leaf sdp-bind-id {
                                                    type types-services:sdp-bind-id;
                                                    mandatory true;
                                                    description "VPLS SDP bind ID used to forward matching packets";
                                                }

                                            } // container sdp

                                        }
                                        ///nokia-conf/configure/filter/ipv6-filter/entry/action/action/forward/forward/forward-action/sap
                                        case sap {

                                            ///nokia-conf/configure/filter/ipv6-filter/entry/action/action/forward/forward/forward-action/sap/sap
                                            container sap {
                                                presence "Enable the sap context";
                                                description "Enable the sap context";

                                                ///nokia-conf/configure/filter/ipv6-filter/entry/action/action/forward/forward/forward-action/sap/sap/vpls
                                                leaf vpls {
                                                    type leafref {
                                                        path "../../../../../../../service/vpls/service-name";
                                                    }
                                                    mandatory true;
                                                    description "VPLS associated with the SAP";
                                                }

                                                ///nokia-conf/configure/filter/ipv6-filter/entry/action/action/forward/forward/forward-action/sap/sap/sap-id
                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                        ///nokia-conf/configure/filter/ipv6-filter/entry/action/action/forward/forward/forward-action/redirect-policy
                                        case redirect-policy {

                                            ///nokia-conf/configure/filter/ipv6-filter/entry/action/action/forward/forward/forward-action/redirect-policy/redirect-policy
                                            leaf redirect-policy {
                                                type leafref {
                                                    path "../../../../../redirect-policy/redirect-policy-name";
                                                }
                                                sros-ext:immutable;
                                                description "Next hop or forward next hop router that forwards a packet that matches this entry";
                                            }

                                        }
                                        ///nokia-conf/configure/filter/ipv6-filter/entry/action/action/forward/forward/forward-action/vprn-target
                                        case vprn-target {

                                            ///nokia-conf/configure/filter/ipv6-filter/entry/action/action/forward/forward/forward-action/vprn-target/vprn-target
                                            container vprn-target {
                                                presence "Enable the vprn-target context";
                                                description "Enable the vprn-target context";

                                                ///nokia-conf/configure/filter/ipv6-filter/entry/action/action/forward/forward/forward-action/vprn-target/vprn-target/bgp-nh
                                                leaf bgp-nh {
                                                    type types-sros:ipv4-address {
                                                        pattern
                                                            "((([0-9]|[1-9][0-9]|1[0-9][0-9]|2[0-4][0-9]|25[0-5])\\.){3}([1-9]|[1-9][0-9]|1[0-9][0-9]|2[0-4][0-9]|25[0-5]))|
                                                                              ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                              ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                              (([1-9]|[1-9][0-9]|1[0-9][0-9]|2[0-4][0-9]|25[0-5]){1}(\\.([0-9]|[1-9][0-9]|1[0-9][0-9]|2[0-4][0-9]|25[0-5])){3})";
                                                    }
                                                    mandatory true;
                                                    description "Target BGP next hop IP address";
                                                }

                                                ///nokia-conf/configure/filter/ipv6-filter/entry/action/action/forward/forward/forward-action/vprn-target/vprn-target/vprn
                                                leaf vprn {
                                                    type leafref {
                                                        path "../../../../../../../service/vprn/service-name";
                                                    }
                                                    mandatory true;
                                                    description "Routing context used for route lookup";
                                                }

                                                ///nokia-conf/configure/filter/ipv6-filter/entry/action/action/forward/forward/forward-action/vprn-target/vprn-target/lsp
                                                leaf lsp {
                                                    type types-sros:named-item-64;
                                                    description "LSP that is specified to forward a packet matching this entry";
                                                }

                                                ///nokia-conf/configure/filter/ipv6-filter/entry/action/action/forward/forward/forward-action/vprn-target/vprn-target/adv-prefix
                                                leaf adv-prefix {
                                                    type types-sros:ipv6-prefix;
                                                    description "Advertised IP prefix for target destination";
                                                }

                                            } // container vprn-target

                                        }
                                        ///nokia-conf/configure/filter/ipv6-filter/entry/action/action/forward/forward/forward-action/gre-tunnel
                                        case gre-tunnel {

                                            ///nokia-conf/configure/filter/ipv6-filter/entry/action/action/forward/forward/forward-action/gre-tunnel/gre-tunnel
                                            leaf gre-tunnel {
                                                type leafref {
                                                    path "../../../../../gre-tunnel-template/gre-tunnel-template-name";
                                                }
                                                description "GRE tunnel template ID that sets the location where an encapsulated matching packet is transported";
                                            }

                                        }
                                        ///nokia-conf/configure/filter/ipv6-filter/entry/action/action/forward/forward/forward-action/mpls-policy
                                        case mpls-policy {

                                            ///nokia-conf/configure/filter/ipv6-filter/entry/action/action/forward/forward/forward-action/mpls-policy/mpls-policy
                                            container mpls-policy {
                                                presence "Enable the mpls-policy context";
                                                description "Enable the mpls-policy context";

                                                ///nokia-conf/configure/filter/ipv6-filter/entry/action/action/forward/forward/forward-action/mpls-policy/mpls-policy/endpoint
                                                leaf endpoint {
                                                    type types-sros:ipv6-unicast-address;
                                                    mandatory true;
                                                    description "MPLS forwarding policy endpoint IPv6 address";
                                                }

                                            } // container mpls-policy

                                        }
                                        ///nokia-conf/configure/filter/ipv6-filter/entry/action/action/forward/forward/forward-action/srte-policy
                                        case srte-policy {

                                            ///nokia-conf/configure/filter/ipv6-filter/entry/action/action/forward/forward/forward-action/srte-policy/srte-policy
                                            container srte-policy {
                                                presence "Enable the srte-policy context";
                                                description "Enable the srte-policy context";

                                                ///nokia-conf/configure/filter/ipv6-filter/entry/action/action/forward/forward/forward-action/srte-policy/srte-policy/endpoint
                                                leaf endpoint {
                                                    type types-sros:ipv6-unicast-or-zero-address;
                                                    mandatory true;
                                                    description "SR-TE policy endpoint IPv6 address";
                                                }

                                                ///nokia-conf/configure/filter/ipv6-filter/entry/action/action/forward/forward/forward-action/srte-policy/srte-policy/color
                                                leaf color {
                                                    type int64 {
                                                        range "0..4294967295";
                                                    }
                                                    mandatory true;
                                                    description "SR-TE policy color ID";
                                                }

                                            } // container srte-policy

                                        }
                                        ///nokia-conf/configure/filter/ipv6-filter/entry/action/action/forward/forward/forward-action/srv6-policy
                                        case srv6-policy {

                                            ///nokia-conf/configure/filter/ipv6-filter/entry/action/action/forward/forward/forward-action/srv6-policy/srv6-policy
                                            container srv6-policy {
                                                presence "Enable the srv6-policy context";
                                                description "Enable the srv6-policy context";

                                                ///nokia-conf/configure/filter/ipv6-filter/entry/action/action/forward/forward/forward-action/srv6-policy/srv6-policy/endpoint
                                                leaf endpoint {
                                                    type types-sros:ipv6-unicast-or-zero-address;
                                                    mandatory true;
                                                    description "SRv6 policy endpoint IPv6 address";
                                                }

                                                ///nokia-conf/configure/filter/ipv6-filter/entry/action/action/forward/forward/forward-action/srv6-policy/srv6-policy/color
                                                leaf color {
                                                    type uint32 {
                                                        range "0..4294967295";
                                                    }
                                                    mandatory true;
                                                    description "SRv6 policy color";
                                                }

                                                ///nokia-conf/configure/filter/ipv6-filter/entry/action/action/forward/forward/forward-action/srv6-policy/srv6-policy/service-sid
                                                leaf service-sid {
                                                    type types-sros:ipv6-unicast-address;
                                                    mandatory true;
                                                    description "SRv6 service segment identifier";
                                                }

                                            } // container srv6-policy

                                        }
                                    }
                                } // container forward

                            }
                            ///nokia-conf/configure/filter/ipv6-filter/entry/action/action/http-redirect
                            case http-redirect {

                                ///nokia-conf/configure/filter/ipv6-filter/entry/action/action/http-redirect/http-redirect
                                container http-redirect {
                                    presence "Enable the http-redirect context";
                                    description "Enable the http-redirect context";

                                    ///nokia-conf/configure/filter/ipv6-filter/entry/action/action/http-redirect/http-redirect/url
                                    leaf url {
                                        type union {
                                            type enumeration {
                                                enum from-cpf                       { value 1; }
                                            }
                                            type types-sros:http-redirect-url;
                                        }
                                        sros-ext:immutable;
                                        mandatory true;
                                        description "URL used for HTTP redirect action";
                                    }

                                    ///nokia-conf/configure/filter/ipv6-filter/entry/action/action/http-redirect/http-redirect/allow-override
                                    leaf allow-override {
                                        type boolean;
                                        default "false";
                                        description "Override the HTTP redirect URL by a RADIUS VSA";
                                    }

                                } // container http-redirect

                            }
                            ///nokia-conf/configure/filter/ipv6-filter/entry/action/action/nat
                            case nat {

                                ///nokia-conf/configure/filter/ipv6-filter/entry/action/action/nat/nat
                                container nat {
                                    presence "Enable the nat context";
                                    description "Enable the nat context";

                                    ///nokia-conf/configure/filter/ipv6-filter/entry/action/action/nat/nat/nat-policy
                                    leaf nat-policy {
                                        type leafref {
                                            path "../../../../../../service/nat/nat-policy/name";
                                        }
                                        sros-ext:isa-auto-clear-on-modify;
                                        description "NAT policy name when action is NAT";
                                    }

                                    ///nokia-conf/configure/filter/ipv6-filter/entry/action/action/nat/nat/nat-type
                                    leaf nat-type {
                                        type types-filter:nat-type;
                                        sros-ext:isa-auto-clear-on-modify;
                                        mandatory true;
                                        description "NAT type to assign when action is NAT";
                                    }

                                } // container nat

                            }
                            ///nokia-conf/configure/filter/ipv6-filter/entry/action/action/tcp-mss-adjust
                            case tcp-mss-adjust {

                                ///nokia-conf/configure/filter/ipv6-filter/entry/action/action/tcp-mss-adjust/tcp-mss-adjust
                                leaf tcp-mss-adjust {
                                    type empty;
                                    description "Adjust MSS option of TCP matching packets to configured value of tcp-mss in router interface context";
                                }

                            }
                            ///nokia-conf/configure/filter/ipv6-filter/entry/action/action/accept
                            case accept {

                                ///nokia-conf/configure/filter/ipv6-filter/entry/action/action/accept/accept
                                leaf accept {
                                    type empty;
                                    description "Accept regular routing to forward a matching packet";
                                }

                            }
                        }
                        ///nokia-conf/configure/filter/ipv6-filter/entry/action/remark
                        container remark {
                            presence "Enable the remark context";
                            description "Enable the remark context";

                            ///nokia-conf/configure/filter/ipv6-filter/entry/action/remark/dscp
                            leaf dscp {
                                type types-qos:dscp-name;
                                mandatory true;
                                description "Destination SAP";
                            }

                        } // container remark

                        ///nokia-conf/configure/filter/ipv6-filter/entry/action/rate-limit
                        container rate-limit {
                            presence "Enable the rate-limit context";
                            description "Enable the rate-limit context";

                            ///nokia-conf/configure/filter/ipv6-filter/entry/action/rate-limit/pir-choice
                            choice pir-choice {
                                mandatory true;
                                ///nokia-conf/configure/filter/ipv6-filter/entry/action/rate-limit/pir-choice/pir-case
                                case pir-case {

                                    ///nokia-conf/configure/filter/ipv6-filter/entry/action/rate-limit/pir-choice/pir-case/pir
                                    leaf pir {
                                        type types-filter:rate-limit-pir-kilobps;
                                        units "kilobps";
                                        description "Peak information rate";
                                    }

                                }
                                ///nokia-conf/configure/filter/ipv6-filter/entry/action/rate-limit/pir-choice/pps-pir-case
                                case pps-pir-case {

                                    ///nokia-conf/configure/filter/ipv6-filter/entry/action/rate-limit/pir-choice/pps-pir-case/pps-pir
                                    leaf pps-pir {
                                        type types-filter:rate-limit-pir-pps;
                                        units "packets per second";
                                        description "Peak information rate";
                                    }

                                }
                            }
                            ///nokia-conf/configure/filter/ipv6-filter/entry/action/rate-limit/criterion-1
                            choice criterion-1 {
                                ///nokia-conf/configure/filter/ipv6-filter/entry/action/rate-limit/criterion-1/hop-limit
                                case hop-limit {

                                    ///nokia-conf/configure/filter/ipv6-filter/entry/action/rate-limit/criterion-1/hop-limit/hop-limit
                                    container hop-limit {
                                        presence "Enable the hop-limit context";
                                        description "Enable the hop-limit context";

                                        ///nokia-conf/configure/filter/ipv6-filter/entry/action/rate-limit/criterion-1/hop-limit/hop-limit/hop-limit
                                        choice hop-limit {
                                            mandatory true;
                                            ///nokia-conf/configure/filter/ipv6-filter/entry/action/rate-limit/criterion-1/hop-limit/hop-limit/hop-limit/eq
                                            case eq {

                                                ///nokia-conf/configure/filter/ipv6-filter/entry/action/rate-limit/criterion-1/hop-limit/hop-limit/hop-limit/eq/eq
                                                leaf eq {
                                                    type types-filter:ttl-or-hop-limit-value;
                                                    description "Equal to condition match value";
                                                }

                                            }
                                            ///nokia-conf/configure/filter/ipv6-filter/entry/action/rate-limit/criterion-1/hop-limit/hop-limit/hop-limit/lt
                                            case lt {

                                                ///nokia-conf/configure/filter/ipv6-filter/entry/action/rate-limit/criterion-1/hop-limit/hop-limit/hop-limit/lt/lt
                                                leaf lt {
                                                    type types-filter:ttl-or-hop-limit-lt-value;
                                                    description "Less than condition match value";
                                                }

                                            }
                                            ///nokia-conf/configure/filter/ipv6-filter/entry/action/rate-limit/criterion-1/hop-limit/hop-limit/hop-limit/gt
                                            case gt {

                                                ///nokia-conf/configure/filter/ipv6-filter/entry/action/rate-limit/criterion-1/hop-limit/hop-limit/hop-limit/gt/gt
                                                leaf gt {
                                                    type types-filter:ttl-or-hop-limit-gt-value;
                                                    description "Greater than condition match value";
                                                }

                                            }
                                            ///nokia-conf/configure/filter/ipv6-filter/entry/action/rate-limit/criterion-1/hop-limit/hop-limit/hop-limit/range
                                            case range {

                                                ///nokia-conf/configure/filter/ipv6-filter/entry/action/rate-limit/criterion-1/hop-limit/hop-limit/hop-limit/range/range
                                                container range {
                                                    presence "Enable the range context";
                                                    description "Enable the range context";

                                                    ///nokia-conf/configure/filter/ipv6-filter/entry/action/rate-limit/criterion-1/hop-limit/hop-limit/hop-limit/range/range/start
                                                    leaf start {
                                                        type types-filter:ttl-or-hop-limit-gt-value;
                                                        mandatory true;
                                                        description "Lower bound of the range";
                                                    }

                                                    ///nokia-conf/configure/filter/ipv6-filter/entry/action/rate-limit/criterion-1/hop-limit/hop-limit/hop-limit/range/range/end
                                                    leaf end {
                                                        type types-filter:ttl-or-hop-limit-lt-value;
                                                        mandatory true;
                                                        description "Upper bound of the range";
                                                    }

                                                } // container range

                                            }
                                        }
                                    } // container hop-limit

                                }
                                ///nokia-conf/configure/filter/ipv6-filter/entry/action/rate-limit/criterion-1/payload-length
                                case payload-length {

                                    ///nokia-conf/configure/filter/ipv6-filter/entry/action/rate-limit/criterion-1/payload-length/payload-length
                                    container payload-length {
                                        presence "Enable the payload-length context";
                                        description "Enable the payload-length context";

                                        ///nokia-conf/configure/filter/ipv6-filter/entry/action/rate-limit/criterion-1/payload-length/payload-length/payload-length
                                        choice payload-length {
                                            mandatory true;
                                            ///nokia-conf/configure/filter/ipv6-filter/entry/action/rate-limit/criterion-1/payload-length/payload-length/payload-length/eq
                                            case eq {

                                                ///nokia-conf/configure/filter/ipv6-filter/entry/action/rate-limit/criterion-1/payload-length/payload-length/payload-length/eq/eq
                                                leaf eq {
                                                    type types-filter:pkt-len-or-payload-len-value;
                                                    description "Exact match criterion for the length";
                                                }

                                            }
                                            ///nokia-conf/configure/filter/ipv6-filter/entry/action/rate-limit/criterion-1/payload-length/payload-length/payload-length/lt
                                            case lt {

                                                ///nokia-conf/configure/filter/ipv6-filter/entry/action/rate-limit/criterion-1/payload-length/payload-length/payload-length/lt/lt
                                                leaf lt {
                                                    type types-filter:pkt-len-or-payload-len-lt-value;
                                                    description "Less than match criterion for the length";
                                                }

                                            }
                                            ///nokia-conf/configure/filter/ipv6-filter/entry/action/rate-limit/criterion-1/payload-length/payload-length/payload-length/gt
                                            case gt {

                                                ///nokia-conf/configure/filter/ipv6-filter/entry/action/rate-limit/criterion-1/payload-length/payload-length/payload-length/gt/gt
                                                leaf gt {
                                                    type types-filter:pkt-len-or-payload-len-gt-value;
                                                    description "Greater than match criterion for the length";
                                                }

                                            }
                                            ///nokia-conf/configure/filter/ipv6-filter/entry/action/rate-limit/criterion-1/payload-length/payload-length/payload-length/range
                                            case range {

                                                ///nokia-conf/configure/filter/ipv6-filter/entry/action/rate-limit/criterion-1/payload-length/payload-length/payload-length/range/range
                                                container range {
                                                    presence "Enable the range context";
                                                    description "Enable the range context";

                                                    ///nokia-conf/configure/filter/ipv6-filter/entry/action/rate-limit/criterion-1/payload-length/payload-length/payload-length/range/range/start
                                                    leaf start {
                                                        type types-filter:pkt-len-or-payload-len-gt-value;
                                                        mandatory true;
                                                        description "Lower bound of the length range";
                                                    }

                                                    ///nokia-conf/configure/filter/ipv6-filter/entry/action/rate-limit/criterion-1/payload-length/payload-length/payload-length/range/range/end
                                                    leaf end {
                                                        type types-filter:pkt-len-or-payload-len-lt-value;
                                                        mandatory true;
                                                        description "Upper bound of the length range";
                                                    }

                                                } // container range

                                            }
                                        }
                                    } // container payload-length

                                }
                            }
                            ///nokia-conf/configure/filter/ipv6-filter/entry/action/rate-limit/choice2
                            choice choice2 {
                                ///nokia-conf/configure/filter/ipv6-filter/entry/action/rate-limit/choice2/extracted-traffic-case
                                case extracted-traffic-case {

                                    ///nokia-conf/configure/filter/ipv6-filter/entry/action/rate-limit/choice2/extracted-traffic-case/extracted-traffic
                                    leaf extracted-traffic {
                                        type empty;
                                        description "Limit the rate of traffic extracted to the CPM";
                                    }

                                }
                            }
                            ///nokia-conf/configure/filter/ipv6-filter/entry/action/rate-limit/pattern
                            container pattern {
                                presence "Enable the pattern context";
                                description "Enable the pattern context";

                                ///nokia-conf/configure/filter/ipv6-filter/entry/action/rate-limit/pattern/expression
                                leaf expression {
                                    type types-sros:hex-string {
                                        length "3..18";
                                    }
                                    mandatory true;
                                    description "Pattern expression to match";
                                }

                                ///nokia-conf/configure/filter/ipv6-filter/entry/action/rate-limit/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ipv6-filter/entry/action/rate-limit/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ipv6-filter/entry/action/rate-limit/pattern/offset-value
                                leaf offset-value {
                                    type int32 {
                                        range "0..255";
                                    }
                                    mandatory true;
                                    description "Offset value for the pattern expression";
                                }

                            } // container pattern

                        } // container rate-limit

                        ///nokia-conf/configure/filter/ipv6-filter/entry/action/drop-when
                        container drop-when {
                            presence "Enable the drop-when context";
                            description "Enable the drop-when context";

                            ///nokia-conf/configure/filter/ipv6-filter/entry/action/drop-when/criterion-1
                            choice criterion-1 {
                                ///nokia-conf/configure/filter/ipv6-filter/entry/action/drop-when/criterion-1/hop-limit
                                case hop-limit {

                                    ///nokia-conf/configure/filter/ipv6-filter/entry/action/drop-when/criterion-1/hop-limit/hop-limit
                                    container hop-limit {
                                        presence "Enable the hop-limit context";
                                        description "Enable the hop-limit context";

                                        ///nokia-conf/configure/filter/ipv6-filter/entry/action/drop-when/criterion-1/hop-limit/hop-limit/hop-limit
                                        choice hop-limit {
                                            mandatory true;
                                            ///nokia-conf/configure/filter/ipv6-filter/entry/action/drop-when/criterion-1/hop-limit/hop-limit/hop-limit/eq
                                            case eq {

                                                ///nokia-conf/configure/filter/ipv6-filter/entry/action/drop-when/criterion-1/hop-limit/hop-limit/hop-limit/eq/eq
                                                leaf eq {
                                                    type types-filter:ttl-or-hop-limit-value;
                                                    description "Equal to condition match value";
                                                }

                                            }
                                            ///nokia-conf/configure/filter/ipv6-filter/entry/action/drop-when/criterion-1/hop-limit/hop-limit/hop-limit/lt
                                            case lt {

                                                ///nokia-conf/configure/filter/ipv6-filter/entry/action/drop-when/criterion-1/hop-limit/hop-limit/hop-limit/lt/lt
                                                leaf lt {
                                                    type types-filter:ttl-or-hop-limit-lt-value;
                                                    description "Less than condition match value";
                                                }

                                            }
                                            ///nokia-conf/configure/filter/ipv6-filter/entry/action/drop-when/criterion-1/hop-limit/hop-limit/hop-limit/gt
                                            case gt {

                                                ///nokia-conf/configure/filter/ipv6-filter/entry/action/drop-when/criterion-1/hop-limit/hop-limit/hop-limit/gt/gt
                                                leaf gt {
                                                    type types-filter:ttl-or-hop-limit-gt-value;
                                                    description "Greater than condition match value";
                                                }

                                            }
                                            ///nokia-conf/configure/filter/ipv6-filter/entry/action/drop-when/criterion-1/hop-limit/hop-limit/hop-limit/range
                                            case range {

                                                ///nokia-conf/configure/filter/ipv6-filter/entry/action/drop-when/criterion-1/hop-limit/hop-limit/hop-limit/range/range
                                                container range {
                                                    presence "Enable the range context";
                                                    description "Enable the range context";

                                                    ///nokia-conf/configure/filter/ipv6-filter/entry/action/drop-when/criterion-1/hop-limit/hop-limit/hop-limit/range/range/start
                                                    leaf start {
                                                        type types-filter:ttl-or-hop-limit-gt-value;
                                                        mandatory true;
                                                        description "Lower bound of the range";
                                                    }

                                                    ///nokia-conf/configure/filter/ipv6-filter/entry/action/drop-when/criterion-1/hop-limit/hop-limit/hop-limit/range/range/end
                                                    leaf end {
                                                        type types-filter:ttl-or-hop-limit-lt-value;
                                                        mandatory true;
                                                        description "Upper bound of the range";
                                                    }

                                                } // container range

                                            }
                                        }
                                    } // container hop-limit

                                }
                                ///nokia-conf/configure/filter/ipv6-filter/entry/action/drop-when/criterion-1/payload-length
                                case payload-length {

                                    ///nokia-conf/configure/filter/ipv6-filter/entry/action/drop-when/criterion-1/payload-length/payload-length
                                    container payload-length {
                                        presence "Enable the payload-length context";
                                        description "Enable the payload-length context";

                                        ///nokia-conf/configure/filter/ipv6-filter/entry/action/drop-when/criterion-1/payload-length/payload-length/payload-length
                                        choice payload-length {
                                            mandatory true;
                                            ///nokia-conf/configure/filter/ipv6-filter/entry/action/drop-when/criterion-1/payload-length/payload-length/payload-length/eq
                                            case eq {

                                                ///nokia-conf/configure/filter/ipv6-filter/entry/action/drop-when/criterion-1/payload-length/payload-length/payload-length/eq/eq
                                                leaf eq {
                                                    type types-filter:pkt-len-or-payload-len-value;
                                                    description "Exact match criterion for the length";
                                                }

                                            }
                                            ///nokia-conf/configure/filter/ipv6-filter/entry/action/drop-when/criterion-1/payload-length/payload-length/payload-length/lt
                                            case lt {

                                                ///nokia-conf/configure/filter/ipv6-filter/entry/action/drop-when/criterion-1/payload-length/payload-length/payload-length/lt/lt
                                                leaf lt {
                                                    type types-filter:pkt-len-or-payload-len-lt-value;
                                                    description "Less than match criterion for the length";
                                                }

                                            }
                                            ///nokia-conf/configure/filter/ipv6-filter/entry/action/drop-when/criterion-1/payload-length/payload-length/payload-length/gt
                                            case gt {

                                                ///nokia-conf/configure/filter/ipv6-filter/entry/action/drop-when/criterion-1/payload-length/payload-length/payload-length/gt/gt
                                                leaf gt {
                                                    type types-filter:pkt-len-or-payload-len-gt-value;
                                                    description "Greater than match criterion for the length";
                                                }

                                            }
                                            ///nokia-conf/configure/filter/ipv6-filter/entry/action/drop-when/criterion-1/payload-length/payload-length/payload-length/range
                                            case range {

                                                ///nokia-conf/configure/filter/ipv6-filter/entry/action/drop-when/criterion-1/payload-length/payload-length/payload-length/range/range
                                                container range {
                                                    presence "Enable the range context";
                                                    description "Enable the range context";

                                                    ///nokia-conf/configure/filter/ipv6-filter/entry/action/drop-when/criterion-1/payload-length/payload-length/payload-length/range/range/start
                                                    leaf start {
                                                        type types-filter:pkt-len-or-payload-len-gt-value;
                                                        mandatory true;
                                                        description "Lower bound of the length range";
                                                    }

                                                    ///nokia-conf/configure/filter/ipv6-filter/entry/action/drop-when/criterion-1/payload-length/payload-length/payload-length/range/range/end
                                                    leaf end {
                                                        type types-filter:pkt-len-or-payload-len-lt-value;
                                                        mandatory true;
                                                        description "Upper bound of the length range";
                                                    }

                                                } // container range

                                            }
                                        }
                                    } // container payload-length

                                }
                            }
                            ///nokia-conf/configure/filter/ipv6-filter/entry/action/drop-when/criterion-2
                            choice criterion-2 {
                                ///nokia-conf/configure/filter/ipv6-filter/entry/action/drop-when/criterion-2/extracted-traffic
                                case extracted-traffic {

                                    ///nokia-conf/configure/filter/ipv6-filter/entry/action/drop-when/criterion-2/extracted-traffic/extracted-traffic
                                    leaf extracted-traffic {
                                        type empty;
                                        description "Drop traffic extracted to CPM";
                                    }

                                }
                            }
                            ///nokia-conf/configure/filter/ipv6-filter/entry/action/drop-when/pattern
                            container pattern {
                                presence "Enable the pattern context";
                                description "Enable the pattern context";

                                ///nokia-conf/configure/filter/ipv6-filter/entry/action/drop-when/pattern/expression
                                leaf expression {
                                    type types-sros:hex-string {
                                        length "3..18";
                                    }
                                    mandatory true;
                                    description "Pattern expression to match";
                                }

                                ///nokia-conf/configure/filter/ipv6-filter/entry/action/drop-when/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ipv6-filter/entry/action/drop-when/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ipv6-filter/entry/action/drop-when/pattern/offset-value
                                leaf offset-value {
                                    type int32 {
                                        range "0..255";
                                    }
                                    mandatory true;
                                    description "Offset value for the pattern expression";
                                }

                            } // container pattern

                        } // container drop-when

                        ///nokia-conf/configure/filter/ipv6-filter/entry/action/accept-when
                        container accept-when {
                            presence "Enable the accept-when context";
                            description "Enable the accept-when context";

                            ///nokia-conf/configure/filter/ipv6-filter/entry/action/accept-when/pattern
                            container pattern {
                                presence "Enable the pattern context";
                                description "Enable the pattern context";

                                ///nokia-conf/configure/filter/ipv6-filter/entry/action/accept-when/pattern/expression
                                leaf expression {
                                    type types-sros:hex-string {
                                        length "3..18";
                                    }
                                    mandatory true;
                                    description "Pattern expression to match";
                                }

                                ///nokia-conf/configure/filter/ipv6-filter/entry/action/accept-when/pattern/mask
                                leaf mask {
                                    type types-sros:hex-string {
                                        length "3..18";
                                        pattern "0x[a-fA-F0-9]*[a-fA-F1-9]+[a-fA-F0-9]*" {
                                            error-message "The value has to be in hex-string format with prefix '0x' and must not be all zeros.";
                                        }
                                    }
                                    mandatory true;
                                    description "Mask for the pattern expression";
                                }

                                ///nokia-conf/configure/filter/ipv6-filter/entry/action/accept-when/pattern/offset-type
                                leaf offset-type {
                                    type enumeration {
                                        enum layer-3                        { value 1; }
                                        enum layer-4                        { value 2; }
                                        enum data                           { value 3; }
                                        enum dns-qtype                      { value 4; }
                                    }
                                    mandatory true;
                                    description "Starting point reference for offset value of pattern";
                                }

                                ///nokia-conf/configure/filter/ipv6-filter/entry/action/accept-when/pattern/offset-value
                                leaf offset-value {
                                    type int32 {
                                        range "0..255";
                                    }
                                    mandatory true;
                                    description "Offset value for the pattern expression";
                                }

                            } // container pattern

                        } // container accept-when

                        ///nokia-conf/configure/filter/ipv6-filter/entry/action/secondary
                        container secondary {
                            presence "Enable the secondary context";
                            description "Enable the secondary context";

                            ///nokia-conf/configure/filter/ipv6-filter/entry/action/secondary/apply-groups
                            leaf-list apply-groups {
                                type leafref {
                                    path "../../../../../../groups/group/name";
                                }
                                max-elements 8;
                                ordered-by user;
                                description "Apply a configuration group at this level";
                            }

                            ///nokia-conf/configure/filter/ipv6-filter/entry/action/secondary/apply-groups-exclude
                            leaf-list apply-groups-exclude {
                                type leafref {
                                    path "../../../../../../groups/group/name";
                                }
                                max-elements 8;
                                ordered-by user;
                                description "Exclude a configuration group at this level";
                            }

                            ///nokia-conf/configure/filter/ipv6-filter/entry/action/secondary/action
                            choice action {
                                mandatory true;
                                ///nokia-conf/configure/filter/ipv6-filter/entry/action/secondary/action/forward
                                case forward {

                                    ///nokia-conf/configure/filter/ipv6-filter/entry/action/secondary/action/forward/forward
                                    container forward {
                                        description "Enter the forward context";

                                        ///nokia-conf/configure/filter/ipv6-filter/entry/action/secondary/action/forward/forward/forward-action
                                        choice forward-action {
                                            ///nokia-conf/configure/filter/ipv6-filter/entry/action/secondary/action/forward/forward/forward-action/next-hop
                                            case next-hop {

                                                ///nokia-conf/configure/filter/ipv6-filter/entry/action/secondary/action/forward/forward/forward-action/next-hop/next-hop
                                                container next-hop {
                                                    presence "Enable the next-hop context";
                                                    description "Enable the next-hop context";

                                                    ///nokia-conf/configure/filter/ipv6-filter/entry/action/secondary/action/forward/forward/forward-action/next-hop/next-hop/next-hop
                                                    choice next-hop {
                                                        mandatory true;
                                                        ///nokia-conf/configure/filter/ipv6-filter/entry/action/secondary/action/forward/forward/forward-action/next-hop/next-hop/next-hop/nh-ip-vrf
                                                        case nh-ip-vrf {

                                                            ///nokia-conf/configure/filter/ipv6-filter/entry/action/secondary/action/forward/forward/forward-action/next-hop/next-hop/next-hop/nh-ip-vrf/nh-ip-vrf
                                                            container nh-ip-vrf {
                                                                presence "Enable the nh-ip-vrf context";
                                                                description "Enable the nh-ip-vrf context";

                                                                ///nokia-conf/configure/filter/ipv6-filter/entry/action/secondary/action/forward/forward/forward-action/next-hop/next-hop/next-hop/nh-ip-vrf/nh-ip-vrf/indirect
                                                                leaf indirect {
                                                                    type boolean;
                                                                    default "false";
                                                                    description "Allow next hop to be indirectly reachable";
                                                                }

                                                                ///nokia-conf/configure/filter/ipv6-filter/entry/action/secondary/action/forward/forward/forward-action/next-hop/next-hop/next-hop/nh-ip-vrf/nh-ip-vrf/router-instance
                                                                leaf router-instance {
                                                                    type string;
                                                                    sros-ext:immutable;
                                                                    mandatory true;
                                                                    description "Routing context for route lookup for forwarding packets";
                                                                }

                                                                ///nokia-conf/configure/filter/ipv6-filter/entry/action/secondary/action/forward/forward/forward-action/next-hop/next-hop/next-hop/nh-ip-vrf/nh-ip-vrf/address
                                                                leaf address {
                                                                    type types-sros:ipv6-address;
                                                                    mandatory true;
                                                                    description "IPv6 address of next hop to forward matching packets";
                                                                }

                                                            } // container nh-ip-vrf

                                                        }
                                                    }
                                                } // container next-hop

                                            }
                                            ///nokia-conf/configure/filter/ipv6-filter/entry/action/secondary/action/forward/forward/forward-action/sdp
                                            case sdp {

                                                ///nokia-conf/configure/filter/ipv6-filter/entry/action/secondary/action/forward/forward/forward-action/sdp/sdp
                                                container sdp {
                                                    presence "Enable the sdp context";
                                                    description "Enable the sdp context";

                                                    ///nokia-conf/configure/filter/ipv6-filter/entry/action/secondary/action/forward/forward/forward-action/sdp/sdp/vpls
                                                    leaf vpls {
                                                        type leafref {
                                                            path "../../../../../../../../service/vpls/service-name";
                                                        }
                                                        mandatory true;
                                                        description "VPLS associated with the SDP";
                                                    }

                                                    ///nokia-conf/configure/filter/ipv6-filter/entry/action/secondary/action/forward/forward/forward-action/sdp/sdp/sdp-bind-id
                                                    leaf sdp-bind-id {
                                                        type types-services:sdp-bind-id;
                                                        sros-ext:immutable;
                                                        mandatory true;
                                                        description "VPLS SDP bind ID used to forward matching packets";
                                                    }

                                                } // container sdp

                                            }
                                            ///nokia-conf/configure/filter/ipv6-filter/entry/action/secondary/action/forward/forward/forward-action/sap
                                            case sap {

                                                ///nokia-conf/configure/filter/ipv6-filter/entry/action/secondary/action/forward/forward/forward-action/sap/sap
                                                container sap {
                                                    presence "Enable the sap context";
                                                    description "Enable the sap context";

                                                    ///nokia-conf/configure/filter/ipv6-filter/entry/action/secondary/action/forward/forward/forward-action/sap/sap/vpls
                                                    leaf vpls {
                                                        type leafref {
                                                            path "../../../../../../../../service/vpls/service-name";
                                                        }
                                                        mandatory true;
                                                        description "VPLS the sdp-bind-id belongs to";
                                                    }

                                                    ///nokia-conf/configure/filter/ipv6-filter/entry/action/secondary/action/forward/forward/forward-action/sap/sap/sap-id
                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                            ///nokia-conf/configure/filter/ipv6-filter/entry/action/secondary/action/forward/forward/forward-action/vprn-target
                                            case vprn-target {

                                                ///nokia-conf/configure/filter/ipv6-filter/entry/action/secondary/action/forward/forward/forward-action/vprn-target/vprn-target
                                                container vprn-target {
                                                    presence "Enable the vprn-target context";
                                                    description "Enable the vprn-target context";

                                                    ///nokia-conf/configure/filter/ipv6-filter/entry/action/secondary/action/forward/forward/forward-action/vprn-target/vprn-target/bgp-nh
                                                    leaf bgp-nh {
                                                        type types-sros:ipv4-address {
                                                            pattern
                                                                "((([0-9]|[1-9][0-9]|1[0-9][0-9]|2[0-4][0-9]|25[0-5])\\.){3}([1-9]|[1-9][0-9]|1[0-9][0-9]|2[0-4][0-9]|25[0-5]))|
                                                                                  ((([0-9]|[1-9][0-9]|1[0-9][0-9]|2[0-4][0-9]|25[0-5])\\.){2}(([1-9]|[1-9][0-9]|1[0-9][0-9]|2[0-4][0-9]|25[0-5])\\.){1}([0-9]|[1-9][0-9]|1[0-9][0-9]|2[0-4][0-9]|25[0-5]){1})|
                                                                                  ((([0-9]|[1-9][0-9]|1[0-9][0-9]|2[0-4][0-9]|25[0-5])\\.){1}([1-9]|[1-9][0-9]|1[0-9][0-9]|2[0-4][0-9]|25[0-5]){1}(\\.([0-9]|[1-9][0-9]|1[0-9][0-9]|2[0-4][0-9]|25[0-5])){2})|
                                                                                  (([1-9]|[1-9][0-9]|1[0-9][0-9]|2[0-4][0-9]|25[0-5]){1}(\\.([0-9]|[1-9][0-9]|1[0-9][0-9]|2[0-4][0-9]|25[0-5])){3})";
                                                        }
                                                        mandatory true;
                                                        description "Target BGP next hop IP address";
                                                    }

                                                    ///nokia-conf/configure/filter/ipv6-filter/entry/action/secondary/action/forward/forward/forward-action/vprn-target/vprn-target/vprn
                                                    leaf vprn {
                                                        type leafref {
                                                            path "../../../../../../../../service/vprn/service-name";
                                                        }
                                                        mandatory true;
                                                        description "Routing context used for route lookup";
                                                    }

                                                    ///nokia-conf/configure/filter/ipv6-filter/entry/action/secondary/action/forward/forward/forward-action/vprn-target/vprn-target/lsp
                                                    leaf lsp {
                                                        type types-sros:named-item-64;
                                                        description "LSP that is specified to forward a packet matching this entry";
                                                    }

                                                    ///nokia-conf/configure/filter/ipv6-filter/entry/action/secondary/action/forward/forward/forward-action/vprn-target/vprn-target/adv-prefix
                                                    leaf adv-prefix {
                                                        type types-sros:ipv6-prefix;
                                                        description "Advertised IP prefix for the target destination";
                                                    }

                                                } // container vprn-target

                                            }
                                        }
                                    } // container forward

                                }
                            }
                            ///nokia-conf/configure/filter/ipv6-filter/entry/action/secondary/remark
                            container remark {
                                presence "Enable the remark context";
                                description "Enable the remark context";

                                ///nokia-conf/configure/filter/ipv6-filter/entry/action/secondary/remark/dscp
                                leaf dscp {
                                    type types-qos:dscp-name;
                                    mandatory true;
                                    description "Destination SAP";
                                }

                            } // container remark

                        } // container secondary

                    } // container action

                } // list entry

                ///nokia-conf/configure/filter/ipv6-filter/embed
                container embed {
                    description "Enter the embed context";

                    ///nokia-conf/configure/filter/ipv6-filter/embed/filter
                    list filter {
                        key "name offset";
                        description "Enter the filter list instance";

                        ///nokia-conf/configure/filter/ipv6-filter/embed/filter/name
                        leaf name {
                            type leafref {
                                path "../../../../ipv6-filter/filter-name";
                            }
                            description "IPv6 policy to be embedded in the filter";
                        }

                        ///nokia-conf/configure/filter/ipv6-filter/embed/filter/offset
                        leaf offset {
                            type types-filter:embed-offset {
                                range "0..2097150";
                            }
                            description "Offset of the inserted entries";
                        }

                        ///nokia-conf/configure/filter/ipv6-filter/embed/filter/admin-state
                        leaf admin-state {
                            type types-sros:admin-state;
                            default "enable";
                            description "Administrative state of the embedded filter";
                        }

                        ///nokia-conf/configure/filter/ipv6-filter/embed/filter/apply-groups
                        leaf-list apply-groups {
                            type leafref {
                                path "../../../../../groups/group/name";
                            }
                            max-elements 8;
                            ordered-by user;
                            description "Apply a configuration group at this level";
                        }

                        ///nokia-conf/configure/filter/ipv6-filter/embed/filter/apply-groups-exclude
                        leaf-list apply-groups-exclude {
                            type leafref {
                                path "../../../../../groups/group/name";
                            }
                            max-elements 8;
                            ordered-by user;
                            description "Exclude a configuration group at this level";
                        }

                    } // list filter

                    ///nokia-conf/configure/filter/ipv6-filter/embed/flowspec
                    list flowspec {
                        key "offset";
                        description "Enter the flowspec list instance";

                        ///nokia-conf/configure/filter/ipv6-filter/embed/flowspec/offset
                        leaf offset {
                            type types-filter:embed-offset;
                            description "Offset of the inserted entries";
                        }

                        ///nokia-conf/configure/filter/ipv6-filter/embed/flowspec/group
                        leaf group {
                            type uint32 {
                                range "0..16383";
                            }
                            sros-ext:immutable;
                            description "Interface group ID for an external configured set of flowspec rules";
                        }

                        ///nokia-conf/configure/filter/ipv6-filter/embed/flowspec/router-instance
                        leaf router-instance {
                            type string;
                            sros-ext:immutable;
                            mandatory true;
                            description "Virtual router for an external configured set of flowspec rules";
                        }

                        ///nokia-conf/configure/filter/ipv6-filter/embed/flowspec/admin-state
                        leaf admin-state {
                            type types-sros:admin-state;
                            default "enable";
                            description "Administrative state of the embedded filter";
                        }

                        ///nokia-conf/configure/filter/ipv6-filter/embed/flowspec/apply-groups
                        leaf-list apply-groups {
                            type leafref {
                                path "../../../../../groups/group/name";
                            }
                            max-elements 8;
                            ordered-by user;
                            description "Apply a configuration group at this level";
                        }

                        ///nokia-conf/configure/filter/ipv6-filter/embed/flowspec/apply-groups-exclude
                        leaf-list apply-groups-exclude {
                            type leafref {
                                path "../../../../../groups/group/name";
                            }
                            max-elements 8;
                            ordered-by user;
                            description "Exclude a configuration group at this level";
                        }

                    } // list flowspec

                    ///nokia-conf/configure/filter/ipv6-filter/embed/openflow
                    list openflow {
                        key "of-switch offset";
                        description "Enter the openflow list instance";

                        ///nokia-conf/configure/filter/ipv6-filter/embed/openflow/of-switch
                        leaf of-switch {
                            type leafref {
                                path "../../../../../openflow/of-switch/name";
                            }
                            description "Referenced Hybrid OpenFlow Switch (OFS) name";
                        }

                        ///nokia-conf/configure/filter/ipv6-filter/embed/openflow/offset
                        leaf offset {
                            type types-filter:embed-offset {
                                range "0..2097150";
                            }
                            description "Offset of the inserted entries";
                        }

                        ///nokia-conf/configure/filter/ipv6-filter/embed/openflow/admin-state
                        leaf admin-state {
                            type types-sros:admin-state;
                            default "enable";
                            description "Administrative state of the embedded filter";
                        }

                        ///nokia-conf/configure/filter/ipv6-filter/embed/openflow/apply-groups
                        leaf-list apply-groups {
                            type leafref {
                                path "../../../../../groups/group/name";
                            }
                            max-elements 8;
                            ordered-by user;
                            description "Apply a configuration group at this level";
                        }

                        ///nokia-conf/configure/filter/ipv6-filter/embed/openflow/apply-groups-exclude
                        leaf-list apply-groups-exclude {
                            type leafref {
                                path "../../../../../groups/group/name";
                            }
                            max-elements 8;
                            ordered-by user;
                            description "Exclude a configuration group at this level";
                        }

                        ///nokia-conf/configure/filter/ipv6-filter/embed/openflow/context
                        choice context {
                            default "grt";
                            description
                                "Specifies the context in which the openflow embedding is inserted into filter.
                                 When no context is present, this object is set to grt value.";
                            ///nokia-conf/configure/filter/ipv6-filter/embed/openflow/context/grt
                            case grt {

                                ///nokia-conf/configure/filter/ipv6-filter/embed/openflow/context/grt/grt
                                leaf grt {
                                    type empty;
                                    sros-ext:immutable;
                                    description "Global routing context";
                                }

                            }
                            ///nokia-conf/configure/filter/ipv6-filter/embed/openflow/context/system
                            case system {

                                ///nokia-conf/configure/filter/ipv6-filter/embed/openflow/context/system/system
                                leaf system {
                                    type empty;
                                    sros-ext:immutable;
                                    description "System context";
                                }

                            }
                            ///nokia-conf/configure/filter/ipv6-filter/embed/openflow/context/vprn
                            case vprn {

                                ///nokia-conf/configure/filter/ipv6-filter/embed/openflow/context/vprn/vprn
                                leaf vprn {
                                    type leafref {
                                        path "../../../../../service/vprn/service-name";
                                    }
                                    sros-ext:immutable;
                                    description "VPRN context";
                                }

                            }
                            ///nokia-conf/configure/filter/ipv6-filter/embed/openflow/context/vpls
                            case vpls {

                                ///nokia-conf/configure/filter/ipv6-filter/embed/openflow/context/vpls/vpls
                                leaf vpls {
                                    type leafref {
                                        path "../../../../../service/vpls/service-name";
                                    }
                                    sros-ext:immutable;
                                    description "VPLS context";
                                }

                                ///nokia-conf/configure/filter/ipv6-filter/embed/openflow/context/vpls/sap
                                leaf sap {
                                    type leafref {
                                        path "../../../../../service/vpls[service-name=current()/../vpls]/sap/sap-id";
                                    }
                                    sros-ext:immutable;
                                    description "SAP context";
                                }

                            }
                        }
                    } // list openflow

                    ///nokia-conf/configure/filter/ipv6-filter/embed/vsd
                    list vsd {
                        status obsolete;
                        key "name offset";
                        description "Enter the vsd list instance";

                        ///nokia-conf/configure/filter/ipv6-filter/embed/vsd/name
                        leaf name {
                            status obsolete;
                            type types-sros:named-item {
                                pattern "_tmnx_vsd_([1-9]|[1-9][0-9]|[1-9][0-9][0-9]|[1-9][0-9][0-9][0-9]|[1-5][0-9][0-9][0-9][0-9]|6[0-4][0-9][0-9][0-9]|65[0-4][0-9][0-9]|655[0-2][0-9]|6553[0-5])";
                            }
                            description "Specifies the name of the filter to be inserted in this filter";
                        }

                        ///nokia-conf/configure/filter/ipv6-filter/embed/vsd/offset
                        leaf offset {
                            status obsolete;
                            type types-filter:embed-offset {
                                range "0..2097150";
                            }
                            description "Offset of the inserted entries";
                        }

                        ///nokia-conf/configure/filter/ipv6-filter/embed/vsd/admin-state
                        leaf admin-state {
                            status obsolete;
                            type types-sros:admin-state;
                            default "enable";
                            description "Administrative state of the embedded filter";
                        }

                        ///nokia-conf/configure/filter/ipv6-filter/embed/vsd/apply-groups
                        leaf-list apply-groups {
                            status obsolete;
                            type leafref {
                                path "../../../../../groups/group/name";
                            }
                            max-elements 8;
                            ordered-by user;
                            description "Apply a configuration group at this level";
                        }

                        ///nokia-conf/configure/filter/ipv6-filter/embed/vsd/apply-groups-exclude
                        leaf-list apply-groups-exclude {
                            status obsolete;
                            type leafref {
                                path "../../../../../groups/group/name";
                            }
                            max-elements 8;
                            ordered-by user;
                            description "Exclude a configuration group at this level";
                        }

                    } // list vsd

                } // container embed

            } // list ipv6-filter

            ///nokia-conf/configure/filter/mac-filter
            list mac-filter {
                key "filter-name";
                description "Enter the mac-filter list instance";

                ///nokia-conf/configure/filter/mac-filter/filter-name
                leaf filter-name {
                    type types-filter:filter-name;
                    description "Filter name";
                }

                ///nokia-conf/configure/filter/mac-filter/default-action
                leaf default-action {
                    type types-filter:filter-default-action;
                    default "drop";
                    description "Action for packets that do not match any entry";
                }

                ///nokia-conf/configure/filter/mac-filter/description
                leaf description {
                    type types-sros:description;
                    description "Text description";
                }

                ///nokia-conf/configure/filter/mac-filter/scope
                leaf scope {
                    type types-filter:filter-scope;
                    default "template";
                    description "Filter policy scope";
                }

                ///nokia-conf/configure/filter/mac-filter/type
                leaf type {
                    type types-qos:mac-filter-type;
                    sros-ext:immutable;
                    default "normal";
                    description "MAC filter policy";
                }

                ///nokia-conf/configure/filter/mac-filter/filter-id
                leaf filter-id {
                    type types-filter:filter-id;
                    sros-ext:immutable;
                    description "MAC filter ID";
                }

                ///nokia-conf/configure/filter/mac-filter/apply-groups
                leaf-list apply-groups {
                    type leafref {
                        path "../../../groups/group/name";
                    }
                    max-elements 8;
                    ordered-by user;
                    description "Apply a configuration group at this level";
                }

                ///nokia-conf/configure/filter/mac-filter/apply-groups-exclude
                leaf-list apply-groups-exclude {
                    type leafref {
                        path "../../../groups/group/name";
                    }
                    max-elements 8;
                    ordered-by user;
                    description "Exclude a configuration group at this level";
                }

                ///nokia-conf/configure/filter/mac-filter/entry
                list entry {
                    key "entry-id";
                    description "Enter the entry list instance";

                    ///nokia-conf/configure/filter/mac-filter/entry/entry-id
                    leaf entry-id {
                        type types-filter:entry-id;
                        description "ID for a match criteria and the corresponding action";
                    }

                    ///nokia-conf/configure/filter/mac-filter/entry/description
                    leaf description {
                        type types-sros:description;
                        description "Text description";
                    }

                    ///nokia-conf/configure/filter/mac-filter/entry/pbr-down-action-override
                    leaf pbr-down-action-override {
                        type types-filter:filter-pbr-down-action-ovr;
                        description "Action when PBR or PBF target for this entry is not available";
                    }

                    ///nokia-conf/configure/filter/mac-filter/entry/sticky-dest
                    leaf sticky-dest {
                        type types-filter:filter-sticky-dest;
                        units "seconds";
                        description "Time before action with available PBR or PBF destination and highest priority";
                    }

                    ///nokia-conf/configure/filter/mac-filter/entry/log
                    leaf log {
                        type leafref {
                            path "../../../log/log-id";
                        }
                        description "Log that is used for packets matching this entry";
                    }

                    ///nokia-conf/configure/filter/mac-filter/entry/collect-stats
                    leaf collect-stats {
                        type boolean;
                        default "false";
                        description "Enable statistics collection for an entry";
                    }

                    ///nokia-conf/configure/filter/mac-filter/entry/apply-groups
                    leaf-list apply-groups {
                        type leafref {
                            path "../../../../groups/group/name";
                        }
                        max-elements 8;
                        ordered-by user;
                        description "Apply a configuration group at this level";
                    }

                    ///nokia-conf/configure/filter/mac-filter/entry/apply-groups-exclude
                    leaf-list apply-groups-exclude {
                        type leafref {
                            path "../../../../groups/group/name";
                        }
                        max-elements 8;
                        ordered-by user;
                        description "Exclude a configuration group at this level";
                    }

                    ///nokia-conf/configure/filter/mac-filter/entry/match
                    container match {
                        description "Enter the match context";

                        ///nokia-conf/configure/filter/mac-filter/entry/match/frame-type
                        leaf frame-type {
                            type types-filter:mac-frame-type;
                            description "MAC frame as match criteria";
                        }

                        ///nokia-conf/configure/filter/mac-filter/entry/match/etype
                        leaf etype {
                            type types-services:etype-value;
                            description "Ethernet type";
                        }

                        ///nokia-conf/configure/filter/mac-filter/entry/match/snap-pid
                        leaf snap-pid {
                            type int32 {
                                range "0..65535";
                            }
                            description "Parameter snap-pid as a MAC filter match criteria";
                        }

                        ///nokia-conf/configure/filter/mac-filter/entry/match/snap-oui
                        leaf snap-oui {
                            type enumeration {
                                enum zero                           { value 2; }
                                enum non-zero                       { value 3; }
                            }
                            description "Parameter snap-oui as a MAC filter match criteria";
                        }

                        ///nokia-conf/configure/filter/mac-filter/entry/match/src-mac
                        container src-mac {
                            presence "Enable the src-mac context";
                            description "Enable the src-mac context";

                            ///nokia-conf/configure/filter/mac-filter/entry/match/src-mac/address
                            leaf address {
                                type yang:mac-address;
                                mandatory true;
                                description "MAC address used as the match criterion";
                            }

                            ///nokia-conf/configure/filter/mac-filter/entry/match/src-mac/mask
                            leaf mask {
                                type yang:mac-address;
                                default "ff:ff:ff:ff:ff:ff";
                                description "MAC address mask as the match criterion";
                            }

                        } // container src-mac

                        ///nokia-conf/configure/filter/mac-filter/entry/match/dst-mac
                        container dst-mac {
                            presence "Enable the dst-mac context";
                            description "Enable the dst-mac context";

                            ///nokia-conf/configure/filter/mac-filter/entry/match/dst-mac/address
                            leaf address {
                                type yang:mac-address;
                                mandatory true;
                                description "MAC address used as the match criterion";
                            }

                            ///nokia-conf/configure/filter/mac-filter/entry/match/dst-mac/mask
                            leaf mask {
                                type yang:mac-address;
                                default "ff:ff:ff:ff:ff:ff";
                                description "MAC address mask as the match criterion";
                            }

                        } // container dst-mac

                        ///nokia-conf/configure/filter/mac-filter/entry/match/dot1p
                        container dot1p {
                            presence "Enable the dot1p context";
                            description "Enable the dot1p context";

                            ///nokia-conf/configure/filter/mac-filter/entry/match/dot1p/priority
                            leaf priority {
                                type types-qos:dot1p-priority;
                                mandatory true;
                                description "IEEE 802.1p value used as a MAC filter match criterion";
                            }

                            ///nokia-conf/configure/filter/mac-filter/entry/match/dot1p/mask
                            leaf mask {
                                type types-qos:dot1p-priority {
                                    range "1..7";
                                }
                                default "7";
                                description "802.1p mask value used as a MAC filter match criterion";
                            }

                        } // container dot1p

                        ///nokia-conf/configure/filter/mac-filter/entry/match/llc-ssap
                        container llc-ssap {
                            presence "Enable the llc-ssap context";
                            description "Enable the llc-ssap context";

                            ///nokia-conf/configure/filter/mac-filter/entry/match/llc-ssap/ssap
                            leaf ssap {
                                type types-qos:service-access-point;
                                mandatory true;
                                description "Source or destination SAP value";
                            }

                            ///nokia-conf/configure/filter/mac-filter/entry/match/llc-ssap/mask
                            leaf mask {
                                type types-qos:service-access-point {
                                    range "1..255";
                                }
                                default "255";
                                description "Source SAP mask";
                            }

                        } // container llc-ssap

                        ///nokia-conf/configure/filter/mac-filter/entry/match/llc-dsap
                        container llc-dsap {
                            presence "Enable the llc-dsap context";
                            description "Enable the llc-dsap context";

                            ///nokia-conf/configure/filter/mac-filter/entry/match/llc-dsap/dsap
                            leaf dsap {
                                type types-qos:service-access-point;
                                mandatory true;
                                description "DSAP value";
                            }

                            ///nokia-conf/configure/filter/mac-filter/entry/match/llc-dsap/mask
                            leaf mask {
                                type types-qos:service-access-point {
                                    range "1..255";
                                }
                                default "255";
                                description "Destination SAP mask";
                            }

                        } // container llc-dsap

                        ///nokia-conf/configure/filter/mac-filter/entry/match/inner-tag
                        container inner-tag {
                            presence "Enable the inner-tag context";
                            description "Enable the inner-tag context";

                            ///nokia-conf/configure/filter/mac-filter/entry/match/inner-tag/tag
                            leaf tag {
                                type int32 {
                                    range "0..4095";
                                }
                                mandatory true;
                                description "Matching value against VID of the second or first VLAN tag in the packet carried transparently";
                            }

                            ///nokia-conf/configure/filter/mac-filter/entry/match/inner-tag/mask
                            leaf mask {
                                type uint32 {
                                    range "1..4095";
                                }
                                default "4095";
                                description "Mask to VID of the inner VLAN tag before comparing it with the inner-tag or outer-tag value";
                            }

                        } // container inner-tag

                        ///nokia-conf/configure/filter/mac-filter/entry/match/outer-tag
                        container outer-tag {
                            presence "Enable the outer-tag context";
                            description "Enable the outer-tag context";

                            ///nokia-conf/configure/filter/mac-filter/entry/match/outer-tag/tag
                            leaf tag {
                                type int32 {
                                    range "0..4095";
                                }
                                mandatory true;
                                description "Matching value against VID of the second or first VLAN tag in the packet carried transparently";
                            }

                            ///nokia-conf/configure/filter/mac-filter/entry/match/outer-tag/mask
                            leaf mask {
                                type uint32 {
                                    range "1..4095";
                                }
                                default "4095";
                                description "Mask to VID of the inner VLAN tag before comparing it with the inner-tag or outer-tag value";
                            }

                        } // container outer-tag

                        ///nokia-conf/configure/filter/mac-filter/entry/match/isid
                        container isid {
                            description "Enter the isid context";

                            ///nokia-conf/configure/filter/mac-filter/entry/match/isid/isid
                            choice isid {
                                ///nokia-conf/configure/filter/mac-filter/entry/match/isid/isid/isid-value
                                case isid-value {

                                    ///nokia-conf/configure/filter/mac-filter/entry/match/isid/isid/isid-value/value
                                    leaf value {
                                        type types-sros:svc-isid;
                                        description "Lowest value of 24-bit service instance identifier for the service matching this entry";
                                    }

                                }
                                ///nokia-conf/configure/filter/mac-filter/entry/match/isid/isid/isid-range
                                case isid-range {

                                    ///nokia-conf/configure/filter/mac-filter/entry/match/isid/isid/isid-range/range
                                    container range {
                                        presence "Enable the range context";
                                        description "Enable the range context";

                                        ///nokia-conf/configure/filter/mac-filter/entry/match/isid/isid/isid-range/range/start
                                        leaf start {
                                            type types-sros:svc-isid;
                                            mandatory true;
                                            description "Lower bound of the ISID range";
                                        }

                                        ///nokia-conf/configure/filter/mac-filter/entry/match/isid/isid/isid-range/range/end
                                        leaf end {
                                            type types-sros:svc-isid;
                                            mandatory true;
                                            description "Upper bound of the ISID range";
                                        }

                                    } // container range

                                }
                            }
                        } // container isid

                    } // container match

                    ///nokia-conf/configure/filter/mac-filter/entry/action
                    container action {
                        presence "Enable the action context";
                        description "Enable the action context";

                        ///nokia-conf/configure/filter/mac-filter/entry/action/fc
                        leaf fc {
                            type types-sros:fc-name;
                            description "Forwarding class for packets matching the entry";
                        }

                        ///nokia-conf/configure/filter/mac-filter/entry/action/apply-groups
                        leaf-list apply-groups {
                            type leafref {
                                path "../../../../../groups/group/name";
                            }
                            max-elements 8;
                            ordered-by user;
                            description "Apply a configuration group at this level";
                        }

                        ///nokia-conf/configure/filter/mac-filter/entry/action/apply-groups-exclude
                        leaf-list apply-groups-exclude {
                            type leafref {
                                path "../../../../../groups/group/name";
                            }
                            max-elements 8;
                            ordered-by user;
                            description "Exclude a configuration group at this level";
                        }

                        ///nokia-conf/configure/filter/mac-filter/entry/action/action
                        choice action {
                            mandatory true;
                            ///nokia-conf/configure/filter/mac-filter/entry/action/action/ignore-match
                            case ignore-match {

                                ///nokia-conf/configure/filter/mac-filter/entry/action/action/ignore-match/ignore-match
                                leaf ignore-match {
                                    type empty;
                                    description "Ignore match criteria for the entry";
                                }

                            }
                            ///nokia-conf/configure/filter/mac-filter/entry/action/action/drop
                            case drop {

                                ///nokia-conf/configure/filter/mac-filter/entry/action/action/drop/drop
                                leaf drop {
                                    type empty;
                                    description "Drop a packet matching this entry";
                                }

                            }
                            ///nokia-conf/configure/filter/mac-filter/entry/action/action/forward
                            case forward {

                                ///nokia-conf/configure/filter/mac-filter/entry/action/action/forward/forward
                                container forward {
                                    description "Enter the forward context";

                                    ///nokia-conf/configure/filter/mac-filter/entry/action/action/forward/forward/forward-action
                                    choice forward-action {
                                        ///nokia-conf/configure/filter/mac-filter/entry/action/action/forward/forward/forward-action/esi-l2
                                        case esi-l2 {

                                            ///nokia-conf/configure/filter/mac-filter/entry/action/action/forward/forward/forward-action/esi-l2/esi-l2
                                            container esi-l2 {
                                                presence "Enable the esi-l2 context";
                                                description "Enable the esi-l2 context";

                                                ///nokia-conf/configure/filter/mac-filter/entry/action/action/forward/forward/forward-action/esi-l2/esi-l2/esi-value
                                                leaf esi-value {
                                                    type types-services:ethernet-segment-id {
                                                        pattern "(0x[0-9a-fA-F]{20})|([0-9a-fA-F]{2}(:[0-9a-fA-F]{2}){9})|([0-9a-fA-F]{2}(-[0-9a-fA-F]{2}){9})";
                                                    }
                                                    mandatory true;
                                                    description "ESI of the first ESI-identified appliance";
                                                }

                                                ///nokia-conf/configure/filter/mac-filter/entry/action/action/forward/forward/forward-action/esi-l2/esi-l2/vpls
                                                leaf vpls {
                                                    type leafref {
                                                        path "../../../../../../../service/vpls/service-name";
                                                    }
                                                    mandatory true;
                                                    description "VPLS service name";
                                                }

                                            } // container esi-l2

                                        }
                                        ///nokia-conf/configure/filter/mac-filter/entry/action/action/forward/forward/forward-action/sdp
                                        case sdp {

                                            ///nokia-conf/configure/filter/mac-filter/entry/action/action/forward/forward/forward-action/sdp/sdp
                                            container sdp {
                                                presence "Enable the sdp context";
                                                description "Enable the sdp context";

                                                ///nokia-conf/configure/filter/mac-filter/entry/action/action/forward/forward/forward-action/sdp/sdp/vpls
                                                leaf vpls {
                                                    type leafref {
                                                        path "../../../../../../../service/vpls/service-name";
                                                    }
                                                    mandatory true;
                                                    description "VPLS associated with the SDP";
                                                }

                                                ///nokia-conf/configure/filter/mac-filter/entry/action/action/forward/forward/forward-action/sdp/sdp/sdp-bind-id
                                                leaf sdp-bind-id {
                                                    type types-services:sdp-bind-id;
                                                    mandatory true;
                                                    description "VPLS SDP bind ID used to forward matching packets";
                                                }

                                            } // container sdp

                                        }
                                        ///nokia-conf/configure/filter/mac-filter/entry/action/action/forward/forward/forward-action/sap
                                        case sap {

                                            ///nokia-conf/configure/filter/mac-filter/entry/action/action/forward/forward/forward-action/sap/sap
                                            container sap {
                                                presence "Enable the sap context";
                                                description "Enable the sap context";

                                                ///nokia-conf/configure/filter/mac-filter/entry/action/action/forward/forward/forward-action/sap/sap/vpls
                                                leaf vpls {
                                                    type leafref {
                                                        path "../../../../../../../service/vpls/service-name";
                                                    }
                                                    mandatory true;
                                                    description "VPLS associated with the SAP";
                                                }

                                                ///nokia-conf/configure/filter/mac-filter/entry/action/action/forward/forward/forward-action/sap/sap/sap-id
                                                leaf sap-id {
                                                    type leafref {
                                                        path "../../../../../../../service/vpls[service-name=current()/../vpls]/sap/sap-id";
                                                    }
                                                    mandatory true;
                                                    description "VPLS Ethernet SAP ID used to forward matching packets";
                                                }

                                            } // container sap

                                        }
                                    }
                                } // container forward

                            }
                            ///nokia-conf/configure/filter/mac-filter/entry/action/action/http-redirect
                            case http-redirect {

                                ///nokia-conf/configure/filter/mac-filter/entry/action/action/http-redirect/http-redirect
                                container http-redirect {
                                    presence "Enable the http-redirect context";
                                    description "Enable the http-redirect context";

                                    ///nokia-conf/configure/filter/mac-filter/entry/action/action/http-redirect/http-redirect/url
                                    leaf url {
                                        type types-sros:http-redirect-url;
                                        sros-ext:immutable;
                                        mandatory true;
                                        description "URL that is used for redirecting";
                                    }

                                } // container http-redirect

                            }
                            ///nokia-conf/configure/filter/mac-filter/entry/action/action/accept
                            case accept {

                                ///nokia-conf/configure/filter/mac-filter/entry/action/action/accept/accept
                                leaf accept {
                                    type empty;
                                    description "Accept regular routing to forward a matching packet";
                                }

                            }
                        }
                        ///nokia-conf/configure/filter/mac-filter/entry/action/rate-limit
                        container rate-limit {
                            presence "Enable the rate-limit context";
                            description "Enable the rate-limit context";

                            ///nokia-conf/configure/filter/mac-filter/entry/action/rate-limit/pir
                            leaf pir {
                                type types-filter:rate-limit;
                                units "kilobps";
                                mandatory true;
                                description "Peak information rate";
                            }

                        } // container rate-limit

                        ///nokia-conf/configure/filter/mac-filter/entry/action/secondary
                        container secondary {
                            presence "Enable the secondary context";
                            description "Enable the secondary context";

                            ///nokia-conf/configure/filter/mac-filter/entry/action/secondary/apply-groups
                            leaf-list apply-groups {
                                type leafref {
                                    path "../../../../../../groups/group/name";
                                }
                                max-elements 8;
                                ordered-by user;
                                description "Apply a configuration group at this level";
                            }

                            ///nokia-conf/configure/filter/mac-filter/entry/action/secondary/apply-groups-exclude
                            leaf-list apply-groups-exclude {
                                type leafref {
                                    path "../../../../../../groups/group/name";
                                }
                                max-elements 8;
                                ordered-by user;
                                description "Exclude a configuration group at this level";
                            }

                            ///nokia-conf/configure/filter/mac-filter/entry/action/secondary/action
                            choice action {
                                mandatory true;
                                ///nokia-conf/configure/filter/mac-filter/entry/action/secondary/action/forward
                                case forward {

                                    ///nokia-conf/configure/filter/mac-filter/entry/action/secondary/action/forward/forward
                                    container forward {
                                        description "Enter the forward context";

                                        ///nokia-conf/configure/filter/mac-filter/entry/action/secondary/action/forward/forward/forward-action
                                        choice forward-action {
                                            ///nokia-conf/configure/filter/mac-filter/entry/action/secondary/action/forward/forward/forward-action/sdp
                                            case sdp {

                                                ///nokia-conf/configure/filter/mac-filter/entry/action/secondary/action/forward/forward/forward-action/sdp/sdp
                                                container sdp {
                                                    presence "Enable the sdp context";
                                                    description "Enable the sdp context";

                                                    ///nokia-conf/configure/filter/mac-filter/entry/action/secondary/action/forward/forward/forward-action/sdp/sdp/vpls
                                                    leaf vpls {
                                                        type leafref {
                                                            path "../../../../../../../../service/vpls/service-name";
                                                        }
                                                        mandatory true;
                                                        description "VPLS associated with the SDP";
                                                    }

                                                    ///nokia-conf/configure/filter/mac-filter/entry/action/secondary/action/forward/forward/forward-action/sdp/sdp/sdp-bind-id
                                                    leaf sdp-bind-id {
                                                        type types-services:sdp-bind-id;
                                                        sros-ext:immutable;
                                                        mandatory true;
                                                        description "VPLS SDP bind ID used to forward matching packets";
                                                    }

                                                } // container sdp

                                            }
                                            ///nokia-conf/configure/filter/mac-filter/entry/action/secondary/action/forward/forward/forward-action/sap
                                            case sap {

                                                ///nokia-conf/configure/filter/mac-filter/entry/action/secondary/action/forward/forward/forward-action/sap/sap
                                                container sap {
                                                    presence "Enable the sap context";
                                                    description "Enable the sap context";

                                                    ///nokia-conf/configure/filter/mac-filter/entry/action/secondary/action/forward/forward/forward-action/sap/sap/vpls
                                                    leaf vpls {
                                                        type leafref {
                                                            path "../../../../../../../../service/vpls/service-name";
                                                        }
                                                        mandatory true;
                                                        description "VPLS the sdp-bind-id belongs to";
                                                    }

                                                    ///nokia-conf/configure/filter/mac-filter/entry/action/secondary/action/forward/forward/forward-action/sap/sap/sap-id
                                                    leaf sap-id {
                                                        type leafref {
                                                            path "../../../../../../../../service/vpls[service-name=current()/../vpls]/sap/sap-id";
                                                        }
                                                        sros-ext:immutable;
                                                        mandatory true;
                                                        description "SAP ID used to forward packets matching the entry";
                                                    }

                                                } // container sap

                                            }
                                        }
                                    } // container forward

                                }
                            }
                        } // container secondary

                    } // container action

                } // list entry

                ///nokia-conf/configure/filter/mac-filter/embed
                container embed {
                    description "Enter the embed context";

                    ///nokia-conf/configure/filter/mac-filter/embed/vsd
                    list vsd {
                        status obsolete;
                        key "name offset";
                        description "Enter the vsd list instance";

                        ///nokia-conf/configure/filter/mac-filter/embed/vsd/name
                        leaf name {
                            status obsolete;
                            type types-sros:named-item {
                                pattern "_tmnx_vsd_([1-9]|[1-9][0-9]|[1-9][0-9][0-9]|[1-9][0-9][0-9][0-9]|[1-5][0-9][0-9][0-9][0-9]|6[0-4][0-9][0-9][0-9]|65[0-4][0-9][0-9]|655[0-2][0-9]|6553[0-5])";
                            }
                            description "Specifies the name of the filter to be inserted in this filter";
                        }

                        ///nokia-conf/configure/filter/mac-filter/embed/vsd/offset
                        leaf offset {
                            status obsolete;
                            type types-filter:embed-offset {
                                range "0..2097150";
                            }
                            description "Offset of the inserted entries";
                        }

                        ///nokia-conf/configure/filter/mac-filter/embed/vsd/admin-state
                        leaf admin-state {
                            status obsolete;
                            type types-sros:admin-state;
                            default "enable";
                            description "Administrative state of the embedded filter";
                        }

                        ///nokia-conf/configure/filter/mac-filter/embed/vsd/apply-groups
                        leaf-list apply-groups {
                            status obsolete;
                            type leafref {
                                path "../../../../../groups/group/name";
                            }
                            max-elements 8;
                            ordered-by user;
                            description "Apply a configuration group at this level";
                        }

                        ///nokia-conf/configure/filter/mac-filter/embed/vsd/apply-groups-exclude
                        leaf-list apply-groups-exclude {
                            status obsolete;
                            type leafref {
                                path "../../../../../groups/group/name";
                            }
                            max-elements 8;
                            ordered-by user;
                            description "Exclude a configuration group at this level";
                        }

                    } // list vsd

                } // container embed

            } // list mac-filter

            ///nokia-conf/configure/filter/system-filter
            container system-filter {
                description "Enable the system-filter context";

                ///nokia-conf/configure/filter/system-filter/apply-groups
                leaf-list apply-groups {
                    type leafref {
                        path "../../../groups/group/name";
                    }
                    max-elements 8;
                    ordered-by user;
                    description "Apply a configuration group at this level";
                }

                ///nokia-conf/configure/filter/system-filter/apply-groups-exclude
                leaf-list apply-groups-exclude {
                    type leafref {
                        path "../../../groups/group/name";
                    }
                    max-elements 8;
                    ordered-by user;
                    description "Exclude a configuration group at this level";
                }

                ///nokia-conf/configure/filter/system-filter/ip
                list ip {
                    key "ip-filter";
                    max-elements 1;
                    description "Add a list entry for ip";

                    ///nokia-conf/configure/filter/system-filter/ip/ip-filter
                    leaf ip-filter {
                        type leafref {
                            path "../../../ip-filter/filter-name";
                        }
                        description "Active IPv4 system filter policy";
                    }

                } // list ip

                ///nokia-conf/configure/filter/system-filter/ipv6
                list ipv6 {
                    key "ipv6-filter";
                    max-elements 1;
                    description "Add a list entry for ipv6";

                    ///nokia-conf/configure/filter/system-filter/ipv6/ipv6-filter
                    leaf ipv6-filter {
                        type leafref {
                            path "../../../ipv6-filter/filter-name";
                        }
                        description "Active IPv6 system filter policy";
                    }

                } // list ipv6

            } // container system-filter

            ///nokia-conf/configure/filter/gre-tunnel-template
            list gre-tunnel-template {
                key "gre-tunnel-template-name";
                max-elements 8191;
                description "Enter the gre-tunnel-template list instance";

                ///nokia-conf/configure/filter/gre-tunnel-template/gre-tunnel-template-name
                leaf gre-tunnel-template-name {
                    type types-sros:named-item;
                    description "GRE tunnel template ID";
                }

                ///nokia-conf/configure/filter/gre-tunnel-template/description
                leaf description {
                    type types-sros:description;
                    description "Text description";
                }

                ///nokia-conf/configure/filter/gre-tunnel-template/apply-groups
                leaf-list apply-groups {
                    type leafref {
                        path "../../../groups/group/name";
                    }
                    max-elements 8;
                    ordered-by user;
                    description "Apply a configuration group at this level";
                }

                ///nokia-conf/configure/filter/gre-tunnel-template/apply-groups-exclude
                leaf-list apply-groups-exclude {
                    type leafref {
                        path "../../../groups/group/name";
                    }
                    max-elements 8;
                    ordered-by user;
                    description "Exclude a configuration group at this level";
                }

                ///nokia-conf/configure/filter/gre-tunnel-template/ipvx
                choice ipvx {
                    ///nokia-conf/configure/filter/gre-tunnel-template/ipvx/ipv4
                    case ipv4 {

                        ///nokia-conf/configure/filter/gre-tunnel-template/ipvx/ipv4/ipv4
                        container ipv4 {
                            description "Enter the ipv4 context";

                            ///nokia-conf/configure/filter/gre-tunnel-template/ipvx/ipv4/ipv4/source-address
                            leaf source-address {
                                type types-sros:ipv4-address;
                                description "Source IP address of the GRE encapsulated";
                            }

                            ///nokia-conf/configure/filter/gre-tunnel-template/ipvx/ipv4/ipv4/gre-key
                            leaf gre-key {
                                type types-filter:filter-gre-tunnel-gre-key;
                                description "GRE key";
                            }

                            ///nokia-conf/configure/filter/gre-tunnel-template/ipvx/ipv4/ipv4/skip-ttl-decrement
                            leaf skip-ttl-decrement {
                                type boolean;
                                default "false";
                                description "Decrement TTL";
                            }

                            ///nokia-conf/configure/filter/gre-tunnel-template/ipvx/ipv4/ipv4/destination-address
                            list destination-address {
                                key "address";
                                max-elements 32;
                                description "Add a list entry for destination-address";

                                ///nokia-conf/configure/filter/gre-tunnel-template/ipvx/ipv4/ipv4/destination-address/address
                                leaf address {
                                    type types-sros:ipv4-address;
                                    description "Destination IPv4 address";
                                }

                            } // list destination-address

                        } // container ipv4

                    }
                    ///nokia-conf/configure/filter/gre-tunnel-template/ipvx/ipv6
                    case ipv6 {

                        ///nokia-conf/configure/filter/gre-tunnel-template/ipvx/ipv6/ipv6
                        container ipv6 {
                            description "Enter the ipv6 context";

                            ///nokia-conf/configure/filter/gre-tunnel-template/ipvx/ipv6/ipv6/source-address
                            leaf source-address {
                                type types-sros:ipv6-unicast-address;
                                description "Source IPv6 address of the GRE encapsulated";
                            }

                            ///nokia-conf/configure/filter/gre-tunnel-template/ipvx/ipv6/ipv6/gre-key
                            leaf gre-key {
                                type enumeration {
                                    enum if-index                       { value -2; }
                                }
                                description "Include a key value in GRE header";
                            }

                            ///nokia-conf/configure/filter/gre-tunnel-template/ipvx/ipv6/ipv6/skip-hop-decrement
                            leaf skip-hop-decrement {
                                type boolean;
                                default "false";
                                description "Decrement TTL of the received packet";
                            }

                            ///nokia-conf/configure/filter/gre-tunnel-template/ipvx/ipv6/ipv6/destination-address
                            list destination-address {
                                key "address";
                                max-elements 1;
                                description "Add a list entry for destination-address";

                                ///nokia-conf/configure/filter/gre-tunnel-template/ipvx/ipv6/ipv6/destination-address/address
                                leaf address {
                                    type types-sros:ipv6-unicast-address;
                                    description "IPv6 destination address";
                                }

                            } // list destination-address

                        } // container ipv6

                    }
                }
            } // list gre-tunnel-template

            ///nokia-conf/configure/filter/md-auto-id
            container md-auto-id {
                description "Enter the md-auto-id context";

                ///nokia-conf/configure/filter/md-auto-id/filter-id-range
                container filter-id-range {
                    presence "Enable the filter-id-range context";
                    description "Enable the filter-id-range context";

                    ///nokia-conf/configure/filter/md-auto-id/filter-id-range/start
                    leaf start {
                        type types-filter:filter-id;
                        sros-ext:immutable;
                        mandatory true;
                        description "Lower bound of the ID range";
                    }

                    ///nokia-conf/configure/filter/md-auto-id/filter-id-range/end
                    leaf end {
                        type types-filter:filter-id;
                        sros-ext:immutable;
                        mandatory true;
                        description "Upper bound of the ID range";
                    }

                    ///nokia-conf/configure/filter/md-auto-id/filter-id-range/apply-groups
                    leaf-list apply-groups {
                        type leafref {
                            path "../../../../groups/group/name";
                        }
                        max-elements 8;
                        ordered-by user;
                        description "Apply a configuration group at this level";
                    }

                    ///nokia-conf/configure/filter/md-auto-id/filter-id-range/apply-groups-exclude
                    leaf-list apply-groups-exclude {
                        type leafref {
                            path "../../../../groups/group/name";
                        }
                        max-elements 8;
                        ordered-by user;
                        description "Exclude a configuration group at this level";
                    }

                } // container filter-id-range

            } // container md-auto-id

            uses conf-filter-dhcp-dhcp-filter;
            uses conf-filter-dhcp-dhcp6-filter;
            uses conf-filter-ip-exception;
            uses conf-filter-ip-exception-ipv6-exception;
        } // container filter

    } // grouping conf-filter

}
