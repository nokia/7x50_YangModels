submodule nokia-conf-subscriber-mgmt {

    yang-version "1.1";

    belongs-to nokia-conf { prefix "conf"; }

    import ietf-yang-types                { prefix "yang"; }
    import nokia-sros-yang-extensions     { prefix "sros-ext"; }
    import nokia-types-application-assurance { prefix "types-aa"; }
    import nokia-types-bgp                { prefix "types-bgp"; }
    import nokia-types-diameter           { prefix "types-diam"; }
    import nokia-types-filter             { prefix "types-filter"; }
    import nokia-types-igmp               { prefix "types-igmp"; }
    import nokia-types-mcast-cac          { prefix "types-mcast-cac"; }
    import nokia-types-ppp                { prefix "types-ppp"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }

    include nokia-conf-aa-group;
    include nokia-conf-aaa;
    include nokia-conf-application-assurance;
    include nokia-conf-filter;
    include nokia-conf-groups;
    include nokia-conf-isa;
    include nokia-conf-log;
    include nokia-conf-mcast-cac;
    include nokia-conf-mcast-mgmt;
    include nokia-conf-policy-options;
    include nokia-conf-python;
    include nokia-conf-qos;
    include nokia-conf-service;
    include nokia-conf-submgt-ancp;
    include nokia-conf-submgt-gtp;
    include nokia-conf-submgt-isa-filter;
    include nokia-conf-submgt-isa-policer;
    include nokia-conf-submgt-local-user-db;
    include nokia-conf-submgt-service-chaining;
    include nokia-conf-submgt-up-resiliency;
    include nokia-conf-submgt-vrgw;
    include nokia-conf-submgt-wlangw;
    include nokia-conf-svc-nat;
    include nokia-conf-svc-vpls;
    include nokia-conf-system;
    include nokia-conf-system-security;

    sros-ext:sros-major-release "rel23";
    organization "Nokia";
    contact
        "Nokia SR OS Support
         Web: <http://www.nokia.com>";
    description
        "Nokia YANG Data model to configure subscriber management on SR OS based routers.

         Copyright 2016 Nokia. All rights reserved. Reproduction of this document
         is authorized on the condition that the foregoing copyright notice is included.

         This nokia-conf-subscriber-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-02";

    grouping conf-subscriber-mgmt {
        container subscriber-mgmt {
            description "Enter the subscriber-mgmt context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list diameter-gx-policy {
                key "name";
                max-elements 32;
                description "Enter the diameter-gx-policy list instance";

                leaf name {
                    type types-sros:named-item;
                    description "Diameter application policy name";
                }

                leaf description {
                    type types-sros:description;
                    description "Text description";
                }

                leaf tx-timer {
                    type types-sros:time-duration {
                        range "10..1000";
                    }
                    units "seconds";
                    default "10";
                    description "Maximum wait time for a pending session request";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice diameter-base {
                    case node {

                        container node {
                            description "Enter the node context";

                            leaf origin-host {
                                type leafref {
                                    path "../../../../aaa/diameter/node/origin-host";
                                }
                                sros-ext:immutable;
                                description "Origin-Host AVP used by the Diameter policy";
                            }

                            leaf destination-realm {
                                type string {
                                    length "1..80";
                                }
                                description "Destination-Realm AVP used by the Diameter peer policy";
                            }

                        } // container node

                    }
                    case peer-policy {
                        status obsolete;

                        leaf peer-policy {
                            status obsolete;
                            type leafref {
                                path "../../../aaa/diameter/peer-policy/name";
                            }
                            sros-ext:immutable;
                            description "Policy for the Diameter peers";
                        }

                    }
                }
                container on-failure {
                    description "Enter the on-failure context";

                    leaf failover {
                        type boolean;
                        default "true";
                        description "Session peer failover";
                    }

                    leaf handling {
                        type enumeration {
                            enum terminate                      { value 1; }
                            enum continue                       { value 2; }
                            enum retry-and-terminate            { value 3; }
                        }
                        default "terminate";
                        description "Session peer failure handling";
                    }

                } // container on-failure

                container gx {
                    description "Enter the gx context";

                    leaf mac-format {
                        type types-submgt:mac-specification;
                        default "aa:";
                        description "MAC address format";
                    }

                    leaf report-ip-address-event {
                        type boolean;
                        default "true";
                        description "Enable CCR-u messages on IP address allocation events";
                    }

                    leaf credit-mcs-interval {
                        type types-sros:time-duration {
                            range "5..60";
                        }
                        units "minutes";
                        default "10";
                        description "Volume syncing interval for usage monitoring";
                    }

                    leaf destination-realm-learning {
                        type boolean;
                        default "true";
                        description "Learn the destination realm from the incoming messages";
                    }

                    container avp-subscription-id {
                        description "Enter the avp-subscription-id context";

                        leaf origin {
                            type enumeration {
                                enum subscriber-id                  { value 1; }
                                enum circuit-id                     { value 2; }
                                enum imsi                           { value 3; }
                                enum msisdn                         { value 4; }
                                enum imei                           { value 5; }
                                enum dual-stack-remote-id           { value 6; }
                                enum mac                            { value 7; }
                                enum username                       { value 8; }
                                enum nas-port-id                    { value 9; }
                            }
                            default "subscriber-id";
                            description "Format of the Subscription-Id-Data AVP";
                        }

                        leaf type {
                            type enumeration {
                                enum e164                           { value 0; }
                                enum imsi                           { value 1; }
                                enum nai                            { value 3; }
                                enum private                        { value 4; }
                            }
                            default "private";
                            description "Format of the Subscription-Id-Type AVP";
                        }

                    } // container avp-subscription-id

                    container ccrt-replay {
                        presence "Enable the ccrt-replay context";
                        description "Enable the ccrt-replay context";

                        leaf interval {
                            type uint32 {
                                range "60..86400";
                            }
                            default "3600";
                            description "Time between consecutive CCR-T replay attempts";
                        }

                        leaf max-lifetime {
                            type types-sros:time-duration {
                                range "1..24";
                            }
                            units "hours";
                            default "24";
                            description "Maximum time that CCR-t messages are replayed";
                        }

                    } // container ccrt-replay

                    container include-avp {
                        description "Enter the include-avp context";

                        leaf an-gw-address {
                            type boolean;
                            default "false";
                            description "Include the IP address of this gateway";
                        }

                        leaf apn-ambr {
                            type boolean;
                            default "false";
                            description "Include the APN aggregate maximum bitrate";
                        }

                        leaf called-station-id {
                            type boolean;
                            default "false";
                            description "Include the called station ID";
                        }

                        leaf ip-can-type {
                            type boolean;
                            default "false";
                            description "Include the IP CAN type";
                        }

                        leaf logical-access-id {
                            type boolean;
                            default "false";
                            description "Include the logical access id";
                        }

                        leaf pdn-connection-id {
                            type boolean;
                            default "false";
                            description "Include the PDN connection id";
                        }

                        leaf physical-access-id {
                            type boolean;
                            default "false";
                            description "Include the physical access ID";
                        }

                        leaf rai {
                            type boolean;
                            default "false";
                            description "Include the routing area identity";
                        }

                        leaf rat-type {
                            type boolean;
                            default "false";
                            description "Include the RAT type";
                        }

                        leaf sgsn-mcc-mnc {
                            type boolean;
                            default "false";
                            description "Include the 3GPP-SGSN-MCC-MNC AVP";
                        }

                        leaf supported-features {
                            type boolean;
                            default "false";
                            description "Include the supported features";
                        }

                        leaf user-location-info {
                            type boolean;
                            default "false";
                            description "Include the 3GPP-User-Location-Information AVP";
                        }

                        container calling-station-id {
                            presence "Enable the calling-station-id context";
                            description "Enable the calling-station-id context";

                            leaf type {
                                type enumeration {
                                    enum sap-string                     { value 1; }
                                    enum mac                            { value 2; }
                                    enum sap-id                         { value 3; }
                                    enum remote-id                      { value 4; }
                                    enum llid                           { value 5; }
                                }
                                default "sap-string";
                                description "Format of the Calling-Station-ID AVP";
                            }

                        } // container calling-station-id

                        container nas-port {
                            presence "Enable the nas-port context";
                            description "Enable the nas-port context";

                            leaf bit-spec {
                                type types-sros:binary-specification {
                                    pattern "([01]|(\\*[0123456789]+)?[oismpvc])+";
                                }
                                mandatory true;
                                description "NAS-Port AVP format";
                            }

                        } // container nas-port

                        container nas-port-id {
                            presence "Enable the nas-port-id context";
                            description "Enable the nas-port-id context";

                            leaf prefix-string {
                                type string {
                                    length "1..8";
                                }
                                description "Prefix string for NAS-Port-Id AVP";
                            }

                            container suffix {
                                description "Enter the suffix context";

                                choice suffix {
                                    default "not-included";
                                    description "Configure the format of the nas-port-id suffix.";
                                    case not-included {

                                        leaf not-included {
                                            type empty;
                                            description "Do not add a suffix";
                                        }

                                    }
                                    case circuit-id {

                                        leaf circuit-id {
                                            type empty;
                                            description "Add Circuit ID as suffix";
                                        }

                                    }
                                    case remote-id {

                                        leaf remote-id {
                                            type empty;
                                            description "Add Remote ID as suffix";
                                        }

                                    }
                                    case user-string {

                                        leaf user-string {
                                            type string {
                                                length "1..64";
                                            }
                                            description "Add a user configurable string as suffix";
                                        }

                                    }
                                }
                            } // container suffix

                        } // container nas-port-id

                        container nas-port-type {
                            presence "Enable the nas-port-type context";
                            description "Enable the nas-port-type context";

                            leaf type {
                                type uint32 {
                                    range "0..255";
                                }
                                description "NAS-Port-Type AVP value";
                            }

                        } // container nas-port-type

                        container user-equipment-info {
                            presence "Enable the user-equipment-info context";
                            description "Enable the user-equipment-info context";

                            leaf type {
                                type enumeration {
                                    enum imeisv                         { value 0; }
                                    enum mac                            { value 1; }
                                    enum eui64                          { value 2; }
                                    enum modified-eui64                 { value 3; }
                                }
                                default "mac";
                                description "Information for User-Equipment-Info attribute";
                            }

                        } // container user-equipment-info

                    } // container include-avp

                    container three-gpp-qos-mapping {
                        description "Enter the three-gpp-qos-mapping context";

                        container apn-ambr-dl {
                            description "Enter the apn-ambr-dl context";

                            choice qos-override {
                                default "ignore-override";
                                case ignore-override {

                                    leaf ignore-override {
                                        type empty;
                                        description "no override on apn-ambr-dl";
                                    }

                                }
                                case arbiter {

                                    leaf arbiter {
                                        type types-sros:named-item;
                                        description "Arbiter name to be overridden";
                                    }

                                }
                                case policer {

                                    leaf policer {
                                        type types-qos:sap-egress-policer-id;
                                        description "Policer ID to be overidden";
                                    }

                                }
                                case queue {

                                    leaf queue {
                                        type types-qos:egress-queue-id;
                                        description "Queue ID to be overridden";
                                    }

                                }
                                case scheduler {

                                    leaf scheduler {
                                        type types-sros:named-item;
                                        description "Name of the scheduler to be overridden";
                                    }

                                }
                                case aggregate-rate {

                                    leaf aggregate-rate {
                                        type empty;
                                        description "Map to an aggregate rate";
                                    }

                                }
                                case hs-sla-agg-rate {

                                    leaf hs-sla-agg-rate {
                                        type empty;
                                        description "Map to an HS SLA aggregate rate";
                                    }

                                }
                            }
                        } // container apn-ambr-dl

                        container apn-ambr-ul {
                            description "Enter the apn-ambr-ul context";

                            choice qos-override {
                                default "ignore-override";
                                case ignore-override {

                                    leaf ignore-override {
                                        type empty;
                                        description "no override on apn-ambr-ul";
                                    }

                                }
                                case arbiter {

                                    leaf arbiter {
                                        type types-sros:named-item;
                                        description "Arbiter name to be overridden";
                                    }

                                }
                                case policer {

                                    leaf policer {
                                        type types-qos:ingress-policer-id;
                                        description "Policer ID to be overridden";
                                    }

                                }
                                case queue {

                                    leaf queue {
                                        type types-qos:ingress-queue-id;
                                        description "Queue ID to be overridden";
                                    }

                                }
                                case scheduler {

                                    leaf scheduler {
                                        type types-sros:named-item;
                                        description "Name of the scheduler to be overridden";
                                    }

                                }
                            }
                        } // container apn-ambr-ul

                    } // container three-gpp-qos-mapping

                    container features {
                        description "Enter the features context";

                        leaf extended-bandwidth {
                            type boolean;
                            default "false";
                            description "Negotiate support for extended bandwidth AVPs";
                        }

                    } // container features

                } // container gx

            } // list diameter-gx-policy

            list diameter-gy-policy {
                key "name";
                max-elements 32;
                description "Enter the diameter-gy-policy list instance";

                leaf name {
                    type types-sros:named-item;
                    description "Diameter application policy name";
                }

                leaf description {
                    type types-sros:description;
                    description "Text description";
                }

                leaf tx-timer {
                    type types-sros:time-duration {
                        range "10..1000";
                    }
                    units "seconds";
                    default "10";
                    description "Maximum wait time for a pending session request";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice diameter-base {
                    case node {

                        container node {
                            description "Enter the node context";

                            leaf origin-host {
                                type leafref {
                                    path "../../../../aaa/diameter/node/origin-host";
                                }
                                sros-ext:immutable;
                                description "Origin-Host AVP used by the Diameter policy";
                            }

                            leaf destination-realm {
                                type string {
                                    length "1..80";
                                }
                                description "Destination-Realm AVP used by the Diameter peer policy";
                            }

                        } // container node

                    }
                    case peer-policy {
                        status obsolete;

                        leaf peer-policy {
                            status obsolete;
                            type leafref {
                                path "../../../aaa/diameter/peer-policy/name";
                            }
                            sros-ext:immutable;
                            description "Policy for the Diameter peers";
                        }

                    }
                }
                container on-failure {
                    description "Enter the on-failure context";

                    leaf failover {
                        type boolean;
                        default "true";
                        description "Session peer failover";
                    }

                    leaf handling {
                        type enumeration {
                            enum terminate                      { value 1; }
                            enum continue                       { value 2; }
                            enum retry-and-terminate            { value 3; }
                        }
                        default "terminate";
                        description "Session peer failure handling";
                    }

                } // container on-failure

                container gy {
                    description "Enter the gy context";

                    leaf mac-format {
                        type types-submgt:mac-specification;
                        default "aa:";
                        description "MAC address format";
                    }

                    leaf out-of-credit-reporting {
                        type enumeration {
                            enum final                          { value 1; }
                            enum quota-exhausted                { value 2; }
                        }
                        default "final";
                        description "Reporting reason when final granted units are consumed";
                    }

                    leaf vendor-support {
                        type types-diam:diam-vendor-support;
                        default "three-gpp";
                        description "Vendor support type announced in capability exchange";
                    }

                    leaf destination-realm-learning {
                        type boolean;
                        default "true";
                        description "Learn the destination realm from the incoming messages";
                    }

                    container avp-subscription-id {
                        description "Enter the avp-subscription-id context";

                        leaf origin {
                            type enumeration {
                                enum subscriber-id                  { value 1; }
                                enum circuit-id                     { value 2; }
                                enum imsi                           { value 3; }
                                enum msisdn                         { value 4; }
                                enum imei                           { value 5; }
                                enum dual-stack-remote-id           { value 6; }
                                enum mac                            { value 7; }
                                enum username                       { value 8; }
                                enum nas-port-id                    { value 9; }
                            }
                            default "subscriber-id";
                            description "Origin for the Subscription-Id-Data AVP";
                        }

                        leaf type {
                            type enumeration {
                                enum e164                           { value 0; }
                                enum imsi                           { value 1; }
                                enum nai                            { value 3; }
                                enum private                        { value 4; }
                            }
                            default "private";
                            description "Origin for the Subscription-Id-Type AVP";
                        }

                    } // container avp-subscription-id

                    container include-avp {
                        description "Enter the include-avp context";

                        leaf three-gpp-charging-characteristics {
                            type boolean;
                            default "true";
                            description "DCCA 3GPP charging characteristics AVP parameter";
                        }

                        leaf three-gpp-charging-id {
                            type enumeration {
                                enum false                          { value 0; }
                                enum auto                           { value 1; }
                                enum esm-info                       { value 2; }
                                enum id                             { value 3; }
                            }
                            default "auto";
                            description "DCCA 3GPP charging ID AVP parameter";
                        }

                        leaf three-gpp-ggsn-ipv4-address {
                            type boolean;
                            default "true";
                            description "Include the 3GPP-GGSN Address in Diameter Gy messages";
                        }

                        leaf three-gpp-ggsn-ipv6-address {
                            type boolean;
                            default "false";
                            description "Include the 3GPP-GGSN-Ipv6 address";
                        }

                        leaf three-gpp-gprs-negotiated-qos-profile {
                            type boolean;
                            default "true";
                            description "Include the 3GPP GPRS-QoS-Negotiated-Profile AVP";
                        }

                        leaf three-gpp-imsi {
                            type enumeration {
                                enum false                          { value 0; }
                                enum subscriber-id                  { value 1; }
                                enum circuit-id                     { value 2; }
                                enum imsi                           { value 3; }
                            }
                            default "subscriber-id";
                            description "Origin of the information to send in the IMSI AVP";
                        }

                        leaf three-gpp-nsapi {
                            type boolean;
                            default "true";
                            description "Include the 3GPP-NSAPI";
                        }

                        leaf three-gpp-selection-mode {
                            type boolean;
                            default "true";
                            description "DCCA 3GPP selection mode AVP parameter";
                        }

                        leaf three-gpp-session-stop-indicator {
                            type boolean;
                            default "true";
                            description "DCCA 3GPP session stop indicator AVP parameter";
                        }

                        leaf three-gpp-user-location-info {
                            type boolean;
                            default "false";
                            description "DCCA 3GPP session stop indicator AVP parameter";
                        }

                        leaf address-avp {
                            type boolean;
                            default "true";
                            description "DCCA AVPs that contain the host address or prefix";
                        }

                        leaf pdp-context-type {
                            type boolean;
                            default "true";
                            description "Include the DCCA PDP-Context-Type AVP Parameter";
                        }

                        leaf ps-information {
                            type boolean;
                            default "false";
                            description "Enable reporting of AVPs in grouped PS-Information AVP";
                        }

                        leaf aaa-user-name {
                            type boolean;
                            default "false";
                            description "Include RADIUS user name AVP in Diameter Gy messages";
                        }

                        container three-gpp-rat-type {
                            presence "Enable the three-gpp-rat-type context";
                            description "Enable the three-gpp-rat-type context";

                            leaf type {
                                type uint32 {
                                    range "1..255";
                                }
                                mandatory true;
                                description "Value for 3GPP-RAT-Type AVP";
                            }

                        } // container three-gpp-rat-type

                        container called-station-id {
                            presence "Enable the called-station-id context";
                            description "Enable the called-station-id context";

                            leaf id {
                                type types-sros:string-not-all-spaces {
                                    length "1..64";
                                }
                                mandatory true;
                                description "Called station ID";
                            }

                        } // container called-station-id

                        container charging-rule-base-name {
                            description "Enter the charging-rule-base-name context";

                            choice charging-rule-base-name {
                                default "category-map";
                                case category-map {

                                    leaf category-map {
                                        type empty;
                                        description "Use the category map name in use for this session";
                                    }

                                }
                                case user-string {

                                    leaf user-string {
                                        type types-sros:string-not-all-spaces {
                                            length "1..64";
                                        }
                                        description "String for charging rule base name";
                                    }

                                }
                                case not-included {

                                    leaf not-included {
                                        type empty;
                                        description "Do not include Charging-Rule-Base-Name AVP in Diameter DCCA CCR messages";
                                    }

                                }
                            }
                        } // container charging-rule-base-name

                        container ggsn-address {
                            presence "Enable the ggsn-address context";
                            description "Enable the ggsn-address context";

                            leaf type {
                                type enumeration {
                                    enum ipv4                           { value 1; }
                                    enum ipv6                           { value 2; }
                                }
                                mandatory true;
                                description "Address type of GGSN address AVP";
                            }

                        } // container ggsn-address

                        container service-context-id {
                            presence "Enable the service-context-id context";
                            description "Enable the service-context-id context";

                            leaf id {
                                type types-sros:string-not-all-spaces {
                                    length "1..32";
                                }
                                mandatory true;
                                description "Name for the service context ID AVP";
                            }

                        } // container service-context-id

                        container user-equipment-info-type {
                            presence "Enable the user-equipment-info-type context";
                            description "Enable the user-equipment-info-type context";

                            leaf type {
                                type enumeration {
                                    enum imeisv                         { value 1; }
                                }
                                mandatory true;
                                description "Information to include in User-Equipment-Info attribute";
                            }

                        } // container user-equipment-info-type

                    } // container include-avp

                    container extended-failure-handling {
                        description "Enter the extended-failure-handling context";

                        leaf admin-state {
                            type types-sros:admin-state;
                            default "disable";
                            description "Administrative state of Extended Failure Handling";
                        }

                        leaf new-session-id {
                            type boolean;
                            default "false";
                            description "Enable use of a new session ID for CCR-i messages";
                        }

                        container interim-credit {
                            description "Enter the interim-credit context";

                            leaf max-attempts {
                                type union {
                                    type uint32 {
                                        range "1..4294967295";
                                    }
                                    type enumeration {
                                        enum infinite                       { value 0; }
                                    }
                                }
                                default "10";
                                description "Attempts to retry setting up a session to the OCS";
                            }

                            leaf reporting {
                                type boolean;
                                default "false";
                                description "Report interim Credit";
                            }

                            leaf validity-time {
                                type union {
                                    type types-sros:time-duration {
                                        range "1..4294967295";
                                    }
                                    type enumeration {
                                        enum none                           { value 0; }
                                    }
                                }
                                units "seconds";
                                default "1800";
                                description "Validity time for interim credit";
                            }

                            container volume {
                                description "Enter the volume context";

                                leaf credits {
                                    type uint32 {
                                        range "1..4294967295";
                                    }
                                    default "500";
                                    description "Default volume credit value";
                                }

                                leaf units {
                                    type enumeration {
                                        enum bytes                          { value 0; }
                                        enum kilobytes                      { value 1; }
                                        enum megabytes                      { value 2; }
                                        enum gigabytes                      { value 3; }
                                    }
                                    default "megabytes";
                                    description "Default volume credit units";
                                }

                            } // container volume

                        } // container interim-credit

                    } // container extended-failure-handling

                    container ccrt-replay {
                        presence "Enable the ccrt-replay context";
                        description "Enable the ccrt-replay context";

                        leaf interval {
                            type uint32 {
                                range "60..86400";
                            }
                            default "3600";
                            description "Interval at which CCR-t messages are replayed";
                        }

                        leaf max-lifetime {
                            type types-sros:time-duration {
                                range "1..24";
                            }
                            units "hours";
                            default "24";
                            description "Maximum time that CCR-t messages are replayed";
                        }

                    } // container ccrt-replay

                } // container gy

            } // list diameter-gy-policy

            list diameter-nasreq-policy {
                key "name";
                max-elements 32;
                description "Enter the diameter-nasreq-policy list instance";

                leaf name {
                    type types-sros:named-item;
                    description "Diameter application policy name";
                }

                leaf description {
                    type types-sros:description;
                    description "Text description";
                }

                leaf tx-timer {
                    type types-sros:time-duration {
                        range "10..1000";
                    }
                    units "seconds";
                    default "10";
                    description "Maximum wait time for a pending session request";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice diameter-base {
                    case node {

                        container node {
                            description "Enter the node context";

                            leaf origin-host {
                                type leafref {
                                    path "../../../../aaa/diameter/node/origin-host";
                                }
                                sros-ext:immutable;
                                description "Origin-Host AVP used by the Diameter policy";
                            }

                            leaf destination-realm {
                                type string {
                                    length "1..80";
                                }
                                description "Destination-Realm AVP used by the Diameter peer policy";
                            }

                        } // container node

                    }
                    case peer-policy {
                        status obsolete;

                        leaf peer-policy {
                            status obsolete;
                            type leafref {
                                path "../../../aaa/diameter/peer-policy/name";
                            }
                            sros-ext:immutable;
                            description "Policy for the Diameter peers";
                        }

                    }
                }
                container on-failure {
                    description "Enter the on-failure context";

                    leaf failover {
                        type boolean;
                        default "true";
                        description "Session peer failover";
                    }

                    leaf handling {
                        type enumeration {
                            enum terminate                      { value 1; }
                            enum continue                       { value 2; }
                            enum retry-and-terminate            { value 3; }
                        }
                        default "terminate";
                        description "Session peer failure handling";
                    }

                } // container on-failure

                container nasreq {
                    description "Enter the nasreq context";

                    leaf mac-format {
                        type types-submgt:mac-specification;
                        default "aa:";
                        description "MAC address format";
                    }

                    leaf password {
                        type types-sros:encrypted-leaf {
                            length "1..115";
                        }
                        description "AA-request password";
                    }

                    container user-name {
                        description "Enter the user-name context";

                        leaf format {
                            type enumeration {
                                enum mac                            { value 1; }
                                enum circuit-id                     { value 2; }
                                enum tuple                          { value 3; }
                                enum ascii-converted-circuit-id     { value 4; }
                                enum ascii-converted-tuple          { value 5; }
                                enum dhcp-client-vendor-opts        { value 6; }
                                enum mac-giaddr                     { value 7; }
                                enum nas-port-id                    { value 8; }
                            }
                            default "mac";
                            description "Format type for username";
                        }

                        leaf operation {
                            type types-submgt:user-name-format-domain-operation;
                            description "Operation to perform";
                        }

                        leaf domain-name {
                            type string {
                                length "1..128";
                            }
                            description "Domain name";
                        }

                    } // container user-name

                    container include-avp {
                        description "Enter the include-avp context";

                        leaf called-station-id {
                            type boolean;
                            default "false";
                            description "Include the called station ID AVP";
                        }

                        leaf circuit-id {
                            type boolean;
                            default "false";
                            description "Include the Agent-Circuit-ID AVP";
                        }

                        leaf imei {
                            type boolean;
                            default "false";
                            description "Include the IMEI";
                        }

                        leaf rat-type {
                            type boolean;
                            default "false";
                            description "Include the Radio Access Technology (RAT) type AVP";
                        }

                        leaf remote-id {
                            type boolean;
                            default "false";
                            description "Include the agent remote ID AVP";
                        }

                        leaf user-location-info {
                            type boolean;
                            default "false";
                            description "Include the 3GPP-User-Location-Information AVP";
                        }

                        container calling-station-id {
                            presence "Enable the calling-station-id context";
                            description "Enable the calling-station-id context";

                            leaf type {
                                type enumeration {
                                    enum sap-string                     { value 1; }
                                    enum mac                            { value 2; }
                                    enum sap-id                         { value 3; }
                                    enum remote-id                      { value 4; }
                                    enum llid                           { value 5; }
                                }
                                default "sap-string";
                                description "Format of the Calling-Station-ID AVP";
                            }

                        } // container calling-station-id

                        container nas-port {
                            presence "Enable the nas-port context";
                            description "Enable the nas-port context";

                            leaf bit-spec {
                                type types-sros:binary-specification {
                                    pattern "([01]|(\\*[0123456789]+)?[oismpvc])+";
                                }
                                mandatory true;
                                description "NAS-Port AVP format";
                            }

                        } // container nas-port

                        container nas-port-id {
                            presence "Enable the nas-port-id context";
                            description "Enable the nas-port-id context";

                            leaf prefix-string {
                                type string {
                                    length "1..8";
                                }
                                description "Prefix string for NAS-Port-Id AVP";
                            }

                            container suffix {
                                description "Enter the suffix context";

                                choice suffix {
                                    default "not-included";
                                    description "Configure the format of the nas-port-id suffix.";
                                    case not-included {

                                        leaf not-included {
                                            type empty;
                                            description "Do not add a suffix";
                                        }

                                    }
                                    case circuit-id {

                                        leaf circuit-id {
                                            type empty;
                                            description "Add Circuit ID as suffix";
                                        }

                                    }
                                    case remote-id {

                                        leaf remote-id {
                                            type empty;
                                            description "Add Remote ID as suffix";
                                        }

                                    }
                                    case user-string {

                                        leaf user-string {
                                            type string {
                                                length "1..64";
                                            }
                                            description "Add a user configurable string as suffix";
                                        }

                                    }
                                }
                            } // container suffix

                        } // container nas-port-id

                        container nas-port-type {
                            presence "Enable the nas-port-type context";
                            description "Enable the nas-port-type context";

                            leaf type {
                                type union {
                                    type enumeration {
                                        enum rfc-aligned                    { value 1000; }
                                    }
                                    type uint32 {
                                        range "0..255";
                                    }
                                }
                                default "rfc-aligned";
                                description "NAS-Port-Type AVP value";
                            }

                        } // container nas-port-type

                    } // container include-avp

                } // container nasreq

            } // list diameter-nasreq-policy

            list group-interface-template {
                key "name";
                max-elements 256;
                description "Enter the group-interface-template list instance";

                leaf name {
                    type types-sros:named-item;
                    description "Identifies this group interface template template";
                }

                leaf description {
                    type types-sros:description;
                    description "Text description";
                }

                leaf ip-mtu {
                    type types-router:ip-mtu-ext;
                    units "bytes";
                    description "IP MTU applied to outgoing packets";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container ipv4 {
                    description "Enter the ipv4 context";

                    container icmp {
                        description "Enter the icmp context";

                        leaf mask-reply {
                            type boolean;
                            default "true";
                            description "Allow responses to ICMP mask requests on the interface";
                        }

                        container redirects {
                            description "Enter the redirects context";

                            leaf admin-state {
                                type types-sros:admin-state;
                                default "enable";
                                description "Administrative state of sending ICMP redirect messages";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL expired messages to send";
                            }

                            leaf seconds {
                                type uint16 {
                                    range "1..60";
                                }
                                units "seconds";
                                default "10";
                                description "Time used to limit the number of TTL expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of Parameter Problem messages to send";
                            }

                            leaf seconds {
                                type uint32 {
                                    range "1..60";
                                }
                                units "seconds";
                                default "10";
                                description "Time used to limit number of Parameter Problem messages";
                            }

                        } // container param-problem

                    } // container icmp

                    container neighbor-discovery {
                        description "Enter the neighbor-discovery context";

                        leaf remote-proxy-arp {
                            type boolean;
                            default "false";
                            description "Enable remote proxy ARP on the interface";
                        }

                        leaf-list proxy-arp-policy {
                            type leafref {
                                path "../../../../../policy-options/policy-statement/name";
                            }
                            max-elements 5;
                            ordered-by user;
                            description "Proxy ARP policy name";
                        }

                    } // container neighbor-discovery

                    container urpf-check {
                        presence "Enable the urpf-check context";
                        description "Enable the urpf-check context";

                        leaf mode {
                            type types-router:urpf-check-mode;
                            default "strict";
                            description "Unicast RPF check mode";
                        }

                    } // container urpf-check

                } // container ipv4

                container ipv6 {
                    description "Enter the ipv6 context";

                    container urpf-check {
                        presence "Enable the urpf-check context";
                        description "Enable the urpf-check context";

                        leaf mode {
                            type types-router:urpf-check-mode;
                            default "strict";
                            description "Unicast RPF check mode";
                        }

                    } // container urpf-check

                } // container ipv6

                container trigger-packet {
                    description "Enter the trigger-packet context";

                    leaf data {
                        type boolean;
                        default "false";
                        description "Sample and forward data packets";
                    }

                } // container trigger-packet

            } // list group-interface-template

            list ipoe-session-policy {
                key "name";
                max-elements 256;
                description "Enter the ipoe-session-policy list instance";

                leaf name {
                    type types-sros:named-item;
                    description "IPoE session policy name";
                }

                leaf circuit-id-from-auth {
                    type boolean;
                    sros-ext:immutable;
                    default "false";
                    description "Use circuit ID from authentication server to identify session";
                }

                leaf description {
                    type types-sros:description;
                    description "Text description";
                }

                leaf session-timeout {
                    type union {
                        type uint32 {
                            range "1..31104000";
                        }
                        type enumeration {
                            enum unlimited                      { value 0; }
                        }
                    }
                    default "unlimited";
                    description "Timeout for IPoE sessions";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container session-key {
                    description "Enter the session-key context";

                    leaf sap {
                        type boolean;
                        description "Use the SAP ID as part of the index";
                    }

                    leaf mac {
                        type boolean;
                        description "Use the MAC address as part of the index";
                    }

                    leaf cid {
                        type boolean;
                        sros-ext:immutable;
                        description "Use the Circuit ID as part of the index";
                    }

                    leaf rid {
                        type boolean;
                        sros-ext:immutable;
                        description "Use the remote ID as part of the index";
                    }

                } // container session-key

            } // list ipoe-session-policy

            list sap-template {
                key "name";
                max-elements 256;
                description "Enter the sap-template list instance";

                leaf name {
                    type types-sros:named-item;
                    description "SAP template name";
                }

                leaf description {
                    type types-sros:description;
                    description "Text description";
                }

                leaf dist-cpu-protection {
                    type leafref {
                        path "../../../system/security/dist-cpu-protection/policy/policy-name";
                    }
                    description "Distributed CPU protection policy name";
                }

                leaf hold-time {
                    type union {
                        type types-sros:time-duration {
                            range "0|30..2592000";
                        }
                        type enumeration {
                            enum infinite                       { value -1; }
                        }
                    }
                    units "seconds";
                    default "30";
                    description "Time to hold a SAP after last PFCP session is removed";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container cpu-protection {
                    description "Enter the cpu-protection context";

                    leaf policy-id {
                        type leafref {
                            path "../../../../system/security/cpu-protection/policy/policy-id";
                        }
                        description "CPU protection policy ID";
                    }

                    choice monitoring {
                        case mac {

                            leaf mac-monitoring {
                                type empty;
                                description "Apply CPU protection policy on MAC sources";
                            }

                        }
                        case ip {

                            leaf ip-src-monitoring {
                                type empty;
                                description "Apply CPU protection policy on IP sources";
                            }

                        }
                    }
                } // container cpu-protection

            } // list sap-template

            list steering-profile {
                key "name";
                max-elements 32;
                description "Enter the steering-profile list instance";

                leaf name {
                    type types-sros:named-item;
                    description "Steering profile name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container access {
                    description "Enter the access context";

                    leaf router-instance {
                        type string;
                        description "Router instance to be used as an access VAS router";
                    }

                } // container access

                container network {
                    description "Enter the network context";

                    leaf next-hop {
                        type types-sros:ipv4-unicast-address;
                        description "Next-hop IP address used for network next-hop";
                    }

                    leaf router-instance {
                        type string;
                        description "Router instance to be used as an access VAS router";
                    }

                } // container network

            } // list steering-profile

            container explicit-subscriber-map {
                description "Enter the explicit-subscriber-map context";

                list entry {
                    key "subscriber-id";
                    description "Enter the entry list instance";

                    leaf subscriber-id {
                        type types-submgt:subscriber-id;
                        description "Subscriber Identification string";
                    }

                    leaf sub-profile {
                        type leafref {
                            path "../../../sub-profile/name";
                        }
                        description "Subscriber profile name";
                    }

                    leaf alias {
                        type string {
                            length "1..64";
                        }
                        description "Alias for subscriber identification string";
                    }

                    leaf sla-profile {
                        type leafref {
                            path "../../../sla-profile/name";
                        }
                        description "SLA profile name";
                    }

                    leaf app-profile {
                        type leafref {
                            path "../../../../application-assurance/group/partition/policy/app-profile/app-profile-name";
                        }
                        description "Application profile name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list entry

            } // container explicit-subscriber-map

            list accu-stats-policy {
                key "name";
                max-elements 32;
                description "Enter the accu-stats-policy list instance";

                leaf name {
                    type types-sros:named-item;
                    description "Policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list egress {
                    key "type id";
                    max-elements 4;
                    description "Add a list entry for egress";

                    leaf type {
                        type types-submgt:queue-or-policer;
                        description "Type";
                    }

                    leaf id {
                        type types-submgt:queue-or-policer-id;
                        description "Queue or policer ID";
                    }

                } // list egress

                list ingress {
                    key "type id";
                    max-elements 4;
                    description "Add a list entry for ingress";

                    leaf type {
                        type types-submgt:queue-or-policer;
                        description "Type";
                    }

                    leaf id {
                        type types-submgt:queue-or-policer-id;
                        description "Queue or policer ID";
                    }

                } // list ingress

            } // list accu-stats-policy

            list host-tracking-policy {
                key "name";
                description "Enter the host-tracking-policy list instance";

                leaf name {
                    type types-sros:named-item;
                    description "Host tracking policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container egress-rate-modify {
                    description "Enter the egress-rate-modify context";

                    choice rate-modify {
                        case agg-rate {

                            leaf agg-rate {
                                type empty;
                                description "Maximum total rate for all subscriber egress queues";
                            }

                        }
                        case scheduler {

                            leaf scheduler {
                                type types-sros:named-item;
                                description "Scheduler to be applied for rate modification";
                            }

                        }
                    }
                } // container egress-rate-modify

            } // list host-tracking-policy

            list igmp-policy {
                key "name";
                description "Enter the igmp-policy list instance";

                leaf name {
                    type types-sros:named-item;
                    description "Policy name";
                }

                leaf description {
                    type types-sros:description;
                    description "Text description";
                }

                leaf redirection-policy {
                    type leafref {
                        path "../../../policy-options/policy-statement/name";
                    }
                    description "Multicast redirection action applied to the subscriber";
                }

                leaf replication {
                    type enumeration {
                        enum per-sap                        { value 0; }
                        enum per-host                       { value 1; }
                        enum per-spi                        { value 2; }
                    }
                    default "per-sap";
                    description "Multicast replication mode for subscriber multicast";
                }

                leaf fast-leave {
                    type boolean;
                    default "true";
                    description "Enable fast leave";
                }

                leaf use-multicast-destination-mac {
                    type boolean;
                    default "false";
                    description "Use multicast destination mac address for outgoing traffic.";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf import-policy {
                    type leafref {
                        path "../../../policy-options/policy-statement/name";
                    }
                    description "Import policy that filters IGMP packets";
                }

                leaf version {
                    type types-igmp:igmp-version;
                    default "3";
                    description "IGMP protocol version";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container egress-rate-modify {
                    description "Enter the egress-rate-modify context";

                    choice rate-modify {
                        case agg-rate {

                            leaf agg-rate {
                                type empty;
                                description "Maximum total rate for all subscriber egress queues";
                            }

                        }
                        case scheduler {

                            leaf scheduler {
                                type types-sros:named-item;
                                description "Scheduler to be applied for rate modification";
                            }

                        }
                    }
                } // container egress-rate-modify

                container static {
                    description "Enter the static context";

                    list group {
                        key "group-address";
                        description "Enter the group list instance";

                        leaf group-address {
                            type types-sros:ipv4-multicast-address;
                            description "Group address of static IGMP multicast channel";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice source-or-starg {
                            mandatory true;
                            case source {

                                list source {
                                    key "source-address";
                                    description "Add a list entry for source";

                                    leaf source-address {
                                        type types-sros:ipv4-unicast-address;
                                        description "Source IP address of multicast channel sending data";
                                    }

                                } // list source

                            }
                            case starg {

                                leaf starg {
                                    type empty;
                                    description "any source address (*,G)";
                                }

                            }
                        }
                    } // list group

                } // container static

                container multicast-reporter {
                    description "Enter the multicast-reporter context";

                    leaf destination {
                        type leafref {
                            path "../../../../multicast-management/multicast-reporting-destination/name";
                        }
                        description "Multicast reporter destination";
                    }

                    leaf admin-state {
                        type types-sros:admin-state;
                        default "disable";
                        description "Administrative state of the multicast reporter";
                    }

                    container optional-fields {
                        description "Enter the optional-fields context";

                        leaf host-mac {
                            type boolean;
                            default "false";
                            description "Include host mac address";
                        }

                        leaf pppoe-session-id {
                            type boolean;
                            default "false";
                            description "Include PPPoE session ID in multicast reporting message";
                        }

                        leaf svc-id {
                            type boolean;
                            default "false";
                            description "Include service ID";
                        }

                        leaf sap-id {
                            type boolean;
                            default "false";
                            description "Include sap ID";
                        }

                    } // container optional-fields

                } // container multicast-reporter

            } // list igmp-policy

            list mld-policy {
                key "name";
                description "Enter the mld-policy list instance";

                leaf name {
                    type types-sros:named-item;
                    description "Policy name";
                }

                leaf description {
                    type types-sros:description;
                    description "Text description";
                }

                leaf redirection-policy {
                    type leafref {
                        path "../../../policy-options/policy-statement/name";
                    }
                    description "Multicast redirection action applied to the subscriber";
                }

                leaf replication {
                    type enumeration {
                        enum per-sap                        { value 0; }
                        enum per-host                       { value 1; }
                        enum per-spi                        { value 2; }
                    }
                    default "per-sap";
                    description "Multicast replication mode for subscriber multicast";
                }

                leaf fast-leave {
                    type boolean;
                    default "true";
                    description "Enable fast leave";
                }

                leaf use-multicast-destination-mac {
                    type boolean;
                    default "false";
                    description "Use multicast destination mac address for outgoing traffic.";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf import-policy {
                    type leafref {
                        path "../../../policy-options/policy-statement/name";
                    }
                    description "Import policy to filter MLD packets";
                }

                leaf version {
                    type types-igmp:mld-version;
                    default "2";
                    description "MLD protocol version";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container egress-rate-modify {
                    description "Enter the egress-rate-modify context";

                    choice rate-modify {
                        case agg-rate {

                            leaf agg-rate {
                                type empty;
                                description "Maximum total rate for all subscriber egress queues";
                            }

                        }
                        case scheduler {

                            leaf scheduler {
                                type types-sros:named-item;
                                description "Scheduler to be applied for rate modification";
                            }

                        }
                    }
                } // container egress-rate-modify

                container static {
                    description "Enter the static context";

                    list group {
                        key "group-address";
                        description "Enter the group list instance";

                        leaf group-address {
                            type types-sros:ipv6-multicast-address;
                            description "Group address of multicast channel";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice source-or-starg {
                            mandatory true;
                            case source {

                                list source {
                                    key "source-address";
                                    description "Add a list entry for source";

                                    leaf source-address {
                                        type types-sros:ipv6-unicast-address;
                                        description "Source IP address";
                                    }

                                } // list source

                            }
                            case starg {

                                leaf starg {
                                    type empty;
                                    description "any source address (*,G)";
                                }

                            }
                        }
                    } // list group

                } // container static

            } // list mld-policy

            list sub-mcac-policy {
                key "name";
                description "Enter the sub-mcac-policy list instance";

                leaf name {
                    type types-sros:named-item;
                    description "Policy name";
                }

                leaf description {
                    type types-sros:description;
                    description "Text description";
                }

                leaf admin-state {
                    type types-sros:admin-state;
                    default "disable";
                    description "Administrative state of the subscriber MCAC policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container bandwidth {
                    description "Enter the bandwidth context";

                    leaf total {
                        type types-mcast-cac:bandwidth-limit;
                        description "Maximum allowed bandwidth";
                    }

                    leaf mandatory {
                        type types-mcast-cac:bandwidth-limit;
                        description "Pre-reserved bandwidth for all mandatory channels";
                    }

                } // container bandwidth

            } // list sub-mcac-policy

            container pfcp {
                description "Enter the pfcp context";

                list association {
                    key "name";
                    max-elements 1;
                    description "Enter the association list instance";

                    leaf name {
                        type types-sros:named-item;
                        description "PFCP association name";
                    }

                    leaf description {
                        type types-sros:description;
                        description "Text description";
                    }

                    leaf admin-state {
                        type types-sros:admin-state;
                        default "disable";
                        description "Administrative state of the PFCP association";
                    }

                    leaf association-setup-retry {
                        status obsolete;
                        type types-sros:time-duration {
                            range "1..36000";
                        }
                        units "seconds";
                        default "10";
                        description "Time to wait between successive association attempts";
                    }

                    leaf association-release-timeout {
                        type union {
                            type enumeration {
                                enum none                           { value 0; }
                            }
                            type types-sros:time-duration {
                                range "30..3600";
                            }
                        }
                        units "seconds";
                        default "3600";
                        description "Time to wait for a response to a release request";
                    }

                    leaf path-restoration-time {
                        type types-sros:time-duration {
                            range "1..11520";
                        }
                        units "minutes";
                        description "Time to wait before declaring the path down";
                    }

                    leaf python-policy {
                        type leafref {
                            path "../../../../python/python-policy/name";
                        }
                        description "Python policy to process PFCP messages";
                    }

                    leaf bfd-expedited-path-down {
                        type boolean;
                        default "false";
                        description "Track BFD sessions to expedite PFCP path down detection";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container node-id {
                        description "Enter the node-id context";

                        choice node-id-type {
                            default "use-ip-address";
                            case fqdn {

                                leaf fqdn {
                                    type types-sros:fully-qualified-domain-name;
                                    sros-ext:auto-restart-to-modify;
                                    description "FQDN that identifies the local system for PFCP";
                                }

                            }
                            case use-ip-address {

                                leaf use-ip-address {
                                    type empty;
                                    sros-ext:auto-restart-to-modify;
                                    description "Use the IP address of interface for the association";
                                }

                            }
                        }
                    } // container node-id

                    container interface {
                        description "Enter the interface context";

                        leaf router-instance {
                            type string;
                            sros-ext:auto-restart-to-modify;
                            description "Router context for the PFCP association";
                        }

                        leaf name {
                            type types-sros:interface-name;
                            sros-ext:auto-restart-to-modify;
                            description "Name of the interface to use for the association";
                        }

                    } // container interface

                    container peer {
                        description "Enter the peer context";

                        choice node-id-type {
                            case ip-address {

                                leaf ip-address {
                                    type types-sros:ip-unicast-address;
                                    sros-ext:auto-restart-to-modify;
                                    description "PFCP peer IP address";
                                }

                            }
                        }
                    } // container peer

                    container heartbeat {
                        description "Enter the heartbeat context";

                        leaf interval {
                            type types-sros:time-duration {
                                range "5..180";
                            }
                            units "seconds";
                            default "60";
                            description "Time between two successful heartbeat request messages";
                        }

                        leaf timeout {
                            type types-sros:time-duration {
                                range "1..20";
                            }
                            units "seconds";
                            default "5";
                            description "Time the system waits for a heartbeat response message";
                        }

                        leaf retries {
                            type uint32 {
                                range "0..30";
                            }
                            default "4";
                            description "Number of retries after the heartbeat timeout expires";
                        }

                    } // container heartbeat

                    container tx {
                        description "Enter the tx context";

                        leaf timeout {
                            type types-sros:time-duration {
                                range "1..30";
                            }
                            units "seconds";
                            default "1";
                            description "Retransmission timer";
                        }

                        leaf retries {
                            type uint32 {
                                range "0..7";
                            }
                            default "3";
                            description "Number of retries";
                        }

                        leaf ttl {
                            type uint32 {
                                range "1..255";
                            }
                            default "255";
                            description "TTL value in the IP header of egress PFCP packets";
                        }

                    } // container tx

                    container nat {
                        description "Enter the nat context";

                        choice isa {
                            case nat {

                                leaf nat-group {
                                    type leafref {
                                        path "../../../../../isa/nat-group/id";
                                    }
                                    description "NAT group used for CUPS NAT functionality";
                                }

                            }
                            case wlan-gw {

                                leaf wlan-gw-group {
                                    type leafref {
                                        path "../../../../../isa/wlan-gw-group/id";
                                    }
                                    description "WLAN gateway group used for CUPS NAT functionality";
                                }

                            }
                        }
                    } // container nat



                } // list association

            } // container pfcp

            list pim-policy {
                key "name";
                max-elements 1;
                description "Enter the pim-policy list instance";

                leaf name {
                    type types-sros:named-item;
                    description "Policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list pim-policy

            list sub-profile {
                key "name";
                description "Enter the sub-profile list instance";

                leaf name {
                    type types-sros:external-named-item;
                    description "Subscriber profile name";
                }

                leaf description {
                    type types-sros:description;
                    description "Text description";
                }

                leaf accounting-policy {
                    type leafref {
                        path "../../../log/accounting-policy/policy-id";
                    }
                    description "Accounting policy";
                }

                leaf accu-stats-policy {
                    type leafref {
                        path "../../accu-stats-policy/name";
                    }
                    description "Accumulated statistics policy";
                }

                leaf collect-stats {
                    type boolean;
                    default "false";
                    description "Collect statistics";
                }

                leaf firewall-policy {
                    type leafref {
                        path "../../../service/nat/firewall-policy/name";
                    }
                    description "Firewall policy";
                }

                leaf host-tracking-policy {
                    type leafref {
                        path "../../host-tracking-policy/name";
                    }
                    description "Host tracking policy";
                }

                leaf hs-sla-mode {
                    type enumeration {
                        enum expanded                       { value 0; }
                        enum single                         { value 1; }
                    }
                    default "expanded";
                    description "HS board subscriber SLA mode";
                }

                leaf igmp-policy {
                    type leafref {
                        path "../../igmp-policy/name";
                    }
                    description "IGMP policy";
                }

                leaf mld-policy {
                    type leafref {
                        path "../../mld-policy/name";
                    }
                    description "MLD policy";
                }

                leaf pim-policy {
                    type leafref {
                        path "../../pim-policy/name";
                    }
                    description "Protocol Independent Multicast (PIM) policy";
                }

                leaf preference {
                    type uint32 {
                        range "1..10";
                    }
                    default "5";
                    description "Relative preference value for the subscriber profile";
                }

                leaf secondary-shaper-hashing {
                    type boolean;
                    default "false";
                    description "Include LAG hashing on secondary shaper";
                }

                leaf sub-mcac-policy {
                    type leafref {
                        path "../../sub-mcac-policy/name";
                    }
                    description "Subscriber MCAC policy";
                }

                leaf upnp-policy {
                    type leafref {
                        path "../../../service/upnp/policy/name";
                    }
                    description "UPnP policy for the subscriber profile";
                }

                leaf volume-stats-type {
                    type enumeration {
                        enum l2                             { value 0; }
                        enum ip                             { value 1; }
                    }
                    default "l2";
                    description "Include non-IP headers in the accounting statistics";
                }

                leaf vport-hashing {
                    type boolean;
                    default "false";
                    description "Include LAG hashing on Vport";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container control {
                    description "Enter the control context";

                    leaf local {
                        type boolean;
                        default "true";
                        description "Allow the local control plane to use the profile";
                    }

                    leaf cups {
                        type boolean;
                        default "false";
                        description "Allow the CUPS control plane to use the profile";
                    }

                } // container control

                container nat {
                    description "Enter the nat context";

                    leaf policy {
                        type leafref {
                            path "../../../../service/nat/nat-policy/name";
                        }
                        description "NAT policy associated with the subscriber profile";
                    }

                    leaf prefix-list {
                        type leafref {
                            path "../../../../service/nat/prefix-list/name";
                        }
                        description "NAT prefix list name";
                    }

                    leaf allow-bypass {
                        type boolean;
                        default "false";
                        description "Allow traffic to bypass NAT";
                    }

                    leaf access-mode {
                        type enumeration {
                            enum auto {
                                value 1;
                                description "Automatically derived from the access SAP's anti-spoof type";
                            }
                            enum bridged {
                                value 2;
                                description "Force to bridged mode";
                            }
                        }
                        default "auto";
                        description "The subscriber NAT access mode";
                    }

                } // container nat

                container ancp {
                    description "Enter the ancp context";

                    leaf ancp-policy {
                        type leafref {
                            path "../../../ancp/ancp-policy/name";
                        }
                        description "ANCP policy for this subscriber profile";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container ancp

                container egress {
                    description "Enter the egress context";

                    container lag-per-link-hash {
                        description "Enter the lag-per-link-hash context";

                        leaf class {
                            type types-services:sap-lag-per-link-hash-class;
                            default "1";
                            description "Class used to select a LAG link";
                        }

                        leaf weight {
                            type types-services:sap-lag-per-link-hash-weight;
                            default "1";
                            description "Weight associated with SAP when selecting a LAG link";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container lag-per-link-hash

                    container qos {
                        description "Enter the qos context";

                        leaf hs-agg-rate {
                            type int32 {
                                range "1..100000000";
                            }
                            units "kilobps";
                            description "Maximum rate for single egress HS queues";
                        }

                        leaf hs-min-resv-bw {
                            type int32 {
                                range "0..100000000";
                            }
                            units "kilobps";
                            default "1";
                            description "Reserved minimum total rate of all egress queues";
                        }

                        leaf hs-low-burst-max-class {
                            type uint32 {
                                range "1..6";
                            }
                            default "6";
                            description "Scheduling classes to map the low burst limit threshold";
                        }

                        container agg-rate {
                            description "Enter the agg-rate context";

                            leaf rate {
                                type int32 {
                                    range "1..800000000";
                                }
                                units "kilobps";
                                description "Maximum total rate of all egress queues";
                            }

                            leaf min-resv-bw {
                                type int32 {
                                    range "0..800000000";
                                }
                                units "kilobps";
                                default "1";
                                description "Reserved minimum total rate of all egress queues";
                            }

                            leaf adaptation-rule {
                                type types-qos:adaptation-rule;
                                default "closest";
                                description "Adaptation rule for operational PIR value of subscriber";
                            }

                            leaf burst-limit {
                                type union {
                                    type types-qos:bytes {
                                        range "1..14000000";
                                    }
                                    type enumeration {
                                        enum auto                           { value -1; }
                                    }
                                }
                                default "auto";
                                description "Burst limit of the subscriber aggregate rate";
                            }

                            leaf queue-frame-based-accounting {
                                type boolean;
                                default "false";
                                description "Use frame-based accounting to evaluate rate limit";
                            }

                        } // container agg-rate

                        container encap-offset {
                            presence "Enable the encap-offset context";
                            description "Enable the encap-offset context";

                            leaf type {
                                type enumeration {
                                    enum pppoa-llc                      { value 1; }
                                    enum pppoa-null                     { value 2; }
                                    enum pppoeoa-llc                    { value 3; }
                                    enum pppoeoa-llc-fcs                { value 4; }
                                    enum pppoeoa-llc-tagged             { value 5; }
                                    enum pppoeoa-llc-tagged-fcs         { value 6; }
                                    enum pppoeoa-null                   { value 7; }
                                    enum pppoeoa-null-fcs               { value 8; }
                                    enum pppoeoa-null-tagged            { value 9; }
                                    enum pppoeoa-null-tagged-fcs        { value 10; }
                                    enum ipoa-llc                       { value 11; }
                                    enum ipoa-null                      { value 12; }
                                    enum ipoeoa-llc                     { value 13; }
                                    enum ipoeoa-llc-fcs                 { value 14; }
                                    enum ipoeoa-llc-tagged              { value 15; }
                                    enum ipoeoa-llc-tagged-fcs          { value 16; }
                                    enum ipoeoa-null                    { value 17; }
                                    enum ipoeoa-null-fcs                { value 18; }
                                    enum ipoeoa-null-tagged             { value 19; }
                                    enum ipoeoa-null-tagged-fcs         { value 20; }
                                    enum pppoe                          { value 21; }
                                    enum pppoe-tagged                   { value 22; }
                                    enum ipoe                           { value 23; }
                                    enum ipoe-tagged                    { value 24; }
                                }
                                description "Offset type";
                            }

                        } // container encap-offset

                        container policer-control-policy {
                            description "Enter the policer-control-policy context";

                            leaf policy-name {
                                type leafref {
                                    path "../../../../../../qos/policer-control-policy/policer-control-policy-name";
                                }
                                description "Policer control policy name";
                            }

                            container overrides {
                                description "Enter the overrides context";

                                container root {
                                    presence "Enable the root context";
                                    description "Enable the root context";

                                    leaf max-rate {
                                        type types-qos:policer-pir-rate-override;
                                        units "kilobps";
                                        description "Maximum rate";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container priority-mbs-thresholds {
                                        description "Enter the priority-mbs-thresholds context";

                                        leaf min-thresh-separation {
                                            type types-qos:policer-burst-size-override;
                                            description "Minimum threshold separation";
                                        }

                                        list priority {
                                            key "level";
                                            description "Enter the priority list instance";

                                            leaf level {
                                                type types-qos:hierarchy-level;
                                                description "Strict priority level";
                                            }

                                            leaf mbs-contribution {
                                                type types-qos:policer-burst-size-override;
                                                description "MBS size";
                                            }

                                            leaf-list apply-groups {
                                                type leafref {
                                                    path "../../../../../../../../../../groups/group/name";
                                                }
                                                max-elements 8;
                                                ordered-by user;
                                                description "Apply a configuration group at this level";
                                            }

                                            leaf-list apply-groups-exclude {
                                                type leafref {
                                                    path "../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type leafref {
                                            path "../../../../../../../../qos/scheduler-policy[scheduler-policy-name=current()/../../../policy-name]/tier/scheduler/scheduler-name";
                                        }
                                        description "Scheduler policy name";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:scheduler-pir-rate;
                                            units "kilobps";
                                            default "max";
                                            description "PIR to override administrative PIR used by scheduler";
                                        }

                                        leaf cir {
                                            type types-qos:scheduler-cir-rate;
                                            units "kilobps";
                                            default "sum";
                                            description "CIR to override administrative CIR used by scheduler";
                                        }

                                    } // container rate

                                } // list scheduler

                            } // container overrides

                        } // container scheduler-policy

                    } // container qos

                } // container egress

                container ingress {
                    description "Enter the ingress context";

                    container qos {
                        description "Enter the qos context";

                        container policer-control-policy {
                            description "Enter the policer-control-policy context";

                            leaf policy-name {
                                type leafref {
                                    path "../../../../../../qos/policer-control-policy/policer-control-policy-name";
                                }
                                description "Policer control policy name";
                            }

                            container overrides {
                                description "Enter the overrides context";

                                container root {
                                    presence "Enable the root context";
                                    description "Enable the root context";

                                    leaf max-rate {
                                        type types-qos:policer-pir-rate-override;
                                        units "kilobps";
                                        description "Maximum rate";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container priority-mbs-thresholds {
                                        description "Enter the priority-mbs-thresholds context";

                                        leaf min-thresh-separation {
                                            type types-qos:policer-burst-size-override;
                                            description "Minimum threshold separation";
                                        }

                                        list priority {
                                            key "level";
                                            description "Enter the priority list instance";

                                            leaf level {
                                                type types-qos:hierarchy-level;
                                                description "Strict priority level";
                                            }

                                            leaf mbs-contribution {
                                                type types-qos:policer-burst-size-override;
                                                description "MBS size";
                                            }

                                            leaf-list apply-groups {
                                                type leafref {
                                                    path "../../../../../../../../../../groups/group/name";
                                                }
                                                max-elements 8;
                                                ordered-by user;
                                                description "Apply a configuration group at this level";
                                            }

                                            leaf-list apply-groups-exclude {
                                                type leafref {
                                                    path "../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type leafref {
                                            path "../../../../../../../../qos/scheduler-policy[scheduler-policy-name=current()/../../../policy-name]/tier/scheduler/scheduler-name";
                                        }
                                        description "Scheduler policy name";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:scheduler-pir-rate;
                                            units "kilobps";
                                            default "max";
                                            description "PIR to override administrative PIR used by scheduler";
                                        }

                                        leaf cir {
                                            type types-qos:scheduler-cir-rate;
                                            units "kilobps";
                                            default "sum";
                                            description "CIR to override administrative CIR used by scheduler";
                                        }

                                    } // container rate

                                } // list scheduler

                            } // container overrides

                        } // container scheduler-policy

                    } // container qos

                } // container ingress

                container radius-accounting {
                    description "Enter the radius-accounting context";

                    leaf-list policy {
                        type leafref {
                            path "../../../radius-accounting-policy/name";
                        }
                        max-elements 5;
                        ordered-by user;
                        description "RADIUS accounting policies";
                    }

                    leaf session-optimized-stop {
                        type boolean;
                        default "false";
                        description "Optimize PPPoE session accounting stop behavior";
                    }

                } // container radius-accounting

                container sla-profile-map {
                    description "Enter the sla-profile-map context";

                    leaf use-direct-map-as-default {
                        type boolean;
                        default "false";
                        description "Allow direct mapping of SLA profile as default";
                    }

                    list entry {
                        key "sla-profile-string";
                        description "Enter the entry list instance";

                        leaf sla-profile-string {
                            type string {
                                length "1..32";
                            }
                            description "SLA profile string";
                        }

                        leaf sla-profile {
                            type leafref {
                                path "../../../../sla-profile/name";
                            }
                            mandatory true;
                            description "SLA profile";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list entry

                } // container sla-profile-map

                container session-limits {
                    description "Enter the session-limits context";

                    leaf ipoe {
                        type types-submgt:sla-profile-host-limit-with-zero;
                        description "Maximum number of IPoE sessions";
                    }

                    leaf overall {
                        type types-submgt:sla-profile-host-limit-with-zero;
                        description "Maximum number of subscriber sessions";
                    }

                    container pppoe {
                        description "Enter the pppoe context";

                        leaf local {
                            type types-submgt:sla-profile-host-limit-with-zero;
                            description "Maximum number of PPPoE local-terminated sessions";
                        }

                        leaf lac {
                            type types-submgt:sla-profile-host-limit-with-zero;
                            description "Maximum number of PPPoE L2TP LAC sessions";
                        }

                        leaf overall {
                            type types-submgt:sla-profile-host-limit-with-zero;
                            description "Maximum number of PPPoE sessions";
                        }

                    } // container pppoe

                    container l2tp {
                        description "Enter the l2tp context";

                        leaf lns {
                            type types-submgt:sla-profile-host-limit-with-zero;
                            description "Maximum number of L2TP LNS sessions";
                        }

                        leaf lts {
                            type types-submgt:sla-profile-host-limit-with-zero;
                            description "Maximum number of L2TP LTS sessions";
                        }

                        leaf overall {
                            type types-submgt:sla-profile-host-limit-with-zero;
                            description "Maximum number of L2TP sessions";
                        }

                    } // container l2tp

                } // container session-limits

                container host-limits {
                    description "Enter the host-limits context";

                    leaf lac-overall {
                        type types-submgt:sla-profile-host-limit-with-zero;
                        description "Maximum number of L2TP LAC hosts";
                    }

                    leaf overall {
                        type types-submgt:sla-profile-host-limit;
                        description "Maximum number of subscriber hosts";
                    }

                    container ipv4 {
                        description "Enter the ipv4 context";

                        leaf arp {
                            type types-submgt:sla-profile-host-limit-with-zero;
                            description "Maximum number of IPv4 ARP hosts";
                        }

                        leaf dhcp {
                            type types-submgt:sla-profile-host-limit-with-zero;
                            description "Maximum number of IPv4 DHCP hosts";
                        }

                        leaf overall {
                            type types-submgt:sla-profile-host-limit-with-zero;
                            description "Maximum number of IPv4 hosts";
                        }

                        leaf ppp {
                            type types-submgt:sla-profile-host-limit-with-zero;
                            description "Maximum number of IPv4 PPP hosts";
                        }

                    } // container ipv4

                    container ipv6 {
                        description "Enter the ipv6 context";

                        leaf overall {
                            type types-submgt:sla-profile-host-limit-with-zero;
                            description "Maximum number of IPv6 hosts";
                        }

                        leaf pd-ipoe-dhcp {
                            type types-submgt:sla-profile-host-limit-with-zero;
                            description "Maximum number of IPv6 IPoE DHCP PD hosts";
                        }

                        leaf pd-overall {
                            type types-submgt:sla-profile-host-limit-with-zero;
                            description "Maximum number of IPv6 DHCP PD hosts";
                        }

                        leaf pd-ppp-dhcp {
                            type types-submgt:sla-profile-host-limit-with-zero;
                            description "Maximum number of IPv6 PPPoE DHCP PD hosts";
                        }

                        leaf wan-ipoe-dhcp {
                            type types-submgt:sla-profile-host-limit-with-zero;
                            description "Maximum number of IPv6 IPoE DHCP WAN hosts";
                        }

                        leaf wan-ipoe-slaac {
                            type types-submgt:sla-profile-host-limit-with-zero;
                            description "Maximum number of IPv6 IPoE SLAAC WAN hosts";
                        }

                        leaf wan-overall {
                            type types-submgt:sla-profile-host-limit-with-zero;
                            description "Maximum number of IPv6 WAN hosts";
                        }

                        leaf wan-ppp-dhcp {
                            type types-submgt:sla-profile-host-limit-with-zero;
                            description "Maximum number of IPv6 PPPoE DHCP WAN hosts";
                        }

                        leaf wan-ppp-slaac {
                            type types-submgt:sla-profile-host-limit-with-zero;
                            description "Maximum number of IPv6 PPPoE SLAAC WAN hosts";
                        }

                    } // container ipv6

                } // container host-limits

            } // list sub-profile

            list sla-profile {
                key "name";
                description "Enter the sla-profile list instance";

                leaf name {
                    type types-sros:external-named-item;
                    description "SLA profile name";
                }

                leaf description {
                    type types-sros:description;
                    description "Text description";
                }

                leaf credit-control-policy {
                    type leafref {
                        path "../../credit-control-policy/name";
                    }
                    description "Credit policy for this SLA profile";
                }

                leaf def-instance-sharing {
                    type enumeration {
                        enum per-sap                        { value 1; }
                        enum per-session                    { value 2; }
                    }
                    default "per-sap";
                    description "Default SPI sharing method for IPoE or PPPoE sessions";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container control {
                    description "Enter the control context";

                    leaf local {
                        type boolean;
                        default "true";
                        description "Allow the local control plane to use the profile";
                    }

                    leaf cups {
                        type boolean;
                        default "false";
                        description "Allow the CUPS control plane to use the profile";
                    }

                } // container control

                container idle-timeout {
                    presence "Enable the idle-timeout context";
                    description "Enable the idle-timeout context";

                    leaf category-map-name {
                        type leafref {
                            path "../../../category-map/category-map-name";
                        }
                        sros-ext:immutable;
                        mandatory true;
                        description "Category map name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list category {
                        key "category-name";
                        max-elements 16;
                        description "Enter the category list instance";

                        leaf category-name {
                            type leafref {
                                path "../../../../category-map[category-map-name=current()/../../category-map-name]/category/category-name";
                            }
                            description "Category name";
                        }

                        leaf timeout {
                            type uint32 {
                                range "60..15552000";
                            }
                            units "seconds";
                            description "Time the category can stay below its activity threshold";
                        }

                        leaf action {
                            type enumeration {
                                enum terminate                      { value 1; }
                                enum shcv                           { value 2; }
                            }
                            default "terminate";
                            description "Action when the idle-timeout is reached";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list category

                } // container idle-timeout

                container egress {
                    description "Enter the egress context";

                    leaf ip-filter {
                        type leafref {
                            path "../../../../filter/ip-filter/filter-name";
                        }
                        description "IPv4 filter policy name";
                    }

                    leaf ipv6-filter {
                        type leafref {
                            path "../../../../filter/ipv6-filter/filter-name";
                        }
                        description "IPv6 filter policy name";
                    }

                    container bonding-selection {
                        description "Enter the bonding-selection context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container rate-thresholds {
                            description "Enter the rate-thresholds context";

                            leaf high {
                                type uint32 {
                                    range "56..99";
                                }
                                units "percent";
                                default "90";
                                description "High threshold rate percentage";
                            }

                            leaf low {
                                type uint32 {
                                    range "55..98";
                                }
                                units "percent";
                                default "80";
                                description "Low threshold rate percentage";
                            }

                        } // container rate-thresholds

                        container weight {
                            description "Enter the weight context";

                            leaf initial {
                                type uint32 {
                                    range "1..100";
                                }
                                units "percent";
                                default "100";
                                description "Initial weight of the preferred connection";
                            }

                            leaf change {
                                type uint32 {
                                    range "0..10";
                                }
                                units "percent";
                                default "5";
                                description "Weight change of the preferred connection";
                            }

                        } // container weight

                    } // container bonding-selection

                    container qos {
                        description "Enter the qos context";

                        leaf hs-agg-rate {
                            type int32 {
                                range "1..100000000";
                            }
                            units "kilobps";
                            description "Maximum rate for expanded egress HS queues";
                        }

                        leaf qos-marking-from-sap {
                            type boolean;
                            default "true";
                            description "Set policy where egress QoS marking rules are applied";
                        }

                        leaf use-ingress-l2tp-dscp {
                            type boolean;
                            default "false";
                            description "Use outer L2TP header for LAC sessions";
                        }

                        container sap-egress {
                            description "Enter the sap-egress context";

                            leaf policy-name {
                                type leafref {
                                    path "../../../../../../qos/sap-egress/sap-egress-policy-name";
                                }
                                description "SAP-egress QoS policy";
                            }

                            leaf port-parent-location {
                                type enumeration {
                                    enum port                           { value 1; }
                                    enum vport                          { value 2; }
                                }
                                default "port";
                                description "Scheduling type for queued traffic";
                            }

                            container overrides {
                                description "Enter the overrides context";

                                leaf hs-queue-stat-mode {
                                    type enumeration {
                                        enum v4-v6                          { value 0; }
                                    }
                                    description "Egress HS queue stats mode";
                                }

                                list hs-wrr-group {
                                    key "id";
                                    description "Enter the hs-wrr-group list instance";

                                    leaf id {
                                        type leafref {
                                            path "../../../../../../../../qos/sap-egress[sap-egress-policy-name=current()/../../../policy-name]/hs-wrr-group/group-id";
                                        }
                                        description "HS WRR group ID to override in the QoS policy table";
                                    }

                                    leaf hs-class-weight {
                                        type types-qos:hs-class-weight-override;
                                        description "Class weight override for WRR group";
                                    }

                                    leaf rate {
                                        type types-qos:hs-wrr-rate-override;
                                        units "kilobps";
                                        description "PIR rate override for WRR group";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                } // list hs-wrr-group

                                list policer {
                                    key "id";
                                    description "Enter the policer list instance";

                                    leaf id {
                                        type leafref {
                                            path "../../../../../../../../qos/sap-egress[sap-egress-policy-name=current()/../../../policy-name]/policer/policer-id";
                                        }
                                        description "Policer ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:egress-per-packet-offset-override;
                                        description "Packet byte offset";
                                    }

                                    leaf stat-mode {
                                        type types-submgt:subscriber-egress-policer-stat-mode-type;
                                        description "Stat mode for the policer";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:policer-pir-rate-override;
                                            units "kilobps";
                                            description "PIR override for the packet bye offset";
                                        }

                                        leaf cir {
                                            type types-qos:policer-cir-rate-override;
                                            units "kilobps";
                                            description "CIR override for the packet byte offset";
                                        }

                                    } // container rate

                                } // list policer

                                list queue {
                                    key "id";
                                    description "Enter the queue list instance";

                                    leaf id {
                                        type leafref {
                                            path "../../../../../../../../qos/sap-egress[sap-egress-policy-name=current()/../../../policy-name]/queue/queue-id";
                                        }
                                        description "Queue ID";
                                    }

                                    leaf avg-frame-overhead {
                                        type decimal64 {
                                            range "0.00..100.00";
                                            fraction-digits 2;
                                        }
                                        units "percent";
                                        description "Average frame overhead";
                                    }

                                    leaf cbs {
                                        type types-qos:burst-size-override;
                                        units "kilobytes";
                                        description "CBS";
                                    }

                                    leaf high-prio-only {
                                        type types-qos:burst-percent-or-default-override;
                                        units "percent";
                                        description "High priority burst size";
                                    }

                                    leaf hs-class-weight {
                                        type types-qos:hs-class-weight-override;
                                        description "Class-weight override for expanded egress HS queues";
                                    }

                                    leaf hs-wrr-weight {
                                        type types-qos:hs-wrr-weight-override;
                                        description "Maximum rate for expanded egress HS queues";
                                    }

                                    leaf mbs {
                                        type types-qos:queue-burst-size-override;
                                        units "bytes";
                                        description "MBS";
                                    }

                                    leaf stat-mode {
                                        type enumeration {
                                            enum v4-v6                          { value 0; }
                                        }
                                        description "Stat mode for the policer";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container hs-wred-queue {
                                        description "Enter the hs-wred-queue context";

                                        leaf policy {
                                            type leafref {
                                                path "../../../../../../../../../qos/slope-policy/slope-policy-name";
                                            }
                                            description "Name of the slope-policy override applied to HS queue";
                                        }

                                    } // container hs-wred-queue

                                    container rate {
                                        description "Enter the rate context";

                                        leaf pir {
                                            type types-qos:queue-pir-rate-override;
                                            units "kilobps";
                                            description "PIR for the queue";
                                        }

                                        leaf cir {
                                            type types-qos:queue-cir-rate-override;
                                            units "kilobps";
                                            description "CIR for the queue";
                                        }

                                    } // container rate

                                } // list queue

                            } // container overrides

                        } // container sap-egress

                        container scheduler-policy {
                            description "Enter the scheduler-policy context";

                            leaf policy-name {
                                type leafref {
                                    path "../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type leafref {
                                            path "../../../../../../../../qos/scheduler-policy[scheduler-policy-name=current()/../../../policy-name]/tier/scheduler/scheduler-name";
                                        }
                                        description "Scheduler policy name";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:scheduler-pir-rate;
                                            units "kilobps";
                                            default "max";
                                            description "Administrative PIR";
                                        }

                                        leaf cir {
                                            type types-qos:scheduler-cir-rate;
                                            units "kilobps";
                                            default "sum";
                                            description "Administrative CIR";
                                        }

                                    } // container rate

                                } // list scheduler

                            } // container overrides

                        } // container scheduler-policy

                    } // container qos

                    container report-rate {
                        description "Enter the report-rate context";

                        choice report-rate {
                            case agg-rate {

                                leaf agg-rate {
                                    type empty;
                                    description "Report the aggregate rate";
                                }

                            }
                            case scheduler {

                                leaf scheduler {
                                    type types-sros:named-item;
                                    description "Report the rate of the specified scheduler";
                                }

                            }
                            case pppoe-actual-rate {

                                leaf pppoe-actual-rate {
                                    type empty;
                                    description "Report rate from the DSL characteristics PPPoE tags";
                                }

                            }
                            case policer {

                                leaf policer {
                                    type uint32 {
                                        range "1..63";
                                    }
                                    description "Report the rate of the specified policer";
                                }

                            }
                            case rfc5515-actual-rate {

                                leaf rfc5515-actual-rate {
                                    type empty;
                                    description "Report the rate as specified in RFC5515";
                                }

                            }
                        }
                    } // container report-rate

                } // container egress

                container session-limits {
                    description "Enter the session-limits context";

                    leaf ipoe {
                        type types-submgt:sla-profile-host-limit-with-zero;
                        description "Maximum number of IPoE sessions";
                    }

                    leaf overall {
                        type types-submgt:sla-profile-host-limit-with-zero;
                        description "Maximum number of subscriber sessions";
                    }

                    container pppoe {
                        description "Enter the pppoe context";

                        leaf local {
                            type types-submgt:sla-profile-host-limit-with-zero;
                            description "Maximum number of PPPoE local terminated sessions";
                        }

                        leaf lac {
                            type types-submgt:sla-profile-host-limit-with-zero;
                            description "Maximum number of PPPoE L2TP LAC sessions";
                        }

                        leaf overall {
                            type types-submgt:sla-profile-host-limit-with-zero;
                            description "Maximum number of PPPoE sessions";
                        }

                    } // container pppoe

                    container l2tp {
                        description "Enter the l2tp context";

                        leaf lns {
                            type types-submgt:sla-profile-host-limit-with-zero;
                            description "Maximum number of L2TP LNS sessions";
                        }

                        leaf lts {
                            type types-submgt:sla-profile-host-limit-with-zero;
                            description "Maximum number of L2TP LTS sessions";
                        }

                        leaf overall {
                            type types-submgt:sla-profile-host-limit-with-zero;
                            description "Maximum number of L2TP sessions";
                        }

                    } // container l2tp

                } // container session-limits

                container host-limits {
                    description "Enter the host-limits context";

                    leaf lac-overall {
                        type types-submgt:sla-profile-host-limit-with-zero;
                        description "Maximum number of L2TP LAC hosts";
                    }

                    leaf overall {
                        type types-submgt:sla-profile-host-limit;
                        description "Maximum number of subscriber hosts";
                    }

                    leaf remove-oldest {
                        type boolean;
                        default "false";
                        description "Remove oldest";
                    }

                    container ipv4 {
                        description "Enter the ipv4 context";

                        leaf arp {
                            type types-submgt:sla-profile-host-limit-with-zero;
                            description "Maximum number of IPv4 ARP hosts";
                        }

                        leaf dhcp {
                            type types-submgt:sla-profile-host-limit-with-zero;
                            description "Maximum number of IPv4 DHCP hosts";
                        }

                        leaf overall {
                            type types-submgt:sla-profile-host-limit-with-zero;
                            description "Maximum number of IPv4 hosts";
                        }

                        leaf ppp {
                            type types-submgt:sla-profile-host-limit-with-zero;
                            description "Maximum number of IPv4 PPP hosts";
                        }

                    } // container ipv4

                    container ipv6 {
                        description "Enter the ipv6 context";

                        leaf overall {
                            type types-submgt:sla-profile-host-limit-with-zero;
                            description "Maximum number of IPv6 hosts";
                        }

                        leaf pd-ipoe-dhcp {
                            type types-submgt:sla-profile-host-limit-with-zero;
                            description "Maximum number of IPv6 IPoE DHCP PD hosts";
                        }

                        leaf pd-overall {
                            type types-submgt:sla-profile-host-limit-with-zero;
                            description "Maximum number of IPv6 DHCP PD hosts";
                        }

                        leaf pd-ppp-dhcp {
                            type types-submgt:sla-profile-host-limit-with-zero;
                            description "Maximum number of IPv6 PPPoE DHCP PD hosts";
                        }

                        leaf wan-ipoe-dhcp {
                            type types-submgt:sla-profile-host-limit-with-zero;
                            description "Maximum number of IPv6 IPoE DHCP WAN hosts";
                        }

                        leaf wan-ipoe-slaac {
                            type types-submgt:sla-profile-host-limit-with-zero;
                            description "Maximum number of IPv6 IPoE SLAAC WAN hosts";
                        }

                        leaf wan-overall {
                            type types-submgt:sla-profile-host-limit-with-zero;
                            description "Maximum number of IPv6 WAN hosts";
                        }

                        leaf wan-ppp-dhcp {
                            type types-submgt:sla-profile-host-limit-with-zero;
                            description "Maximum number IPv6 PPPoE DHCP WAN hosts";
                        }

                        leaf wan-ppp-slaac {
                            type types-submgt:sla-profile-host-limit-with-zero;
                            description "Maximum number of IPv6 PPPoE SLAAC WAN hosts";
                        }

                    } // container ipv6

                } // container host-limits

                container ingress {
                    description "Enter the ingress context";

                    leaf ip-filter {
                        type leafref {
                            path "../../../../filter/ip-filter/filter-name";
                        }
                        description "IPv4 filter policy name";
                    }

                    leaf ipv6-filter {
                        type leafref {
                            path "../../../../filter/ipv6-filter/filter-name";
                        }
                        description "IPv6 filter policy name";
                    }

                    container qos {
                        description "Enter the qos context";

                        container sap-ingress {
                            description "Enter the sap-ingress context";

                            leaf policy-name {
                                type leafref {
                                    path "../../../../../../qos/sap-ingress/sap-ingress-policy-name";
                                }
                                description "SAP-ingress QoS policy";
                            }

                            leaf queuing-type {
                                type types-qos:ingress-queuing-type;
                                default "service";
                                description "Queuing type";
                            }

                            container overrides {
                                description "Enter the overrides context";

                                list policer {
                                    key "id";
                                    description "Enter the policer list instance";

                                    leaf id {
                                        type leafref {
                                            path "../../../../../../../../qos/sap-ingress[sap-ingress-policy-name=current()/../../../policy-name]/policer/policer-id";
                                        }
                                        description "Policer ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:ingress-per-packet-offset-override;
                                        description "Packet byte offset";
                                    }

                                    leaf stat-mode {
                                        type types-submgt:subscriber-ingress-policer-stat-mode-type;
                                        description "Stat mode for the policer";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:policer-pir-rate-override;
                                            units "kilobps";
                                            description "PIR override for the packet bye offset";
                                        }

                                        leaf cir {
                                            type types-qos:policer-cir-rate-override;
                                            units "kilobps";
                                            description "CIR override for the packet byte offset";
                                        }

                                    } // container rate

                                } // list policer

                                list queue {
                                    key "id";
                                    description "Enter the queue list instance";

                                    leaf id {
                                        type leafref {
                                            path "../../../../../../../../qos/sap-ingress[sap-ingress-policy-name=current()/../../../policy-name]/queue/queue-id";
                                        }
                                        description "Queue ID";
                                    }

                                    leaf cbs {
                                        type types-qos:burst-size-override;
                                        units "kilobytes";
                                        description "CBS";
                                    }

                                    leaf high-prio-only {
                                        type types-qos:burst-percent-or-default-override;
                                        units "percent";
                                        description "High priority burst size";
                                    }

                                    leaf mbs {
                                        type types-qos:queue-burst-size-override;
                                        units "bytes";
                                        description "MBS";
                                    }

                                    leaf stat-mode {
                                        type enumeration {
                                            enum v4-v6                          { value 0; }
                                        }
                                        description "Stat mode for the policer";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container rate {
                                        description "Enter the rate context";

                                        leaf pir {
                                            type types-qos:queue-pir-rate-override;
                                            units "kilobps";
                                            description "PIR for the queue";
                                        }

                                        leaf cir {
                                            type types-qos:queue-cir-rate-override;
                                            units "kilobps";
                                            description "CIR for the queue";
                                        }

                                    } // container rate

                                } // list queue

                            } // container overrides

                        } // container sap-ingress

                    } // container qos

                    container report-rate {
                        description "Enter the report-rate context";

                        choice report-rate {
                            case agg-rate {

                                leaf agg-rate {
                                    type empty;
                                    description "Report the aggregate rate";
                                }

                            }
                            case scheduler {

                                leaf scheduler {
                                    type types-sros:named-item;
                                    description "Report the rate of the specified scheduler";
                                }

                            }
                            case pppoe-actual-rate {

                                leaf pppoe-actual-rate {
                                    type empty;
                                    description "Report rate from the DSL characteristics PPPoE tags";
                                }

                            }
                            case policer {

                                leaf policer {
                                    type uint32 {
                                        range "1..63";
                                    }
                                    description "Report the rate of the specified policer";
                                }

                            }
                            case rfc5515-actual-rate {

                                leaf rfc5515-actual-rate {
                                    type empty;
                                    description "Report the rate as specified in RFC5515";
                                }

                            }
                        }
                    } // container report-rate

                } // container ingress


                container one-time-http-redirection {
                    description "Enter the one-time-http-redirection context";

                    leaf ip-filter {
                        type leafref {
                            path "../../../../filter/ip-filter/filter-name";
                        }
                        description "IPv4 filter policy name";
                    }

                } // container one-time-http-redirection

                container pfcp-mappings {
                    description "Enter the pfcp-mappings context";

                    leaf second-level-flow-rate {
                        type enumeration {
                            enum ignore                         { value 1; }
                            enum shape                          { value 2; }
                        }
                        default "shape";
                        description "Enforcement for two-level rate limiting downstream";
                    }

                    container session-qer {
                        description "Enter the session-qer context";

                        container uplink {
                            description "Enter the uplink context";

                            choice uplink {
                                case queue {

                                    leaf queue {
                                        type types-qos:ingress-queue-id;
                                        description "Queue target of MBR/GBR override";
                                    }

                                }
                                case policer {

                                    leaf policer {
                                        type types-qos:ingress-policer-id;
                                        description "Policer target of MBR/GBR override";
                                    }

                                }
                                case scheduler {

                                    leaf scheduler {
                                        type types-sros:named-item;
                                        description "Scheduler target of MBR/GBR override";
                                    }

                                }
                                case arbiter {

                                    leaf arbiter {
                                        type types-sros:named-item;
                                        description "Arbiter target of MBR/GBR override";
                                    }

                                }
                            }
                        } // container uplink

                        container downlink {
                            description "Enter the downlink context";

                            choice downlink {
                                case aggregate-rate {

                                    leaf aggregate-rate {
                                        type empty;
                                        description "Map MBR/GBR to a rate override for the aggregate rate";
                                    }

                                }
                                case queue {

                                    leaf queue {
                                        type types-qos:egress-queue-id;
                                        description "Queue target of MBR/GBR override";
                                    }

                                }
                                case policer {

                                    leaf policer {
                                        type types-qos:egress-policer-id;
                                        description "Policer target of MBR/GBR override";
                                    }

                                }
                                case scheduler {

                                    leaf scheduler {
                                        type types-sros:named-item;
                                        description "Scheduler target of MBR/GBR override";
                                    }

                                }
                                case arbiter {

                                    leaf arbiter {
                                        type types-sros:named-item;
                                        description "Arbiter target of MBR/GBR override";
                                    }

                                }
                            }
                        } // container downlink

                    } // container session-qer

                } // container pfcp-mappings

            } // list sla-profile

            list sub-ident-policy {
                key "name";
                description "Enter the sub-ident-policy list instance";

                leaf name {
                    type types-sros:external-named-item;
                    description "Subscriber identification policy name";
                }

                leaf description {
                    type types-sros:description;
                    description "Text description";
                }

                leaf strings-from-option {
                    type uint32 {
                        range "1..254";
                    }
                    description "IPOE option to get the identification strings";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container primary {
                    description "Enter the primary context";

                    leaf script-url {
                        type types-sros:url;
                        description "Identification script URL";
                    }

                    leaf admin-state {
                        type types-sros:admin-state;
                        default "disable";
                        description "Administrative state of script execution";
                    }

                } // container primary

                container secondary {
                    description "Enter the secondary context";

                    leaf script-url {
                        type types-sros:url;
                        description "Identification script URL";
                    }

                    leaf admin-state {
                        type types-sros:admin-state;
                        default "disable";
                        description "Administrative state of script execution";
                    }

                } // container secondary

                container tertiary {
                    description "Enter the tertiary context";

                    leaf script-url {
                        type types-sros:url;
                        description "Identification script URL";
                    }

                    leaf admin-state {
                        type types-sros:admin-state;
                        default "disable";
                        description "Administrative state of script execution";
                    }

                } // container tertiary

                container app-profile-map {
                    description "Enter the app-profile-map context";

                    leaf use-direct-map-as-default {
                        type boolean;
                        default "false";
                        description "Enable direct mapping of application profile as default";
                    }

                    list entry {
                        key "app-profile-string";
                        description "Enter the entry list instance";

                        leaf app-profile-string {
                            type string {
                                length "1..16";
                            }
                            description "Application profile string";
                        }

                        leaf app-profile {
                            type leafref {
                                path "../../../../../application-assurance/group/partition/policy/app-profile/app-profile-name";
                            }
                            mandatory true;
                            description "Application profile name";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list entry

                } // container app-profile-map

                container sla-profile-map {
                    description "Enter the sla-profile-map context";

                    leaf use-direct-map-as-default {
                        type boolean;
                        default "false";
                        description "Allow direct mapping of SLA profile as default";
                    }

                    list entry {
                        key "sla-profile-string";
                        description "Enter the entry list instance";

                        leaf sla-profile-string {
                            type string {
                                length "1..32";
                            }
                            description "SLA profile string";
                        }

                        leaf sla-profile {
                            type leafref {
                                path "../../../../sla-profile/name";
                            }
                            mandatory true;
                            description "SLA profile";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list entry

                } // container sla-profile-map

                container sub-profile-map {
                    description "Enter the sub-profile-map context";

                    leaf use-direct-map-as-default {
                        type boolean;
                        default "false";
                        description "Allow direct mapping of subscriber profile as default";
                    }

                    list entry {
                        key "sub-profile-string";
                        description "Enter the entry list instance";

                        leaf sub-profile-string {
                            type string {
                                length "1..32";
                            }
                            description "Subscriber identification string";
                        }

                        leaf sub-profile {
                            type leafref {
                                path "../../../../sub-profile/name";
                            }
                            mandatory true;
                            description "Subscriber profile";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list entry

                } // container sub-profile-map

            } // list sub-ident-policy

            list ppp-policy {
                key "name";
                max-elements 256;
                description "Enter the ppp-policy list instance";

                leaf name {
                    type types-sros:named-item;
                    description "PPP policy name";
                }

                leaf description {
                    type types-sros:description;
                    description "Text description";
                }

                leaf default-pap-password {
                    type types-sros:encrypted-leaf {
                        length "1..115";
                    }
                    description "Default PAP password when no password from PPP client";
                }

                leaf default-user-name {
                    type types-sros:string-not-all-spaces {
                        length "1..253";
                    }
                    description "Default username used for authentication";
                }

                leaf cookies {
                    type boolean;
                    default "true";
                    description "Enable/disable the use of AC-Cookie tags.";
                }

                leaf force-ppp-mtu-gt-1492 {
                    type boolean;
                    default "false";
                    description "Enable PPPoE MRU negotiations greater than 1492 bytes";
                }

                leaf ipcp-subnet-negotiation {
                    type boolean;
                    default "false";
                    description "Allow IPCP subnet negotiation for PPPoE hosts";
                }

                leaf lcp-ignore-magic-numbers {
                    type boolean;
                    default "false";
                    description "Ignore LCP peer magic number mismatch";
                }

                leaf max-sessions-per-mac {
                    type uint32 {
                        range "1..8191";
                    }
                    default "1";
                    description "Maximum number of sessions per MAC address";
                }

                leaf allow-same-circuit-id-for-dhcp {
                    type boolean;
                    default "false";
                    description "Enable support for IPv4 address allocation on a SAP";
                }

                leaf pado-ac-name {
                    type types-sros:string-not-all-spaces {
                        length "1..128";
                    }
                    description "Access Concentrator name used in PPPoE PADO message";
                }

                leaf pado-delay {
                    type uint32 {
                        range "1..30";
                    }
                    units "deciseconds";
                    description "Delay timeout before sending a PADO";
                }

                leaf ppp-authentication {
                    type enumeration {
                        enum pap                            { value 1; }
                        enum chap                           { value 2; }
                        enum pref-chap                      { value 3; }
                        enum pref-pap                       { value 4; }
                    }
                    default "pref-chap";
                    description "PPP authentication protocol to negotiate";
                }

                leaf ppp-initial-delay {
                    type boolean;
                    default "false";
                    description "Select delay timeout before starting the PPP stack";
                }

                leaf ppp-mtu {
                    type uint32 {
                        range "512..9212";
                    }
                    description "Maximum PPP MTU size";
                }

                leaf re-establish-session {
                    type boolean;
                    default "false";
                    description "Reconnect and override an existing session";
                }

                leaf reject-unconfigured-ncp {
                    type boolean;
                    default "false";
                    description "Enable/disable reject unconfigured NCP.";
                }

                leaf reply-on-padt {
                    type boolean;
                    default "false";
                    description "Enable/disable reply on PADT packets.";
                }

                leaf session-timeout {
                    type types-sros:time-duration {
                        range "1..31104000";
                    }
                    units "seconds";
                    description "Session timeout interval";
                }

                leaf sid-allocation {
                    type enumeration {
                        enum sequential                     { value 0; }
                        enum random                         { value 1; }
                    }
                    default "sequential";
                    description "PPPoE session ID allocation method";
                }

                leaf unique-sid {
                    type enumeration {
                        enum per-sap                        { value 1; }
                        enum per-sap-mac                    { value 2; }
                        enum per-msap                       { value 3; }
                    }
                    default "per-sap-mac";
                    description "Mode in which a unique session ID is allocated";
                }

                leaf ncp-renegotiation {
                    type enumeration {
                        enum ignore                         { value 1; }
                        enum terminate-session              { value 2; }
                    }
                    default "terminate-session";
                    description "Behavior for subsequent NCP renegotiation messages";
                }

                leaf lcp-ignore-identifier {
                    type boolean;
                    default "false";
                    description "Ignore identifier values in the LCP Echo Reply";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container max-sessions-per-cid {
                    presence "Enable the max-sessions-per-cid context";
                    description "Enable the max-sessions-per-cid context";

                    leaf limit {
                        type uint32 {
                            range "1..8190";
                        }
                        mandatory true;
                        description "Maximum sessions per Agent Circuit ID and per SAP";
                    }

                    leaf allow-sessions-without-cid {
                        type boolean;
                        default "false";
                        description "Allow PPPoE sessions without an Agent Circuit ID";
                    }

                } // container max-sessions-per-cid

                container keepalive {
                    description "Enter the keepalive context";

                    leaf interval {
                        type types-sros:time-duration {
                            range "4..300";
                        }
                        units "seconds";
                        default "30";
                        description "PPP keepalive interval";
                    }

                    leaf hold-up-multiplier {
                        type uint32 {
                            range "1..5";
                        }
                        default "3";
                        description "PPP keepalive multiplier";
                    }

                } // container keepalive

                container ppp-chap-challenge-length {
                    description "Enter the ppp-chap-challenge-length context";

                    leaf min {
                        type uint32 {
                            range "8..64";
                        }
                        default "32";
                        description "Minimum length for the PPP CHAP challenge";
                    }

                    leaf max {
                        type uint32 {
                            range "8..64";
                        }
                        default "64";
                        description "Maximum length for the PPP CHAP challenge";
                    }

                } // container ppp-chap-challenge-length

                container mlppp {
                    description "Enter the mlppp context";

                    leaf accept-mrru {
                        type boolean;
                        default "false";
                        description "Accept multilink MRRU LCP option";
                    }

                    leaf short-sequence-numbers {
                        type boolean;
                        default "false";
                        description "Request a peer to send short sequence numbers";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container endpoint {
                        description "Enter the endpoint context";

                        choice endpoint {
                            case ip {

                                leaf ip {
                                    type types-ppp:mlppp-ip-endpoint;
                                    description "Endpoint ID as an IP address";
                                }

                            }
                            case mac {

                                leaf mac {
                                    type types-ppp:mlppp-mac-endpoint;
                                    description "Endpoint ID as a MAC address";
                                }

                            }
                        }
                    } // container endpoint

                } // container mlppp

                container ppp-options {
                    description "Enter the ppp-options context";

                    list custom-option {
                        key "protocol option-number";
                        description "Enter the custom-option list instance";

                        leaf protocol {
                            type enumeration {
                                enum lcp                            { value 1; }
                                enum ipcp                           { value 2; }
                                enum ipv6cp                         { value 3; }
                            }
                            description "Protocol for the custom PPP option";
                        }

                        leaf option-number {
                            type uint32 {
                                range "0..255";
                            }
                            description "PPP option number";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice option-data {
                            mandatory true;
                            case address {

                                leaf address {
                                    type types-sros:ipv4-address;
                                    description "IP address of the custom PPP option";
                                }

                            }
                            case hex-string {

                                leaf hex-string {
                                    type types-sros:hex-string {
                                        length "1..256";
                                    }
                                    description "Hexadecimal string for the custom PPP option";
                                }

                            }
                            case ascii-string {

                                leaf ascii-string {
                                    type types-sros:string-not-all-spaces {
                                        length "1..127";
                                    }
                                    description "ASCII string for the customer PPP option";
                                }

                            }
                            case empty {

                                leaf empty {
                                    type empty;
                                    description "Configure an empty PPP option.";
                                }

                            }
                        }
                    } // list custom-option

                } // container ppp-options

            } // list ppp-policy

            list pppoe-client-policy {
                key "name";
                max-elements 256;
                description "Enter the pppoe-client-policy list instance";

                leaf name {
                    type types-sros:named-item;
                    description "PPPoE client policy name";
                }

                leaf description {
                    type types-sros:description;
                    description "Text description";
                }

                leaf mru {
                    type uint32 {
                        range "512..9154";
                    }
                    default "1492";
                    description "PPPoE MRU";
                }

                leaf mtu {
                    type uint32 {
                        range "512..9154";
                    }
                    default "1492";
                    description "PPPoE MTU";
                }

                leaf python-policy {
                    type leafref {
                        path "../../../python/python-policy/name";
                    }
                    description "Python policy for all messages to and from PPPoE client";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container keepalive {
                    description "Enter the keepalive context";

                    leaf interval {
                        type types-sros:time-duration {
                            range "10..300";
                        }
                        units "seconds";
                        default "30";
                        description "PPPoE keepalive interval";
                    }

                    leaf hold-up-multiplier {
                        type uint32 {
                            range "1..5";
                        }
                        default "3";
                        description "PPPoE keepalive multiplier";
                    }

                } // container keepalive

                container restart-backoff {
                    description "Enter the restart-backoff context";

                    leaf initial-time {
                        type types-sros:time-duration {
                            range "10..3600";
                        }
                        units "seconds";
                        default "30";
                        description "Initial backoff time";
                    }

                    leaf max-time {
                        type types-sros:time-duration {
                            range "10..3600";
                        }
                        units "seconds";
                        default "600";
                        description "Maximum backoff time";
                    }

                } // container restart-backoff

                container stack {
                    description "Enter the stack context";

                    leaf ipv4 {
                        type boolean;
                        default "true";
                        description "Start IPCP to retrieve an IPv4 address";
                    }

                    leaf ipv6-slaac {
                        type boolean;
                        default "false";
                        description "Start IPv6CP and use SLAAC to retrieve an IPv6 prefix";
                    }

                } // container stack

            } // list pppoe-client-policy

            list radius-accounting-policy {
                key "name";
                max-elements 32;
                description "Enter the radius-accounting-policy list instance";

                leaf name {
                    type types-sros:named-item;
                    description "RADIUS-based accounting policy name";
                }

                leaf description {
                    type types-sros:description;
                    description "Text description";
                }

                leaf acct-tunnel-connection-fmt {
                    type types-sros:ascii-specification {
                        length "1..253";
                    }
                    default "%n";
                    description "String sent in the accounting message";
                }

                leaf delay-start-time {
                    type types-sros:time-duration {
                        range "1..10";
                    }
                    units "seconds";
                    description "Accounting start delay";
                }

                leaf radius-server-policy {
                    type leafref {
                        path "../../../aaa/radius/server-policy/name";
                    }
                    description "Referenced RADIUS server policy";
                }

                leaf session-id-format {
                    type enumeration {
                        enum description                    { value 1; }
                        enum number                         { value 2; }
                    }
                    default "description";
                    description "Format used in accounting session ID attributes";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container triggered-updates {
                    description "Enter the triggered-updates context";

                    choice gtp-mode {
                        default "gtp-mode-change";
                        case gtp-mode-mobility {

                            leaf gtp-mobility {
                                status deprecated;
                                type boolean;
                                default "false";
                                description "Send updates for mobility events";
                            }

                        }
                        case gtp-mode-change {

                            container gtp-change {
                                description "Enter the gtp-change context";

                                leaf service-request {
                                    type boolean;
                                    default "false";
                                    description "Send an IU for service request (reactivation) procedure";
                                }

                                leaf s1-release {
                                    type boolean;
                                    default "false";
                                    description "Send an IU for S1 release (idle) procedure";
                                }

                                leaf uli-change {
                                    type boolean;
                                    default "false";
                                    description "Send an IU when a user location change is detected";
                                }

                                leaf teidc-change {
                                    type boolean;
                                    default "false";
                                    description "Send an IU when GTP-C TEIDs are changed";
                                }

                                leaf teidu-change {
                                    type boolean;
                                    default "false";
                                    description "Send an IU when GTP-U TEIDs are changed";
                                }

                            } // container gtp-change

                        }
                    }
                } // container triggered-updates

                container host-accounting {
                    description "Enter the host-accounting context";

                    leaf admin-state {
                        type types-sros:admin-state;
                        default "disable";
                        description "Administrative state of per-host accounting";
                    }

                    leaf interim-update {
                        type boolean;
                        default "false";
                        description "Allow interim-update accounting messages to be sent";
                    }

                } // container host-accounting

                container queue-instance-accounting {
                    description "Enter the queue-instance-accounting context";

                    leaf admin-state {
                        type types-sros:admin-state;
                        default "enable";
                        description "Administrative state of per-queue instance accounting";
                    }

                    leaf interim-update {
                        type boolean;
                        default "true";
                        description "Send accounting messages for the queue instance";
                    }

                } // container queue-instance-accounting

                container session-accounting {
                    description "Enter the session-accounting context";

                    leaf admin-state {
                        type types-sros:admin-state;
                        default "disable";
                        description "Administrative state of per-session accounting";
                    }

                    leaf interim-update {
                        type boolean;
                        default "false";
                        description "Allow interim-update accounting messages to be sent";
                    }

                    leaf host-update {
                        type boolean;
                        default "false";
                        description "Allow host updates";
                    }

                } // container session-accounting

                container update-interval {
                    description "Enter the update-interval context";

                    leaf interval {
                        type types-sros:time-duration {
                            range "5..259200";
                        }
                        units "minutes";
                        description "Intermediate update interval";
                    }

                    leaf jitter {
                        type union {
                            type enumeration {
                                enum auto                           { value -10; }
                            }
                            type types-sros:time-duration {
                                range "0..3600";
                            }
                        }
                        units "seconds";
                        default "auto";
                        description "Maximum random delay for intermediate update interval";
                    }

                } // container update-interval

                container mcs-interval {
                    description "Enter the mcs-interval context";

                    leaf interval {
                        type union {
                            type enumeration {
                                enum none                           { value 0; }
                                enum use-update-interval            { value 1; }
                            }
                            type types-sros:time-duration {
                                range "5..60";
                            }
                        }
                        units "minutes";
                        description "MCS synchronization interval of usage counters";
                    }

                } // container mcs-interval

                container custom-record {
                    description "Enter the custom-record context";

                    leaf significant-change {
                        type uint32 {
                            range "0..max";
                        }
                        description "Significant change required to generate the record";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list override-counter {
                        status obsolete;
                        key "id";
                        description "Enter the override-counter list instance";

                        leaf id {
                            status obsolete;
                            type uint32 {
                                range "1..8";
                            }
                            description "Override counter ID";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        container e-counters {
                            status obsolete;
                            description "Enter the e-counters context";

                            leaf in-profile-octets-discarded-count {
                                status obsolete;
                                type boolean;
                                default "false";
                                description "Include the in-profile octets discarded count";
                            }

                            leaf in-profile-octets-forwarded-count {
                                status obsolete;
                                type boolean;
                                default "false";
                                description "Include the in-profile octets forwarded count";
                            }

                            leaf in-profile-packets-discarded-count {
                                status obsolete;
                                type boolean;
                                default "false";
                                description "Include the in-profile packets discarded count";
                            }

                            leaf in-profile-packets-forwarded-count {
                                status obsolete;
                                type boolean;
                                default "false";
                                description "Include the in-profile packets forwarded count";
                            }

                            leaf out-profile-octets-discarded-count {
                                status obsolete;
                                type boolean;
                                default "false";
                                description "Include the out-profile octets discarded count";
                            }

                            leaf out-profile-octets-forwarded-count {
                                status obsolete;
                                type boolean;
                                default "false";
                                description "Include the out-of-profile octets forwarded count";
                            }

                            leaf out-profile-packets-discarded-count {
                                status obsolete;
                                type boolean;
                                default "false";
                                description "Include the out-profile packets discarded count";
                            }

                            leaf out-profile-packets-forwarded-count {
                                status obsolete;
                                type boolean;
                                default "false";
                                description "Include the out-of-profile packets forwarded count";
                            }

                        } // container e-counters

                        container i-counters {
                            status obsolete;
                            description "Enter the i-counters context";

                            leaf all-octets-offered-count {
                                status obsolete;
                                type boolean;
                                default "false";
                                description "Include the all octets offered count";
                            }

                            leaf all-packets-offered-count {
                                status obsolete;
                                type boolean;
                                default "false";
                                description "Include all packets offered count";
                            }

                            leaf high-octets-discarded-count {
                                status obsolete;
                                type boolean;
                                default "false";
                                description "Include the high octets discarded count";
                            }

                            leaf high-packets-discarded-count {
                                status obsolete;
                                type boolean;
                                default "false";
                                description "Include the high packets discarded count";
                            }

                            leaf in-profile-octets-forwarded-count {
                                status obsolete;
                                type boolean;
                                default "false";
                                description "Include the in-profile octets forwarded count";
                            }

                            leaf in-profile-packets-forwarded-count {
                                status obsolete;
                                type boolean;
                                default "false";
                                description "Include the in-profile packets forwarded count";
                            }

                            leaf low-octets-discarded-count {
                                status obsolete;
                                type boolean;
                                default "false";
                                description "Include the low octets discarded count";
                            }

                            leaf low-packets-discarded-count {
                                status obsolete;
                                type boolean;
                                default "false";
                                description "Include the low packets discarded count";
                            }

                            leaf out-profile-octets-forwarded-count {
                                status obsolete;
                                type boolean;
                                default "false";
                                description "Include the out-of-profile octets forwarded count";
                            }

                            leaf out-profile-packets-forwarded-count {
                                status obsolete;
                                type boolean;
                                default "false";
                                description "Include the out-of-profile packets forwarded count";
                            }

                        } // container i-counters

                    } // list override-counter

                    list queue {
                        key "id";
                        description "Enter the queue list instance";

                        leaf id {
                            type uint32 {
                                range "1..32";
                            }
                            description "Queue ID for which counters are collected in the record";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // list queue

                    container ref-override-counter {
                        status obsolete;
                        description "Enter the ref-override-counter context";

                        choice counter {
                            status obsolete;
                            case id {
                                status obsolete;

                                leaf id {
                                    status obsolete;
                                    type leafref {
                                        path "../../override-counter/id";
                                    }
                                    description "Override counter ID";
                                }

                            }
                            case all {
                                status obsolete;

                                leaf all {
                                    status obsolete;
                                    type empty;
                                    description "Apply significant change for all override counter IDs";
                                }

                            }
                        }
                        container e-counters {
                            status obsolete;
                            description "Enter the e-counters context";

                            leaf in-profile-octets-discarded-count {
                                status obsolete;
                                type boolean;
                                default "false";
                                description "Include the in-profile octets discarded count";
                            }

                            leaf in-profile-octets-forwarded-count {
                                status obsolete;
                                type boolean;
                                default "false";
                                description "Include the in-profile octets forwarded count";
                            }

                            leaf in-profile-packets-discarded-count {
                                status obsolete;
                                type boolean;
                                default "false";
                                description "Include the in-profile packets discarded count";
                            }

                            leaf in-profile-packets-forwarded-count {
                                status obsolete;
                                type boolean;
                                default "false";
                                description "Include the in-profile packets forwarded count";
                            }

                            leaf out-profile-octets-discarded-count {
                                status obsolete;
                                type boolean;
                                default "false";
                                description "Include the out-profile octets discarded count";
                            }

                            leaf out-profile-octets-forwarded-count {
                                status obsolete;
                                type boolean;
                                default "false";
                                description "Include the out-of-profile octets forwarded count";
                            }

                            leaf out-profile-packets-discarded-count {
                                status obsolete;
                                type boolean;
                                default "false";
                                description "Include the out-profile packets discarded count";
                            }

                            leaf out-profile-packets-forwarded-count {
                                status obsolete;
                                type boolean;
                                default "false";
                                description "Include the out-of-profile packets forwarded count";
                            }

                        } // container e-counters

                        container i-counters {
                            status obsolete;
                            description "Enter the i-counters context";

                            leaf all-octets-offered-count {
                                status obsolete;
                                type boolean;
                                default "false";
                                description "Include the all octets offered count";
                            }

                            leaf all-packets-offered-count {
                                status obsolete;
                                type boolean;
                                default "false";
                                description "Include all packets offered count";
                            }

                            leaf high-octets-discarded-count {
                                status obsolete;
                                type boolean;
                                default "false";
                                description "Include the high octets discarded count";
                            }

                            leaf high-packets-discarded-count {
                                status obsolete;
                                type boolean;
                                default "false";
                                description "Include the high packets discarded count";
                            }

                            leaf in-profile-octets-forwarded-count {
                                status obsolete;
                                type boolean;
                                default "false";
                                description "Include the in-profile octets forwarded count";
                            }

                            leaf in-profile-packets-forwarded-count {
                                status obsolete;
                                type boolean;
                                default "false";
                                description "Include the in-profile packets forwarded count";
                            }

                            leaf low-octets-discarded-count {
                                status obsolete;
                                type boolean;
                                default "false";
                                description "Include the low octets discarded count";
                            }

                            leaf low-packets-discarded-count {
                                status obsolete;
                                type boolean;
                                default "false";
                                description "Include the low packets discarded count";
                            }

                            leaf out-profile-octets-forwarded-count {
                                status obsolete;
                                type boolean;
                                default "false";
                                description "Include the out-of-profile octets forwarded count";
                            }

                            leaf out-profile-packets-forwarded-count {
                                status obsolete;
                                type boolean;
                                default "false";
                                description "Include the out-of-profile packets forwarded count";
                            }

                        } // container i-counters

                    } // container ref-override-counter

                    container ref-queue {
                        description "Enter the ref-queue context";

                        choice queue {
                            case id {

                                leaf id {
                                    type leafref {
                                        path "../../queue/id";
                                    }
                                    description "Queue ID";
                                }

                            }
                            case all {

                                leaf all {
                                    type empty;
                                    description "Apply significant change to counters for all queues";
                                }

                            }
                        }
                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // container ref-queue

                } // container custom-record

                container include-radius-attribute {
                    description "Enter the include-radius-attribute context";

                    leaf access-loop-options {
                        type boolean;
                        default "false";
                        description "Include access loop information";
                    }

                    leaf acct-authentic {
                        type boolean;
                        default "false";
                        description "Enable/disable include of the acct-authentic attribute.";
                    }

                    leaf acct-delay-time {
                        type boolean;
                        default "false";
                        description "Include the acct-delay-time RADIUS attribute";
                    }

                    leaf acct-triggered-reason {
                        type boolean;
                        default "false";
                        description "Include Alc-Acct-Triggered-Reason attribute";
                    }

                    leaf error-code {
                        type boolean;
                        default "false";
                        description "Include detailed error codes";
                    }

                    leaf all-authorized-session-addresses {
                        type boolean;
                        default "false";
                        description "Include all address/prefix attributes";
                    }

                    leaf apn {
                        type boolean;
                        default "false";
                        description "Enable/disable include of the APN attribute.";
                    }

                    leaf bonding-active-connections {
                        type boolean;
                        default "false";
                        description "Include the RADIUS Alc-Bonding-Active-Connection VSA";
                    }

                    leaf bonding-id {
                        type boolean;
                        default "false";
                        description "Include the Alc-Bonding-Id VSA";
                    }

                    leaf brg-num-active-sessions {
                        type boolean;
                        default "false";
                        description "Include the RADIUS Alc-BRG-Num-Active-Sessions VSA";
                    }

                    leaf called-station-id {
                        type boolean;
                        default "false";
                        description "Include called-station-id attribute";
                    }

                    leaf circuit-id {
                        type boolean;
                        default "false";
                        description "Include circuit-id attribute";
                    }

                    leaf delegated-ipv6-prefix {
                        type boolean;
                        default "false";
                        description "Include delegated-ipv6-prefix attribute";
                    }

                    leaf detailed-acct-attributes {
                        type boolean;
                        default "true";
                        description "Include more detailed accounting attributes";
                    }

                    leaf dhcp-vendor-class-id {
                        type boolean;
                        default "false";
                        description "Include the RADIUS Alc-DHCP-Vendor-Class-Id VSA";
                    }

                    leaf firewall-info {
                        type boolean;
                        default "false";
                        description "Include the Firewall Information VSA in AAA protocols";
                    }

                    leaf framed-interface-id {
                        type boolean;
                        default "false";
                        description "Include framed-interface-id attribute";
                    }

                    leaf framed-ip-address {
                        type boolean;
                        default "false";
                        description "Include framed-ip-address attribute";
                    }

                    leaf framed-ip-netmask {
                        type boolean;
                        default "false";
                        description "Include framed-ip-netmask attribute";
                    }

                    leaf framed-ipv6-prefix {
                        type boolean;
                        default "false";
                        description "Include framed-ipv6-prefix attribute";
                    }

                    leaf framed-ipv6-route {
                        type boolean;
                        default "false";
                        description "Include framed-ipv6-route attribute";
                    }

                    leaf framed-route {
                        type boolean;
                        default "false";
                        description "Include framed-route attribute";
                    }

                    leaf imei {
                        type boolean;
                        default "false";
                        description "Enable/disable include of the IMEI attribute.";
                    }

                    leaf ipv6-address {
                        type boolean;
                        default "false";
                        description "Include the IPv6 address attribute";
                    }

                    leaf lanext-bridge-id {
                        type boolean;
                        default "false";
                        description "Include Alc-Bridge-Id in RADIUS accounting packets";
                    }

                    leaf lanext-device-type {
                        type boolean;
                        default "false";
                        description "Include Alc-HLE-Device-type in accounting packets";
                    }

                    leaf lanext-route-distinguisher {
                        type boolean;
                        default "false";
                        description "Include route distinguisher (Alc-RD) in RADIUS packets";
                    }

                    leaf lanext-route-target {
                        type boolean;
                        default "false";
                        description "Include route target (Alc-RT) in RADIUS packets";
                    }

                    leaf lanext-vni {
                        type boolean;
                        default "false";
                        description "Enable/disable include of the lanext-vni attribute.";
                    }

                    leaf mac-address {
                        type boolean;
                        default "false";
                        description "Include the client MAC address in the RADIUS message";
                    }

                    leaf msisdn {
                        type boolean;
                        default "false";
                        description "Enable/disable include of the MSISDN attribute.";
                    }

                    leaf nas-identifier {
                        type boolean;
                        default "false";
                        description "Enable/disable include of the NAS-Identifier attribute.";
                    }

                    leaf nat-port-range {
                        type boolean;
                        default "false";
                        description "Include NAT port range attribute";
                    }

                    leaf remote-id {
                        type boolean;
                        default "false";
                        description "Include remote-id attribute";
                    }

                    leaf sla-profile {
                        type boolean;
                        default "false";
                        description "Include sla-profile attribute";
                    }

                    leaf spi-sharing-id {
                        type boolean;
                        default "false";
                        description "Include spi-sharing-id attribute";
                    }

                    leaf std-acct-attributes {
                        type boolean;
                        default "false";
                        description "Include standard accounting attributes";
                    }

                    leaf steering-profile {
                        type boolean;
                        default "false";
                        description "Include the RADIUS Alc-Steering-Profile VSA";
                    }

                    leaf sub-profile {
                        type boolean;
                        default "false";
                        description "Include sub-profile attribute";
                    }

                    leaf subscriber-id {
                        type boolean;
                        default "false";
                        description "Include subscriber-id attribute";
                    }

                    leaf tunnel-client-attrs {
                        type boolean;
                        default "false";
                        description "Enable/disable include of tunnel-client attributes.";
                    }

                    leaf tunnel-server-attrs {
                        type boolean;
                        default "false";
                        description "Enable/disable include of tunnel-server attributes.";
                    }

                    leaf user-name {
                        type boolean;
                        default "false";
                        description "Include the user-name attribute";
                    }

                    leaf v6-aggregate-stats {
                        type boolean;
                        default "false";
                        description "Report IPv6 aggregated forwarded octet and packet counters";
                    }

                    leaf wifi-num-attached-ues {
                        type boolean;
                        default "false";
                        description "Include the RADIUS Alc-Num-Attached-UEs VSA";
                    }

                    leaf wifi-rssi {
                        type boolean;
                        default "false";
                        description "Include 802.11 received signal strength indicator";
                    }

                    leaf wifi-ssid-vlan {
                        type boolean;
                        default "false";
                        description "Include per-SSID VLAN ID in the Alc-Wlan-SSID-VLAN VSA";
                    }

                    leaf uli {
                        type boolean;
                        default "false";
                        description "Generate the ULI RADIUS attribute";
                    }

                    leaf bearer-fteid {
                        type boolean;
                        default "false";
                        description "Include bearer-fteid attribute";
                    }

                    leaf xconnect-tunnel-home-address {
                        type boolean;
                        default "false";
                        description "Include the Alc-Xconnect-Tunnel-Home-Ipv6 attribute";
                    }

                    leaf imsi {
                        type boolean;
                        default "false";
                        description "Include the IMSI attribute for FWA sessions";
                    }

                    container calling-station-id {
                        presence "Enable the calling-station-id context";
                        description "Enable the calling-station-id context";

                        leaf type {
                            type enumeration {
                                enum sap-string                     { value 1; }
                                enum mac                            { value 2; }
                                enum sap-id                         { value 3; }
                                enum remote-id                      { value 4; }
                                enum llid                           { value 5; }
                            }
                            default "sap-string";
                            description "Format of the Calling-Station-ID attribute";
                        }

                    } // container calling-station-id

                    container nas-port {
                        presence "Enable the nas-port context";
                        description "Enable the nas-port context";

                        leaf bit-spec {
                            type types-sros:binary-specification {
                                pattern "([01]|(\\*[0123456789]+)?[smpoivc])+";
                            }
                            mandatory true;
                            description "RADIUS NAS-Port attribute";
                        }

                    } // container nas-port

                    container nas-port-id {
                        presence "Enable the nas-port-id context";
                        description "Enable the nas-port-id context";

                        leaf prefix-string {
                            type string {
                                length "1..8";
                            }
                            description "String to be prefixed to the NAS-Port-Id attribute";
                        }

                        leaf suffix {
                            type enumeration {
                                enum circuit-id                     { value 1; }
                                enum remote-id                      { value 2; }
                            }
                            description "String to be suffixed to the NAS-Port-Id attribute";
                        }

                    } // container nas-port-id

                    container nas-port-type {
                        presence "Enable the nas-port-type context";
                        description "Enable the nas-port-type context";

                        leaf type {
                            type union {
                                type enumeration {
                                    enum rfc-aligned                    { value 1000; }
                                }
                                type uint32 {
                                    range "0..255";
                                }
                            }
                            default "rfc-aligned";
                            description "Value for RADIUS NAS-Port-Type attribute";
                        }

                    } // container nas-port-type

                } // container include-radius-attribute

            } // list radius-accounting-policy

            container authentication-origin {
                description "Enter the authentication-origin context";

                container overrides {
                    description "Enter the overrides context";

                    list priority {
                        key "id";
                        description "Enter the priority list instance";

                        leaf id {
                            type uint32 {
                                range "1..4294967295";
                            }
                            description "Authentication origin priority override";
                        }

                        leaf source {
                            type types-submgt:authentication-origin;
                            mandatory true;
                            description "Source of authentication priority";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list priority

                } // container overrides

            } // container authentication-origin

            list radius-authentication-policy {
                key "name";
                max-elements 32;
                description "Enter the radius-authentication-policy list instance";

                leaf name {
                    type types-sros:named-item;
                    description "RADIUS authentication policy name";
                }

                leaf description {
                    type types-sros:description;
                    description "Text description";
                }

                leaf password {
                    type types-sros:encrypted-leaf {
                        length "1..115";
                    }
                    description "RADIUS request password";
                }

                leaf pppoe-access-method {
                    type enumeration {
                        enum none                           { value 1; }
                        enum padi                           { value 2; }
                        enum pap-chap                       { value 3; }
                    }
                    default "padi";
                    description "PPPoE access method";
                }

                leaf radius-server-policy {
                    type leafref {
                        path "../../../aaa/radius/server-policy/name";
                    }
                    description "Referenced RADIUS server policy";
                }

                leaf re-authentication {
                    type boolean;
                    default "false";
                    description "Enable re-authentication on IPOE renewal";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container fallback {
                    description "Enter the fallback context";

                    leaf force-probing {
                        type boolean;
                        default "false";
                        description "Enable force probing";
                    }

                    container action {
                        description "Enter the action context";

                        choice action {
                            case accept {

                                leaf accept {
                                    type empty;
                                    description "Automatically accept all authentication requests";
                                }

                            }
                            case user-db {

                                leaf user-db {
                                    type types-sros:named-item;
                                    description "Local user database used to authenticate to the server";
                                }

                            }
                        }
                    } // container action

                } // container fallback

                container ppp-user-name {
                    description "Enter the ppp-user-name context";

                    leaf domain-operation {
                        type types-submgt:user-name-format-domain-operation;
                        description "Operation to perform on the PAP or CHAP username";
                    }

                    leaf domain-name {
                        type string {
                            length "1..128";
                        }
                        description "Domain name";
                    }

                } // container ppp-user-name

                container send-acct-stop-on-fail {
                    description "Enter the send-acct-stop-on-fail context";

                    leaf on-request-failure {
                        type boolean;
                        default "false";
                        description "Send an accounting stop message for failures";
                    }

                    leaf on-reject {
                        type boolean;
                        default "false";
                        description "Send an accounting stop message for Access-Reject";
                    }

                    leaf on-accept-failure {
                        type boolean;
                        default "false";
                        description "Send an accounting stop message when a failure occurs";
                    }

                } // container send-acct-stop-on-fail

                container user-name {
                    description "Enter the user-name context";

                    leaf format {
                        type enumeration {
                            enum mac                            { value 1; }
                            enum circuit-id                     { value 2; }
                            enum tuple                          { value 3; }
                            enum ascii-converted-circuit-id     { value 4; }
                            enum ascii-converted-tuple          { value 5; }
                            enum dhcp-client-vendor-opts        { value 6; }
                            enum mac-giaddr                     { value 7; }
                            enum ppp-user-name                  { value 8; }
                        }
                        default "mac";
                        description "User name format in the RADIUS message";
                    }

                    leaf mac-format {
                        type types-submgt:mac-specification;
                        default "aa:";
                        description "MAC address format when contacting a RADIUS server";
                    }

                    leaf gtp-format {
                        type enumeration {
                            enum imsi                           { value 1; }
                            enum imsi-apn                       { value 2; }
                            enum msisdn                         { value 3; }
                            enum msisdn-apn                     { value 4; }
                        }
                        default "imsi";
                        description "Username format used for FWA sessions";
                    }

                    leaf domain-operation {
                        type types-submgt:user-name-format-domain-operation;
                        description "Operation to perform on the username";
                    }

                    leaf domain-name {
                        type string {
                            length "1..128";
                        }
                        description "Domain name";
                    }

                } // container user-name

                container include-radius-attribute {
                    description "Enter the include-radius-attribute context";

                    leaf access-loop-options {
                        type boolean;
                        default "false";
                        description "Include access loop information";
                    }

                    leaf apn {
                        type boolean;
                        default "false";
                        description "Enable/disable include of the APN attribute.";
                    }

                    leaf called-station-id {
                        type boolean;
                        default "false";
                        description "Include called-station-id attribute";
                    }

                    leaf circuit-id {
                        type boolean;
                        default "false";
                        description "Include circuit-id attribute";
                    }

                    leaf dhcp-options {
                        type boolean;
                        default "false";
                        description "Generate the DHCP options RADIUS attribute";
                    }

                    leaf dhcp-vendor-class-id {
                        type boolean;
                        default "false";
                        description "Include the RADIUS Alc-DHCP-Vendor-Class-Id VSA";
                    }

                    leaf dhcp6-options {
                        type boolean;
                        default "false";
                        description "Generate the DHCPv6 options RADIUS attribute";
                    }

                    leaf gprs-negotiated-qos-profile {
                        type boolean;
                        default "false";
                        description "Generate GPRS negotiated QoS profile RADIUS attribute";
                    }

                    leaf imei {
                        type boolean;
                        default "false";
                        description "Enable/disable include of the IMEI attribute.";
                    }

                    leaf mac-address {
                        type boolean;
                        default "false";
                        description "Include the client MAC address in the RADIUS message";
                    }

                    leaf msisdn {
                        type boolean;
                        default "false";
                        description "Enable/disable include of the MSISDN attribute.";
                    }

                    leaf nas-identifier {
                        type boolean;
                        default "false";
                        description "Enable/disable include of the NAS-Identifier attribute.";
                    }

                    leaf pppoe-service-name {
                        type boolean;
                        default "false";
                        description "Generate the pppoe-service-name RADIUS attribute";
                    }

                    leaf rat-type {
                        type boolean;
                        default "false";
                        description "Generate the RAT type RADIUS attribute";
                    }

                    leaf remote-id {
                        type boolean;
                        default "false";
                        description "Include remote-id attribute";
                    }

                    leaf sap-session-index {
                        type boolean;
                        default "false";
                        description "Generate the per-SAP unique session index";
                    }

                    leaf tunnel-server-attrs {
                        type boolean;
                        default "false";
                        description "Enable/disable include of tunnel-server attributes.";
                    }

                    leaf uli {
                        type boolean;
                        default "false";
                        description "Generate the ULI RADIUS attribute";
                    }

                    leaf wifi-num-attached-ues {
                        type boolean;
                        default "false";
                        description "Include the RADIUS Alc-Num-Attached-UEs VSA";
                    }

                    leaf wifi-ssid-vlan {
                        type boolean;
                        default "false";
                        description "Include per-SSID VLAN ID in the Alc-Wlan-SSID-VLAN VSA";
                    }

                    leaf xconnect-tunnel-home-address {
                        type boolean;
                        default "false";
                        description "Include the Alc-Xconnect-Tunnel-Home-Ipv6 attribute";
                    }

                    leaf imsi {
                        type boolean;
                        default "false";
                        description "Include the IMSI attribute for FWA sessions";
                    }

                    container acct-session-id {
                        presence "Enable the acct-session-id context";
                        description "Enable the acct-session-id context";

                        leaf type {
                            type enumeration {
                                enum host                           { value 1; }
                                enum session                        { value 2; }
                            }
                            default "host";
                            description "Format of the accounting session ID attribute";
                        }

                    } // container acct-session-id

                    container calling-station-id {
                        presence "Enable the calling-station-id context";
                        description "Enable the calling-station-id context";

                        leaf type {
                            type enumeration {
                                enum sap-string                     { value 1; }
                                enum mac                            { value 2; }
                                enum sap-id                         { value 3; }
                                enum remote-id                      { value 4; }
                                enum llid                           { value 5; }
                            }
                            default "sap-string";
                            description "Format of the Calling-Station-ID attribute";
                        }

                    } // container calling-station-id

                    container nas-port {
                        presence "Enable the nas-port context";
                        description "Enable the nas-port context";

                        leaf bit-spec {
                            type types-sros:binary-specification {
                                pattern "([01]|(\\*[0123456789]+)?[smpoivc])+";
                            }
                            mandatory true;
                            description "RADIUS NAS-Port attribute";
                        }

                    } // container nas-port

                    container nas-port-id {
                        presence "Enable the nas-port-id context";
                        description "Enable the nas-port-id context";

                        leaf prefix-string {
                            type string {
                                length "1..8";
                            }
                            description "String to be prefixed to the NAS-Port-Id attribute";
                        }

                        leaf suffix {
                            type enumeration {
                                enum circuit-id                     { value 1; }
                                enum remote-id                      { value 2; }
                            }
                            description "String to be suffixed to the NAS-Port-Id attribute";
                        }

                    } // container nas-port-id

                    container nas-port-type {
                        presence "Enable the nas-port-type context";
                        description "Enable the nas-port-type context";

                        leaf type {
                            type union {
                                type enumeration {
                                    enum rfc-aligned                    { value 1000; }
                                }
                                type uint32 {
                                    range "0..255";
                                }
                            }
                            default "rfc-aligned";
                            description "Value for RADIUS NAS-Port-Type attribute";
                        }

                    } // container nas-port-type

                } // container include-radius-attribute

            } // list radius-authentication-policy

            container auto-sub-id {
                description "Enter the auto-sub-id context";

                leaf-list ipoe-key {
                    type types-submgt:sub-id-key-ipoe;
                    max-elements 4;
                    ordered-by user;
                    description "Auto-generated subscriber ID key1 for IPoE hosts";
                }

                leaf-list ppp-key {
                    type types-submgt:sub-id-key-ppp;
                    max-elements 5;
                    ordered-by user;
                    description "Auto-generated subscriber identifier key1 for PPP hosts";
                }

                leaf implicit-generation {
                    type boolean;
                    default "true";
                    description "Generate implicitly a subscriber ID when not provided";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container auto-sub-id

            list rip-policy {
                key "name";
                max-elements 255;
                description "Enter the rip-policy list instance";

                leaf name {
                    type types-sros:named-item;
                    description "RIP policy name";
                }

                leaf description {
                    type types-sros:description;
                    description "Text description";
                }

                leaf authentication-key {
                    type types-sros:encrypted-leaf {
                        length "1..51";
                    }
                    description "Authentication key";
                }

                leaf authentication-type {
                    type enumeration {
                        enum password                       { value 2; }
                        enum message-digest                 { value 3; }
                        enum message-digest-20              { value 4; }
                    }
                    description "Authentication type used between RIP neighbors";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list rip-policy

            list host-lockout-policy {
                key "name";
                max-elements 128;
                description "Enter the host-lockout-policy list instance";

                leaf name {
                    type types-sros:named-item;
                    description "Host lockout policy name to associate with the SAP";
                }

                leaf description {
                    type types-sros:description;
                    description "Text description";
                }

                leaf host-key {
                    type enumeration {
                        enum all                            { value 0; }
                        enum mac                            { value 1; }
                    }
                    sros-ext:immutable;
                    default "all";
                    description "Parameters in host identification for lockout on a SAP";
                }

                leaf lockout-reset-time {
                    type types-sros:time-duration {
                        range "1..86400";
                    }
                    units "seconds";
                    default "60";
                    description "Lockout reset time settings";
                }

                leaf max-lockout-hosts {
                    type uint32 {
                        range "1..32000";
                    }
                    default "100";
                    description "Max lockout hosts";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container lockout-time {
                    description "Enter the lockout-time context";

                    leaf min {
                        type types-sros:time-duration {
                            range "1..86400";
                        }
                        units "seconds";
                        default "10";
                        description "Minimum lockout time";
                    }

                    leaf max {
                        type types-sros:time-duration {
                            range "1..86400";
                        }
                        units "seconds";
                        default "3600";
                        description "Maximum lockout time";
                    }

                } // container lockout-time

            } // list host-lockout-policy

            list shcv-policy {
                key "name";
                max-elements 64;
                description "Enter the shcv-policy list instance";

                leaf name {
                    type types-sros:external-named-item;
                    description "SHCV policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container periodic {
                    description "Enter the periodic context";

                    leaf action {
                        type types-submgt:host-connectivity-verify-action;
                        default "alarm";
                        description "Action when periodic connectivity verification fails";
                    }

                    leaf interval {
                        type types-submgt:host-connectivity-verify-interval;
                        default "30";
                        description "Time interval which all known sources are verified";
                    }

                    leaf retry-count {
                        type types-submgt:host-connectivity-verify-retry-count;
                        default "2";
                        description "Number of retransmissions in connectivity verification";
                    }

                    leaf timeout {
                        type types-submgt:host-connectivity-verify-retry-timeout;
                        default "10";
                        description "Timeout before connectivity verification retransmitted";
                    }

                    leaf admin-state {
                        type types-sros:admin-state;
                        default "enable";
                        description "Administrative state of periodic connectivity check";
                    }

                } // container periodic

                container vpls {
                    description "Enter the vpls context";

                    leaf source-ip {
                        type types-sros:ipv4-unicast-address;
                        description "Source IPv4 address for connectivity verification";
                    }

                    leaf source-mac {
                        type yang:mac-address;
                        sros-ext:immutable;
                        description "Source MAC address for connectivity verification";
                    }

                } // container vpls

                container layer-3 {
                    description "Enter the layer-3 context";

                    leaf source-ip-origin {
                        type types-submgt:host-connectivity-verify-source-ip-origin;
                        default "interface";
                        description "Source IP address to be used for SHCV messages";
                    }

                    leaf unnumbered-source-ip {
                        type types-sros:ipv4-unicast-address;
                        description "Source IPv4 address for unnumbered subscriber hosts";
                    }

                } // container layer-3

                container trigger {
                    description "Enter the trigger context";

                    container ip-conflict {
                        description "Enter the ip-conflict context";

                        leaf retry-count {
                            type types-submgt:host-connectivity-verify-retry-count;
                            default "1";
                            description "Number of retransmissions in periodic connectivity test";
                        }

                        leaf timeout {
                            type types-submgt:host-connectivity-verify-retry-timeout;
                            default "1";
                            description "Timeout before a retransmission";
                        }

                        leaf admin-state {
                            type types-sros:admin-state;
                            default "enable";
                            description "Administrative state of the trigger for IP conflict";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container ip-conflict

                    container host-limit-exceeded {
                        description "Enter the host-limit-exceeded context";

                        leaf retry-count {
                            type types-submgt:host-connectivity-verify-retry-count;
                            default "1";
                            description "Number of retransmissions in periodic connectivity test";
                        }

                        leaf timeout {
                            type types-submgt:host-connectivity-verify-retry-timeout;
                            default "1";
                            description "Timeout before a retransmission";
                        }

                        leaf admin-state {
                            type types-sros:admin-state;
                            default "enable";
                            description "Administrative state of trigger for host-limit exceeded";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container host-limit-exceeded

                    container inactivity {
                        description "Enter the inactivity context";

                        leaf retry-count {
                            type types-submgt:host-connectivity-verify-retry-count;
                            default "2";
                            description "Number of retransmissions in periodic connectivity test";
                        }

                        leaf timeout {
                            type types-submgt:host-connectivity-verify-retry-timeout;
                            default "10";
                            description "Timeout before a retransmission";
                        }

                        leaf admin-state {
                            type types-sros:admin-state;
                            default "enable";
                            description "Administrative state of the trigger for inactive hosts";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container inactivity

                    container mobility {
                        description "Enter the mobility context";

                        leaf retry-count {
                            type types-submgt:host-connectivity-verify-retry-count;
                            default "1";
                            description "Number of retransmissions in periodic connectivity test";
                        }

                        leaf timeout {
                            type types-submgt:host-connectivity-verify-retry-timeout;
                            default "1";
                            description "Timeout before a retransmission";
                        }

                        leaf admin-state {
                            type types-sros:admin-state;
                            default "enable";
                            description "Administrative state of trigger for SAP IP/MAC conflict";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container mobility

                    container mac-learning {
                        description "Enter the mac-learning context";

                        leaf retry-count {
                            type types-submgt:host-connectivity-verify-retry-count;
                            default "2";
                            description "Number of retransmissions in periodic connectivity test";
                        }

                        leaf timeout {
                            type types-submgt:host-connectivity-verify-retry-timeout;
                            default "10";
                            description "Timeout before a retransmission";
                        }

                        leaf admin-state {
                            type types-sros:admin-state;
                            default "enable";
                            description "Administrative state of trigger for MAC learning";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container mac-learning

                } // container trigger

            } // list shcv-policy

            list http-redirect-policy {
                key "name";
                max-elements 16;
                description "Enter the http-redirect-policy list instance";

                leaf name {
                    type types-sros:named-item;
                    description "HTTP redirect policy name";
                }

                leaf description {
                    type types-sros:description;
                    description "Text description";
                }

                leaf url {
                    type types-sros:http-redirect-url;
                    description "HTTP URL to which the matching traffic is redirected";
                }

                leaf dst-port {
                    type types-sros:tcp-udp-port-non-zero;
                    default "80";
                    description "Destination port number of the HTTP request to match";
                }

                leaf portal-hold-time {
                    type types-sros:time-duration {
                        range "1..60";
                    }
                    description "Time to hold redirect forwarding resources";
                }

                leaf ignore-app-profile {
                    type boolean;
                    default "false";
                    description "Ignore application profile attribute in the RADIUS Access-Accept message";
                }

                leaf application-assurance {
                    type leafref {
                        path "../../../application-assurance/group/partition/policy/app-profile/app-profile-name";
                    }
                    description "AA application profile used for portal authentication";
                }

                leaf aa-url-parameter {
                    type types-aa:aa-http-url-param;
                    description "AA URL parameter included for HTTP portal redirect";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list forward-entry {
                    key "dst-ip protocol dst-port";
                    description "Add a list entry for forward-entry";

                    leaf dst-ip {
                        type types-sros:ip-prefix;
                        description "Destination address";
                    }

                    leaf protocol {
                        type enumeration {
                            enum tcp                            { value 6; }
                            enum udp                            { value 17; }
                        }
                        description "Destination protocol";
                    }

                    leaf dst-port {
                        type types-sros:tcp-udp-port-non-zero;
                        description "Destination port";
                    }

                } // list forward-entry

            } // list http-redirect-policy

            list msap-policy {
                key "name";
                max-elements 256;
                description "Enter the msap-policy list instance";

                leaf name {
                    type types-sros:named-item;
                    description "Managed SAP policy name";
                }

                leaf description {
                    type types-sros:description;
                    description "Text description";
                }

                leaf dist-cpu-protection {
                    type types-sros:named-item;
                    description "Distributed CPU protection policy";
                }

                leaf lag-link-map-profile {
                    type types-services:link-map-profile-id;
                    description "Map profile for LAG link";
                }

                leaf sticky-msaps {
                    type boolean;
                    default "false";
                    description "Prevent MSAPs from being deleted";
                }

                leaf sticky-msaps-idle-timeout {
                    when "not(../sticky-msaps = 'false')" {
                        description "sticky-msaps must be set";
                    }
                    type uint32 {
                        range "5..604800";
                    }
                    units "seconds";
                    description "Timeout used for sticky MSAPs";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container cpu-protection {
                    description "Enter the cpu-protection context";

                    leaf policy-id {
                        type leafref {
                            path "../../../../system/security/cpu-protection/policy/policy-id";
                        }
                        description "CPM protection policy";
                    }

                    choice monitoring {
                        case mac {

                            leaf mac-monitoring {
                                type empty;
                                description "Apply the per-source rate limit";
                            }

                        }
                        case ip {

                            leaf ip-src-monitoring {
                                type empty;
                                description "Apply the IP source monitoring";
                            }

                        }
                    }
                } // container cpu-protection

                container sub-sla-mgmt {
                    description "Enter the sub-sla-mgmt context";

                    leaf subscriber-limit {
                        type types-submgt:sap-subscriber-limit;
                        default "1";
                        description "Maximum subscribers on this SAP";
                    }

                    leaf sub-ident-policy {
                        type leafref {
                            path "../../../sub-ident-policy/name";
                        }
                        description "Configure subscriber identification policy";
                    }

                    container defaults {
                        description "Enter the defaults context";

                        leaf app-profile {
                            type leafref {
                                path "../../../../../application-assurance/group/partition/policy/app-profile/app-profile-name";
                            }
                            description "Application profile name";
                        }

                        leaf sla-profile {
                            type leafref {
                                path "../../../../sla-profile/name";
                            }
                            description "Default SLA profile";
                        }

                        leaf sub-profile {
                            type leafref {
                                path "../../../../sub-profile/name";
                            }
                            description "Subscriber profile";
                        }

                        container int-dest-id {
                            description "Enter the int-dest-id context";

                            choice int-dest-id-config {
                                case top-q-tag {

                                    leaf top-q-tag {
                                        type empty;
                                        description "Derive string from top most delineating Dot1Q tag";
                                    }

                                }
                                case string {

                                    leaf string {
                                        type types-submgt:int-dest-id;
                                        description "String to be used as the int-dest-id";
                                    }

                                }
                            }
                        } // container int-dest-id

                        container subscriber-id {
                            description "Enter the subscriber-id context";

                            choice subscriber-id-config {
                                case auto-id {

                                    leaf auto-id {
                                        type empty;
                                        description "Autogenerated sub-id as default sub-id";
                                    }

                                }
                                case sap-id {

                                    leaf sap-id {
                                        type empty;
                                        description "SAP-id as default sub-id";
                                    }

                                }
                                case string {

                                    leaf string {
                                        type types-submgt:subscriber-id;
                                        description "String to be used as default sub-id";
                                    }

                                }
                            }
                        } // container subscriber-id

                    } // container defaults

                    container single-sub-parameters {
                        description "Enter the single-sub-parameters context";

                        leaf profiled-traffic-only {
                            type boolean;
                            default "false";
                            description "Enable/disable profiled-traffic-only.";
                        }

                        container non-sub-traffic-profiles {
                            presence "Enable the non-sub-traffic-profiles context";
                            description "Enable the non-sub-traffic-profiles context";

                            leaf sub-profile {
                                type leafref {
                                    path "../../../../../sub-profile/name";
                                }
                                mandatory true;
                                description "Subscriber profile";
                            }

                            leaf sla-profile {
                                type leafref {
                                    path "../../../../../sla-profile/name";
                                }
                                mandatory true;
                                description "SLA profile name";
                            }

                            leaf subscriber-id {
                                type types-submgt:subscriber-id;
                                description "Subscriber identification string";
                            }

                            leaf app-profile {
                                type leafref {
                                    path "../../../../../../application-assurance/group/partition/policy/app-profile/app-profile-name";
                                }
                                description "Application profile name";
                            }

                        } // container non-sub-traffic-profiles

                    } // container single-sub-parameters

                } // container sub-sla-mgmt

                container igmp-host-tracking {
                    description "Enter the igmp-host-tracking context";

                    leaf expiry-time {
                        type types-sros:time-duration {
                            range "1..65535";
                        }
                        units "seconds";
                        description "Time that the system continues to track inactive hosts";
                    }

                    leaf import-policy {
                        type leafref {
                            path "../../../../policy-options/policy-statement/name";
                        }
                        description "Import policy that filters IGMP packets";
                    }

                    leaf maximum-number-groups {
                        type uint32 {
                            range "1..16000";
                        }
                        description "Maximum number of multicast groups to be tracked";
                    }

                    leaf maximum-number-group-sources {
                        type uint32 {
                            range "1..32000";
                        }
                        description "Maximum number of multicast groups to track per group";
                    }

                    leaf maximum-number-sources {
                        type uint32 {
                            range "1..1000";
                        }
                        description "Maximum number of multicast sources to be tracked";
                    }

                } // container igmp-host-tracking

                container vpls-only-sap-parameters {
                    description "Enter the vpls-only-sap-parameters context";

                    leaf arp-reply-agent {
                        type types-services:arp-reply-agent;
                        description "Enable arp-reply-agent function";
                    }

                    leaf mac-da-hashing {
                        type boolean;
                        default "false";
                        description "Include hashing on MAC DA ISO subscriber ID";
                    }

                    leaf split-horizon-group {
                        type types-sros:named-item;
                        description "Name of the split horizon group for the MSAP";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container arp-host {
                        description "Enter the arp-host context";

                        leaf host-limit {
                            type types-submgt:sap-host-limit;
                            default "1";
                            description "Maximum number of ARP hosts";
                        }

                        leaf min-auth-interval {
                            type types-sros:time-duration {
                                range "1..6000";
                            }
                            units "minutes";
                            default "15";
                            description "Minimum authentication interval";
                        }

                    } // container arp-host

                    container egress {
                        description "Enter the egress context";

                        container qos {
                            description "Enter the qos context";

                            leaf policy-name {
                                type leafref {
                                    path "../../../../../../qos/sap-egress/sap-egress-policy-name";
                                }
                                description "QoS policy ID or name to associate with the MSAPs";
                            }

                        } // container qos

                    } // container egress

                    container ingress {
                        description "Enter the ingress context";

                        container qos {
                            description "Enter the qos context";

                            leaf policy-name {
                                type leafref {
                                    path "../../../../../../qos/sap-ingress/sap-ingress-policy-name";
                                }
                                description "QoS policy ID or name to associate with the MSAPs";
                            }

                            leaf queuing-type {
                                type enumeration {
                                    enum multipoint-shared              { value 1; }
                                    enum service                        { value 2; }
                                }
                                default "multipoint-shared";
                                description "Queuing type";
                            }

                        } // container qos

                    } // container ingress

                    container dhcp {
                        description "Enter the dhcp context";

                        leaf lease-populate {
                            type types-submgt:sap-lease-state-limit;
                            default "1";
                            description "Maximum number of DHCPv4 leases per managed SAP";
                        }

                        container proxy-server {
                            description "Enter the proxy-server context";

                            leaf admin-state {
                                type types-sros:admin-state;
                                default "disable";
                                description "Administrative state of the DHCP proxy server";
                            }

                            leaf emulated-server {
                                type types-sros:ipv4-unicast-address;
                                description "IP address used as DHCP server address in SAP context";
                            }

                            container lease-time {
                                description "Enter the lease-time context";

                                leaf value {
                                    type types-sros:time-duration {
                                        range "300..315446399";
                                    }
                                    units "seconds";
                                    description "DHCP lease time";
                                }

                                leaf radius-override {
                                    type boolean;
                                    default "false";
                                    description "Use lease time information provided by RADIUS server";
                                }

                            } // container lease-time

                        } // container proxy-server

                        container option-82 {
                            description "Enter the option-82 context";

                            leaf action {
                                type enumeration {
                                    enum replace                        { value 1; }
                                    enum drop                           { value 2; }
                                    enum keep                           { value 3; }
                                }
                                default "keep";
                                description "DHCP relay forwarding policy action";
                            }

                            leaf circuit-id {
                                type enumeration {
                                    enum none                           { value 0; }
                                    enum ascii-tuple                    { value 1; }
                                    enum vlan-ascii-tuple               { value 2; }
                                }
                                default "ascii-tuple";
                                description "Circuit ID suboption of the IPOE relay";
                            }

                            container remote-id {
                                description "Enter the remote-id context";

                                choice remote-id {
                                    case mac {

                                        leaf mac {
                                            type empty;
                                            description "MAC address of the remote end encoded in the sub-option";
                                        }

                                    }
                                    case string {

                                        leaf string {
                                            type types-sros:named-item;
                                            description "String to encode in the suboption";
                                        }

                                    }
                                }
                            } // container remote-id

                            container vendor-specific-option {
                                description "Enter the vendor-specific-option context";

                                leaf client-mac-address {
                                    type boolean;
                                    default "false";
                                    description "Send MAC address in Nokia vendor-specific sub-option";
                                }

                                leaf sap-id {
                                    type boolean;
                                    default "false";
                                    description "Send SAP ID in the Nokia vendor-specific sub-option";
                                }

                                leaf service-id {
                                    type boolean;
                                    default "false";
                                    description "Send service ID in the Nokia vendor-specific sub-option";
                                }

                                leaf string {
                                    type types-sros:string-not-all-spaces {
                                        length "1..32";
                                    }
                                    description "String in the sub-option of the DHCP relay packet";
                                }

                                leaf system-id {
                                    type boolean;
                                    default "false";
                                    description "Send system ID in the Nokia vendor-specific sub-option";
                                }

                            } // container vendor-specific-option

                        } // container option-82

                    } // container dhcp

                    container igmp-snooping {
                        description "Enter the igmp-snooping context";

                        leaf fast-leave {
                            type boolean;
                            default "false";
                            description "Allow IGMP fast leave processing";
                        }

                        leaf query-last-member-interval {
                            type types-sros:time-duration {
                                range "1..50";
                            }
                            units "deciseconds";
                            default "10";
                            description "Time between group-specific query messages";
                        }

                        leaf import-policy {
                            type leafref {
                                path "../../../../../policy-options/policy-statement/name";
                            }
                            description "Import policy that filters IGMP packets";
                        }

                        leaf maximum-number-groups {
                            type union {
                                type enumeration {
                                    enum unlimited                      { value 0; }
                                }
                                type uint32 {
                                    range "1..16000";
                                }
                            }
                            default "unlimited";
                            description "Maximum number of multicast groups";
                        }

                        leaf query-interval {
                            type types-sros:time-duration {
                                range "2..1024";
                            }
                            units "seconds";
                            default "125";
                            description "Time between two consecutive host-query messages";
                        }

                        leaf query-response-interval {
                            type types-sros:time-duration {
                                range "1..1023";
                            }
                            units "seconds";
                            default "10";
                            description "Time to wait for a response to the host-query messages";
                        }

                        leaf robust-count {
                            type uint32 {
                                range "2..7";
                            }
                            default "2";
                            description "Number of retries after expected message loss";
                        }

                        leaf send-queries {
                            type boolean;
                            default "false";
                            description "Generate IGMP general queries";
                        }

                        leaf version {
                            type types-igmp:igmp-version;
                            default "3";
                            description "IGMP version";
                        }

                        container mcac {
                            description "Enter the mcac context";

                            leaf interface-policy {
                                type leafref {
                                    path "../../../../../../mcac/interface-policy/policy-name";
                                }
                                description "MCAC interface policy name";
                            }

                            leaf policy {
                                type leafref {
                                    path "../../../../../../mcac/policy/policy-name";
                                }
                                description "Multicast CAC policy name";
                            }

                            container bandwidth {
                                description "Enter the bandwidth context";

                                leaf total {
                                    type types-mcast-cac:bandwidth-limit;
                                    description "Maximum allowed bandwidth";
                                }

                                leaf mandatory {
                                    type types-mcast-cac:bandwidth-limit;
                                    description "Pre-reserved bandwidth for all mandatory channels";
                                }

                            } // container bandwidth

                            container mc-constraints {
                                description "Enter the mc-constraints context";

                                leaf use-lag-port-weight {
                                    type boolean;
                                    default "false";
                                    description "Use LAG port weight to calculate MCAC constraints";
                                }

                                list level {
                                    key "level-id";
                                    description "Enter the level list instance";

                                    leaf level-id {
                                        type types-mcast-cac:constraints-level;
                                        description "Bandwidth level ID for an MCAC constraint";
                                    }

                                    leaf bandwidth {
                                        type types-mcast-cac:bandwidth;
                                        default "1";
                                        description "Bandwidth available for this level";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                } // list level

                                list number-down {
                                    key "number-lag-port-down";
                                    description "Enter the number-down list instance";

                                    leaf number-lag-port-down {
                                        type uint32 {
                                            range "1..64";
                                        }
                                        description "Number of lag ports down";
                                    }

                                    leaf level {
                                        type types-mcast-cac:constraints-level;
                                        mandatory true;
                                        description "Level to be associated with this number of lag ports that are down";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                } // list number-down

                            } // container mc-constraints

                        } // container mcac

                        container mvr {
                            description "Enter the mvr context";

                            leaf from-vpls {
                                type leafref {
                                    path "../../../../../../service/vpls/service-name";
                                }
                                description "MVR VPLS from which the multicast channels are taken";
                            }

                        } // container mvr

                    } // container igmp-snooping

                } // container vpls-only-sap-parameters

                container ies-vprn-only-sap-parameters {
                    description "Enter the ies-vprn-only-sap-parameters context";

                    leaf anti-spoof {
                        type types-services:anti-spoof-option-ip-mac;
                        default "source-ip-and-mac-addr";
                        description "Anti-spoof filtering for the MSAP";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container egress {
                        description "Enter the egress context";

                        container qos {
                            description "Enter the qos context";

                            leaf policy-name {
                                type leafref {
                                    path "../../../../../../qos/sap-egress/sap-egress-policy-name";
                                }
                                description "QoS policy ID or name to associate with the MSAPs";
                            }

                        } // container qos

                    } // container egress

                    container ingress {
                        description "Enter the ingress context";

                        container qos {
                            description "Enter the qos context";

                            leaf policy-name {
                                type leafref {
                                    path "../../../../../../qos/sap-ingress/sap-ingress-policy-name";
                                }
                                description "QoS policy ID or name to associate with the MSAPs";
                            }

                            leaf queuing-type {
                                type enumeration {
                                    enum shared                         { value 1; }
                                    enum service                        { value 2; }
                                }
                                default "shared";
                                description "Queuing type";
                            }

                        } // container qos

                    } // container ingress

                } // container ies-vprn-only-sap-parameters

            } // list msap-policy

            list category-map {
                key "category-map-name";
                max-elements 255;
                description "Enter the category-map list instance";

                leaf category-map-name {
                    type types-sros:named-item;
                    description "Category map name";
                }

                leaf description {
                    type types-sros:description;
                    description "Text description";
                }

                leaf credit-type {
                    type enumeration {
                        enum volume                         { value 1; }
                        enum time                           { value 2; }
                    }
                    default "volume";
                    description "Credit type";
                }

                leaf credit-exhaust-threshold {
                    type uint32 {
                        range "50..100";
                    }
                    units "percent";
                    default "100";
                    description "Percentage for credit exhaust threshold";
                }

                leaf activity-threshold {
                    type types-submgt:activity-threshold;
                    description "Threshold to determine whether an activity is ongoing";
                }

                leaf gx-session-level-usage {
                    type boolean;
                    default "false";
                    description "Allow Gx session level Usage Monitoring";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list category {
                    key "category-name";
                    max-elements 16;
                    description "Enter the category list instance";

                    leaf category-name {
                        type types-sros:named-item;
                        description "Category name";
                    }

                    leaf description {
                        type types-sros:description;
                        description "Text description";
                    }

                    leaf rating-group {
                        type int64 {
                            range "0..4294967295";
                        }
                        description "Rating group for this category";
                    }

                    leaf credit-type-override {
                        type enumeration {
                            enum volume                         { value 1; }
                            enum time                           { value 2; }
                        }
                        description "Credit type override in category map";
                    }

                    leaf out-of-credit-action-override {
                        type enumeration {
                            enum continue                       { value 1; }
                            enum disconnect-host                { value 2; }
                            enum block-category                 { value 3; }
                            enum change-service-level           { value 4; }
                        }
                        description "Out of credit action that is overridden in category map";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container default-credit {
                        description "Enter the default-credit context";

                        choice default-credit {
                            case time {

                                leaf time {
                                    type types-sros:time-duration {
                                        range "1..4294967295";
                                    }
                                    units "seconds";
                                    description "Default time credit";
                                }

                            }
                            case volume {

                                container volume {
                                    presence "Enable the volume context";
                                    description "Enable the volume context";

                                    leaf value {
                                        type uint32 {
                                            range "1..4294967295";
                                        }
                                        mandatory true;
                                        description "Default volume credit";
                                    }

                                    leaf unit {
                                        type enumeration {
                                            enum bytes                          { value 0; }
                                            enum kilobytes                      { value 1; }
                                            enum megabytes                      { value 2; }
                                            enum gigabytes                      { value 3; }
                                        }
                                        default "bytes";
                                        description "Unit for the default volume credit";
                                    }

                                } // container volume

                            }
                        }
                    } // container default-credit

                    container exhausted-credit-service-level {
                        description "Enter the exhausted-credit-service-level context";

                        leaf pir {
                            type types-qos:pir-rate-override;
                            description "PIR";
                        }

                        container ingress {
                            description "Enter the ingress context";

                            container ip-filter {
                                description "Enter the ip-filter context";

                                list entry {
                                    key "id";
                                    max-elements 10;
                                    description "Enter the entry list instance";

                                    leaf id {
                                        type types-filter:limited-entry-id;
                                        description "IP filter entry ID";
                                    }

                                    leaf description {
                                        type types-sros:description;
                                        description "Text description";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container match {
                                        description "Enter the match context";

                                        leaf protocol {
                                            type types-sros:match-ip-protocol;
                                            description "IPv4 protocol to match";
                                        }

                                        leaf multiple-option {
                                            type boolean;
                                            description "Match the multiple option";
                                        }

                                        leaf option-present {
                                            type boolean;
                                            description "Match the present option";
                                        }

                                        leaf dst-ip {
                                            type types-sros:ipv4-address-and-mask;
                                            description "Destination IP address and mask to match";
                                        }

                                        leaf dscp {
                                            type types-qos:dscp-name;
                                            description "DSCP to match";
                                        }

                                        leaf fragment {
                                            type enumeration {
                                                enum false                          { value 2; }
                                                enum true                           { value 3; }
                                            }
                                            description "Fragmentation to match";
                                        }

                                        container icmp {
                                            description "Enter the icmp context";

                                            leaf code {
                                                type types-filter:ipv4-match-icmp-codes;
                                                description "ICMP code to match";
                                            }

                                            leaf type {
                                                type types-filter:ipv4-match-icmp-types;
                                                description "ICMP type to match";
                                            }

                                        } // container icmp

                                        container ip-option {
                                            description "Enter the ip-option context";

                                            leaf type {
                                                type types-filter:filter-match-ip-option;
                                                default "0";
                                                description "First IP option value for the IP header";
                                            }

                                            leaf mask {
                                                type types-filter:filter-match-ip-option;
                                                default "0";
                                                description "IP option mask";
                                            }

                                        } // container ip-option

                                        container tcp-flags {
                                            description "Enter the tcp-flags context";

                                            leaf ack {
                                                type boolean;
                                                description "Check for ACK bit";
                                            }

                                            leaf syn {
                                                type boolean;
                                                description "Check for SYN bit";
                                            }

                                        } // container tcp-flags

                                        container src-port {
                                            description "Enter the src-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container src-port

                                        container dst-port {
                                            description "Enter the dst-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container dst-port

                                    } // container match

                                    container action {
                                        description "Enter the action context";

                                        choice type {
                                            default "drop";
                                            description "Action type for the filter entry";
                                            case drop {

                                                leaf drop {
                                                    type empty;
                                                    description "Packets matching the filter entry are dropped";
                                                }

                                            }
                                            case forward {

                                                leaf forward {
                                                    type empty;
                                                    description "Packets matching the filter entry are forwarded";
                                                }

                                            }
                                            case http-redirect {

                                                container http-redirect {
                                                    presence "Enable the http-redirect context";
                                                    description "Enable the http-redirect context";

                                                    leaf url {
                                                        type types-sros:http-redirect-url;
                                                        mandatory true;
                                                        description "URL that is used to redirect the packets";
                                                    }

                                                    leaf allow-override {
                                                        type boolean;
                                                        default "false";
                                                        description "Allow URL to be overridden by RADIUS/Diameter";
                                                    }

                                                } // container http-redirect

                                            }
                                        }
                                    } // container action

                                } // list entry

                            } // container ip-filter

                            container ipv6-filter {
                                description "Enter the ipv6-filter context";

                                list entry {
                                    key "id";
                                    max-elements 10;
                                    description "Enter the entry list instance";

                                    leaf id {
                                        type types-filter:limited-entry-id;
                                        description "IP filter entry ID";
                                    }

                                    leaf description {
                                        type types-sros:description;
                                        description "Text description";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container match {
                                        description "Enter the match context";

                                        leaf next-header {
                                            type types-sros:match-ip-protocol;
                                            description "IP protocol to match";
                                        }

                                        leaf dst-ip {
                                            type types-sros:ipv6-address-and-mask;
                                            default "0::0 0::0";
                                            description "Destination IP address and mask to match";
                                        }

                                        leaf dscp {
                                            type types-qos:dscp-name;
                                            description "DSCP to match";
                                        }

                                        container icmp {
                                            description "Enter the icmp context";

                                            leaf code {
                                                type types-filter:ipv4-match-icmp-codes;
                                                description "ICMP code to match";
                                            }

                                            leaf type {
                                                type types-filter:ipv4-match-icmp-types;
                                                description "ICMP type to match";
                                            }

                                        } // container icmp

                                        container tcp-flags {
                                            description "Enter the tcp-flags context";

                                            leaf ack {
                                                type boolean;
                                                description "Check for ACK bit";
                                            }

                                            leaf syn {
                                                type boolean;
                                                description "Check for SYN bit";
                                            }

                                        } // container tcp-flags

                                        container src-port {
                                            description "Enter the src-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container src-port

                                        container dst-port {
                                            description "Enter the dst-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container dst-port

                                    } // container match

                                    container action {
                                        description "Enter the action context";

                                        choice type {
                                            default "drop";
                                            description "Action type for the filter entry";
                                            case drop {

                                                leaf drop {
                                                    type empty;
                                                    description "Packets matching the filter entry are dropped";
                                                }

                                            }
                                            case forward {

                                                leaf forward {
                                                    type empty;
                                                    description "Packets matching the filter entry are forwarded";
                                                }

                                            }
                                        }
                                    } // container action

                                } // list entry

                            } // container ipv6-filter

                        } // container ingress

                        container egress {
                            description "Enter the egress context";

                            container ip-filter {
                                description "Enter the ip-filter context";

                                list entry {
                                    key "id";
                                    max-elements 10;
                                    description "Enter the entry list instance";

                                    leaf id {
                                        type types-filter:limited-entry-id;
                                        description "IP filter entry ID";
                                    }

                                    leaf description {
                                        type types-sros:description;
                                        description "Text description";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container match {
                                        description "Enter the match context";

                                        leaf protocol {
                                            type types-sros:match-ip-protocol;
                                            description "IPv4 protocol to match";
                                        }

                                        leaf multiple-option {
                                            type boolean;
                                            description "Match the multiple option";
                                        }

                                        leaf option-present {
                                            type boolean;
                                            description "Match the present option";
                                        }

                                        leaf src-ip {
                                            type types-sros:ipv4-address-and-mask;
                                            description "Source IP address and mask to match";
                                        }

                                        leaf dscp {
                                            type types-qos:dscp-name;
                                            description "DSCP to match";
                                        }

                                        leaf fragment {
                                            type enumeration {
                                                enum false                          { value 2; }
                                                enum true                           { value 3; }
                                            }
                                            description "Fragmentation to match";
                                        }

                                        container icmp {
                                            description "Enter the icmp context";

                                            leaf code {
                                                type types-filter:ipv4-match-icmp-codes;
                                                description "ICMP code to match";
                                            }

                                            leaf type {
                                                type types-filter:ipv4-match-icmp-types;
                                                description "ICMP type to match";
                                            }

                                        } // container icmp

                                        container ip-option {
                                            description "Enter the ip-option context";

                                            leaf type {
                                                type types-filter:filter-match-ip-option;
                                                default "0";
                                                description "First IP option value for the IP header";
                                            }

                                            leaf mask {
                                                type types-filter:filter-match-ip-option;
                                                default "0";
                                                description "IP option mask";
                                            }

                                        } // container ip-option

                                        container tcp-flags {
                                            description "Enter the tcp-flags context";

                                            leaf ack {
                                                type boolean;
                                                description "Check for ACK bit";
                                            }

                                            leaf syn {
                                                type boolean;
                                                description "Check for SYN bit";
                                            }

                                        } // container tcp-flags

                                        container src-port {
                                            description "Enter the src-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container src-port

                                        container dst-port {
                                            description "Enter the dst-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container dst-port

                                    } // container match

                                    container action {
                                        description "Enter the action context";

                                        choice type {
                                            default "drop";
                                            description "Action type for the filter entry";
                                            case drop {

                                                leaf drop {
                                                    type empty;
                                                    description "Packets matching the filter entry are dropped";
                                                }

                                            }
                                            case forward {

                                                leaf forward {
                                                    type empty;
                                                    description "Packets matching the filter entry are forwarded";
                                                }

                                            }
                                            case http-redirect {

                                                container http-redirect {
                                                    presence "Enable the http-redirect context";
                                                    description "Enable the http-redirect context";

                                                    leaf url {
                                                        type types-sros:http-redirect-url;
                                                        mandatory true;
                                                        description "URL that is used to redirect the packets";
                                                    }

                                                    leaf allow-override {
                                                        type boolean;
                                                        default "false";
                                                        description "Allow URL to be overridden by RADIUS/Diameter";
                                                    }

                                                } // container http-redirect

                                            }
                                        }
                                    } // container action

                                } // list entry

                            } // container ip-filter

                            container ipv6-filter {
                                description "Enter the ipv6-filter context";

                                list entry {
                                    key "id";
                                    max-elements 10;
                                    description "Enter the entry list instance";

                                    leaf id {
                                        type types-filter:limited-entry-id;
                                        description "IP filter entry ID";
                                    }

                                    leaf description {
                                        type types-sros:description;
                                        description "Text description";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container match {
                                        description "Enter the match context";

                                        leaf next-header {
                                            type types-sros:match-ip-protocol;
                                            description "IP protocol to match";
                                        }

                                        leaf src-ip {
                                            type types-sros:ipv6-address-and-mask;
                                            default "0::0 0::0";
                                            description "Source IP address and mask as the match condition";
                                        }

                                        leaf dscp {
                                            type types-qos:dscp-name;
                                            description "DSCP to match";
                                        }

                                        container icmp {
                                            description "Enter the icmp context";

                                            leaf code {
                                                type types-filter:ipv4-match-icmp-codes;
                                                description "ICMP code to match";
                                            }

                                            leaf type {
                                                type types-filter:ipv4-match-icmp-types;
                                                description "ICMP type to match";
                                            }

                                        } // container icmp

                                        container tcp-flags {
                                            description "Enter the tcp-flags context";

                                            leaf ack {
                                                type boolean;
                                                description "Check for ACK bit";
                                            }

                                            leaf syn {
                                                type boolean;
                                                description "Check for SYN bit";
                                            }

                                        } // container tcp-flags

                                        container src-port {
                                            description "Enter the src-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container src-port

                                        container dst-port {
                                            description "Enter the dst-port context";

                                            choice port {
                                                case eq {

                                                    leaf eq {
                                                        type uint16 {
                                                            range "0..65535";
                                                        }
                                                        description "Port equal";
                                                    }

                                                }
                                                case lt {

                                                    leaf lt {
                                                        type uint16 {
                                                            range "1..65535";
                                                        }
                                                        description "Port less than";
                                                    }

                                                }
                                                case gt {

                                                    leaf gt {
                                                        type uint16 {
                                                            range "0..65534";
                                                        }
                                                        description "Port greater than";
                                                    }

                                                }
                                                case range {

                                                    container range {
                                                        presence "Enable the range context";
                                                        description "Enable the range context";

                                                        leaf start {
                                                            type uint16 {
                                                                range "0..65535";
                                                            }
                                                            mandatory true;
                                                            description "Lower bound of the port range to match";
                                                        }

                                                        leaf end {
                                                            type uint16 {
                                                                range "0..65535";
                                                            }
                                                            mandatory true;
                                                            description "Upper bound of the port range to match";
                                                        }

                                                    } // container range

                                                }
                                            }
                                        } // container dst-port

                                    } // container match

                                    container action {
                                        description "Enter the action context";

                                        choice type {
                                            default "drop";
                                            description "Action type for the filter entry";
                                            case drop {

                                                leaf drop {
                                                    type empty;
                                                    description "Packets matching the filter entry are dropped";
                                                }

                                            }
                                            case forward {

                                                leaf forward {
                                                    type empty;
                                                    description "Packets matching the filter entry are forwarded";
                                                }

                                            }
                                        }
                                    } // container action

                                } // list entry

                            } // container ipv6-filter

                        } // container egress

                    } // container exhausted-credit-service-level


                    container ingress {
                        description "Enter the ingress context";

                        leaf-list queue {
                            type int8 {
                                range "1..32";
                            }
                            max-elements 32;
                            description "Ingress queues used in this category";
                        }

                        leaf-list policer {
                            type int8 {
                                range "1..63";
                            }
                            max-elements 63;
                            description "Ingress policers used in this category";
                        }

                    } // container ingress

                    container egress {
                        description "Enter the egress context";

                        leaf-list queue {
                            type int8 {
                                range "1..8";
                            }
                            max-elements 8;
                            description "Egress queues for this category";
                        }

                        leaf-list policer {
                            type int8 {
                                range "1..63";
                            }
                            max-elements 63;
                            description "Egress policers for this category";
                        }

                    } // container egress

                } // list category

            } // list category-map

            list credit-control-policy {
                key "name";
                max-elements 255;
                description "Enter the credit-control-policy list instance";

                leaf name {
                    type types-sros:named-item;
                    description "Credit control policy name";
                }

                leaf description {
                    type types-sros:description;
                    description "Text description";
                }

                leaf default-category-map {
                    type leafref {
                        path "../../category-map/category-map-name";
                    }
                    description "Default category map for this policy";
                }

                leaf out-of-credit-action {
                    type enumeration {
                        enum continue                       { value 1; }
                        enum disconnect-host                { value 2; }
                        enum block-category                 { value 3; }
                        enum change-service-level           { value 4; }
                    }
                    default "continue";
                    description "Action when out of credit is reached";
                }

                leaf error-handling-action {
                    type enumeration {
                        enum continue                       { value 1; }
                        enum block                          { value 2; }
                    }
                    default "continue";
                    description "Error handling action for the policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container server {
                    description "Enter the server context";

                    choice server {
                        default "radius";
                        case radius {

                            leaf radius {
                                type empty;
                                description "Use RADIUS servers in the authentication policy";
                            }

                        }
                        case diameter {

                            leaf diameter {
                                type leafref {
                                    path "../../../diameter-gy-policy/name";
                                }
                                description "Diameter policy that specifies Diameter peers to use";
                            }

                        }
                    }
                } // container server

            } // list credit-control-policy

            list router-advertisement-policy {
                key "name";
                max-elements 16;
                description "Enter the router-advertisement-policy list instance";

                leaf name {
                    type types-sros:external-named-item;
                    description "Router advertisement policy name";
                }

                leaf max-advertisement-interval {
                    type types-sros:time-duration {
                        range "900..1800";
                    }
                    units "seconds";
                    default "1800";
                    description "Maximum advertisement interval";
                }

                leaf min-advertisement-interval {
                    type types-sros:time-duration {
                        range "900..1350";
                    }
                    units "seconds";
                    default "900";
                    description "Minimum advertisement interval";
                }

                leaf force-mcast {
                    type enumeration {
                        enum ip                             { value 1; }
                        enum ip-mac                         { value 2; }
                    }
                    description "Protocol with forced multicast";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container options {
                    description "Enter the options context";

                    leaf current-hop-limit {
                        type uint32 {
                            range "0..255";
                        }
                        default "64";
                        description "Hop limit to be advertised";
                    }

                    leaf managed-configuration {
                        type boolean;
                        default "false";
                        description "Managed address configuration flag";
                    }

                    leaf mtu {
                        type union {
                            type uint32 {
                                range "1280..9212";
                            }
                            type enumeration {
                                enum not-included                   { value 0; }
                            }
                        }
                        units "bytes";
                        default "not-included";
                        description "Advertised MTU value";
                    }

                    leaf other-stateful-configuration {
                        type boolean;
                        default "false";
                        description "Other stateful configuration flag";
                    }

                    leaf reachable-time {
                        type types-sros:time-duration {
                            range "0..3600000";
                        }
                        units "milliseconds";
                        default "0";
                        description "Reachable time for advertisements";
                    }

                    leaf retransmit-timer {
                        type uint32 {
                            range "0..1800000";
                        }
                        units "seconds";
                        default "0";
                        description "Retransmit time in router advertisements from interface";
                    }

                    leaf router-lifetime {
                        type union {
                            type types-sros:time-duration {
                                range "2700..9000";
                            }
                            type enumeration {
                                enum no-default-router              { value 0; }
                            }
                        }
                        units "seconds";
                        default "4500";
                        description "Router lifetime";
                    }

                    container dns {
                        description "Enter the dns context";

                        leaf include-rdnss {
                            type boolean;
                            default "false";
                            description "Include the RDNSS server option 25";
                        }

                        leaf rdnss-lifetime {
                            type union {
                                type types-sros:time-duration {
                                    range "900..3600";
                                }
                                type enumeration {
                                    enum infinite                       { value -1; }
                                }
                            }
                            units "seconds";
                            default "3600";
                            description "Maximum time for the RDNSS address to remain valid";
                        }

                    } // container dns

                } // container options

                container prefix-options {
                    description "Enter the prefix-options context";

                    container stateful {
                        description "Enter the stateful context";

                        leaf auto-lifetimes {
                            type boolean;
                            default "false";
                            description "Use automatic lifetimes for stateful prefixes";
                        }

                        leaf on-link {
                            type boolean;
                            default "true";
                            description "Assign the prefix to an interface on the specified link";
                        }

                        leaf preferred-lifetime {
                            type types-submgt:router-advertisement-prefix-options-lifetime;
                            units "seconds";
                            default "3600";
                            description "Time for a prefix to remain preferred";
                        }

                        leaf valid-lifetime {
                            type types-submgt:router-advertisement-prefix-options-lifetime;
                            units "seconds";
                            default "86400";
                            description "Time for a prefix to remain valid";
                        }

                    } // container stateful

                    container stateless {
                        description "Enter the stateless context";

                        leaf on-link {
                            type boolean;
                            default "true";
                            description "Assign the prefix to an interface on the specified link";
                        }

                        leaf preferred-lifetime {
                            type types-submgt:router-advertisement-prefix-options-lifetime;
                            units "seconds";
                            default "3600";
                            description "Time for a prefix to remain preferred";
                        }

                        leaf valid-lifetime {
                            type types-submgt:router-advertisement-prefix-options-lifetime;
                            units "seconds";
                            default "86400";
                            description "Time for a prefix to remain valid";
                        }

                    } // container stateless

                } // container prefix-options

            } // list router-advertisement-policy

            list bgp-peering-policy {
                key "name";
                max-elements 255;
                description "Enter the bgp-peering-policy list instance";

                leaf name {
                    type types-sros:named-item;
                    description "BGP peer policy name";
                }

                leaf description {
                    type types-sros:description;
                    description "Text description";
                }

                leaf advertise-inactive {
                    type boolean;
                    description "Advertise inactive BGP routes to other BGP peers";
                }

                leaf aggregator-id-zero {
                    type boolean;
                    description "Add router ID to BGP aggregator path attribute";
                }

                leaf as-override {
                    type boolean;
                    description "Replace the peer ASN with the local ASN in AS Path";
                }

                leaf authentication-keychain {
                    type leafref {
                        path "../../../system/security/keychains/keychain/keychain-name";
                    }
                    description "Keychain name used for the TCP session";
                }

                leaf authentication-key {
                    type types-sros:encrypted-leaf {
                        length "1..370";
                    }
                    description "BGP authentication key for all peers";
                }

                leaf bfd-liveness {
                    type boolean;
                    default "false";
                    description "Enable BFD";
                }

                leaf cluster {
                    type types-sros:ipv4-address;
                    description "Cluster ID for route reflector server";
                }

                leaf connect-retry {
                    type int32 {
                        range "1..65535";
                    }
                    units "seconds";
                    description "BGP connect retry timer value";
                }

                leaf damping {
                    type boolean;
                    description "Use BGP route damping for learned routes";
                }

                leaf client-reflect {
                    type boolean;
                    description "Enable client reflection of routes to all client peers";
                }

                leaf fast-external-failover {
                    type boolean;
                    description "Enable/disable BGP fast external failover.";
                }

                leaf hold-time {
                    type int32 {
                        range "0|3..65535";
                    }
                    units "seconds";
                    description "BGP hold time before closing connection";
                }

                leaf keepalive {
                    type int32 {
                        range "0..21845";
                    }
                    units "seconds";
                    description "BGP keepalive timer";
                }

                leaf local-address {
                    type types-sros:ip-unicast-address;
                    description "Local IP address used when communicating with BGP peers";
                }

                leaf local-preference {
                    type int64 {
                        range "0..4294967295";
                    }
                    description "Local preference for incoming routes if not specified";
                }

                leaf loop-detect {
                    type types-bgp:loop-detect;
                    description "Strategy for loop detection in the AS path";
                }

                leaf med-out {
                    type union {
                        type uint32;
                        type enumeration {
                            enum igp-cost                       { value -1; }
                        }
                    }
                    description "Multi-Exit Discriminator (MED) advertising";
                }

                leaf min-route-advertisement {
                    type int16 {
                        range "1..255";
                    }
                    units "seconds";
                    description "Minimum interval for prefix to be advertised to a peer";
                }

                leaf multihop {
                    type uint32 {
                        range "1..255";
                    }
                    description "TTL value entered in IP header of packets sent to peer";
                }

                leaf next-hop-self {
                    type boolean;
                    description "Set net hop path attribute to self when advertising";
                }

                leaf passive {
                    type boolean;
                    description "Wait passively for BGP peer to connect";
                }

                leaf peer-as {
                    type uint32 {
                        range "1..4294967295";
                    }
                    description "AS number for remote peer";
                }

                leaf preference {
                    type uint32 {
                        range "1..255";
                    }
                    description "Route preference for routes learned via configured peer";
                }

                leaf prefix-limit {
                    status obsolete;
                    type uint32 {
                        range "1..4294967295";
                    }
                    description "Maximum number of routes that can be learned from peer";
                }

                leaf ttl-security {
                    type int32 {
                        range "1..255";
                    }
                    description "Minimum TTL value for incoming BGP packet";
                }

                leaf type {
                    type types-bgp:peer-type;
                    description "Peer type";
                }

                leaf asn-4-byte {
                    type boolean;
                    description "Enable the use of 4-byte ASNs";
                }

                leaf-list import {
                    type leafref {
                        path "../../../policy-options/policy-statement/name";
                    }
                    max-elements 15;
                    ordered-by user;
                    description "Import route policies to control advertised routes";
                }

                leaf-list export {
                    type leafref {
                        path "../../../policy-options/policy-statement/name";
                    }
                    max-elements 15;
                    ordered-by user;
                    description "Export route policies to control advertised routes";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container family {
                    description "Enter the family context";

                    leaf ipv4 {
                        type boolean;
                        default "false";
                        description "Advertise MP-BGP support for the IPv4 address family";
                    }

                    leaf ipv6 {
                        type boolean;
                        default "false";
                        description "Advertise MP-BGP support for the IPv6 address family";
                    }

                } // container family

                container send-communities {
                    description "Enter the send-communities context";

                    leaf standard {
                        type boolean;
                        description "Send standard communities that existed before VPRNs";
                    }

                    leaf extended {
                        type boolean;
                        description "Send communities which includes VRF target handling";
                    }

                } // container send-communities

                container local-as {
                    description "Enter the local-as context";

                    leaf as-number {
                        type uint32 {
                            range "1..4294967295";
                        }
                        description "AS number to be advertised to peer";
                    }

                    leaf private {
                        type boolean;
                        default "false";
                        description "Hide local AS number in paths learned from peering";
                    }

                } // container local-as

                container remove-private {
                    presence "Enable the remove-private context";
                    description "Enable the remove-private context";

                    leaf limited {
                        type boolean;
                        default "false";
                        description "Remove private AS numbers up to first public ASN encountered";
                    }

                } // container remove-private

                list prefix-limits {
                    key "family";
                    description "Enter the prefix-limits list instance";

                    leaf family {
                        type enumeration {
                            enum ipv4                           { value 1; }
                            enum ipv6                           { value 2; }
                        }
                        description "Address family to which the limit applies";
                    }

                    leaf maximum {
                        type uint32 {
                            range "1..4294967295";
                        }
                        mandatory true;
                        description "Maximum number of routes to be learned from a peer";
                    }

                    leaf log-only {
                        type boolean;
                        default "false";
                        description "Send warning message at threshold instead of take-down";
                    }

                    leaf threshold {
                        type uint32 {
                            range "1..100";
                        }
                        default "90";
                        description "Percentage threshold that triggers a warning message";
                    }

                    leaf idle-timeout {
                        type int32 {
                            range "1..1024";
                        }
                        description "Time BGP peering remains idle before reconnecting";
                    }

                    leaf post-import {
                        type boolean;
                        default "false";
                        description "Apply limit only to routes accepted by import policies";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list prefix-limits

            } // list bgp-peering-policy

            container svlan-statistics {
                description "Enter the svlan-statistics context";

                leaf admin-state {
                    type types-sros:admin-state;
                    default "disable";
                    description "Administrative state of statistics collection";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container svlan-statistics

            container system-behavior {
                description "Enter the system-behavior context";

                leaf legacy-dns-nbns {
                    type boolean;
                    default "false";
                    description "Restrict authentication origins for name servers";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container system-behavior

            container subscriber-interface-statistics {
                description "Enter the subscriber-interface-statistics context";

                leaf admin-state {
                    type types-sros:admin-state;
                    default "disable";
                    description "Administrative state for statistics collection";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container subscriber-interface-statistics

            container group-interface-statistics {
                description "Enter the group-interface-statistics context";

                leaf admin-state {
                    type types-sros:admin-state;
                    default "disable";
                    description "Administrative state for statistics collection";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container group-interface-statistics

            uses conf-submgt-ancp;
            uses conf-submgt-gtp;
            uses conf-submgt-isa-filter;
            uses conf-submgt-isa-policer;
            uses conf-submgt-service-chaining-isa-service-chaining;
            uses conf-submgt-local-user-db;
            uses conf-submgt-up-resiliency;
            uses conf-submgt-vrgw;
            uses conf-submgt-wlangw-wlan-gw;
        } // container subscriber-mgmt

    } // grouping conf-subscriber-mgmt

}
