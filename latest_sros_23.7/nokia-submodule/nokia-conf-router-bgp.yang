submodule nokia-conf-router-bgp {

    yang-version "1.1";

    belongs-to nokia-conf { prefix "conf"; }

    import nokia-sros-yang-extensions     { prefix "sros-ext"; }
    import nokia-types-bgp                { prefix "types-bgp"; }
    import nokia-types-router             { prefix "types-router"; }
    import nokia-types-sros               { prefix "types-sros"; }

    include nokia-conf-bmp;
    include nokia-conf-groups;
    include nokia-conf-policy-options;
    include nokia-conf-router;
    include nokia-conf-router-segment-routing;
    include nokia-conf-system;
    include nokia-conf-system-security;

    sros-ext:sros-major-release "rel23";
    organization "Nokia";
    contact
        "Nokia SR OS Support
         Web: <http://www.nokia.com>";
    description
        "Nokia YANG Data model to configure bgp protocol on SR OS based routers.

         Copyright 2016 Nokia. All rights reserved. Reproduction of this document
         is authorized on the condition that the foregoing copyright notice is included.

         This nokia-conf-router-bgp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-04-28";

    grouping conf-router-bgp {
        ///nokia-conf/configure/router/bgp
        container bgp {
            presence "Enable the bgp context";
            description "Enable the bgp context";

            ///nokia-conf/configure/router/bgp/description
            leaf description {
                type types-sros:description;
                description "Text description";
            }

            ///nokia-conf/configure/router/bgp/connect-retry
            leaf connect-retry {
                type int32 {
                    range "1..65535";
                }
                default "120";
                description "BGP connect retry timer value";
            }

            ///nokia-conf/configure/router/bgp/admin-state
            leaf admin-state {
                type types-sros:admin-state;
                default "enable";
                description "Administrative state of the BGP instance";
            }

            ///nokia-conf/configure/router/bgp/keepalive
            leaf keepalive {
                type int32 {
                    range "0..21845";
                }
                default "30";
                description "Time after which the BGP KEEPALIVE message is sent";
            }

            ///nokia-conf/configure/router/bgp/damping
            leaf damping {
                type boolean;
                default "false";
                description "Use BGP route damping to reduce route flap";
            }

            ///nokia-conf/configure/router/bgp/local-preference
            leaf local-preference {
                type uint32;
                default "100";
                description "Default local preference if not in incoming routes";
            }

            ///nokia-conf/configure/router/bgp/loop-detect
            leaf loop-detect {
                type types-bgp:loop-detect;
                default "ignore-loop";
                description "Strategy for loop detection in the AS path";
            }

            ///nokia-conf/configure/router/bgp/loop-detect-threshold
            leaf loop-detect-threshold {
                type uint32 {
                    range "0..15";
                }
                default "0";
                description "Threshold for the global ASN in a received AS path";
            }

            ///nokia-conf/configure/router/bgp/tcp-mss
            leaf tcp-mss {
                type uint32 {
                    range "384..9746";
                }
                description "TCP maximum segment size override";
            }

            ///nokia-conf/configure/router/bgp/selective-label-ipv4-install
            leaf selective-label-ipv4-install {
                type boolean;
                default "false";
                description "Enable selective download for BGP label-ipv4 routes";
            }

            ///nokia-conf/configure/router/bgp/selective-label-ip-prioritization
            leaf selective-label-ip-prioritization {
                type boolean;
                default "false";
                description "Enable BGP selective prioritization for labeled routes";
            }

            ///nokia-conf/configure/router/bgp/min-route-advertisement
            leaf min-route-advertisement {
                type int16 {
                    range "1..255";
                }
                default "30";
                description "Minimum time before a prefix can be advertised to peer";
            }

            ///nokia-conf/configure/router/bgp/aggregator-id-zero
            leaf aggregator-id-zero {
                type boolean;
                default "false";
                description "Set router ID in the BGP AGGREGATOR attribute to 0";
            }

            ///nokia-conf/configure/router/bgp/preference
            leaf preference {
                type uint32 {
                    range "1..255";
                }
                default "170";
                description "Route preference for routes learned from all peers";
            }

            ///nokia-conf/configure/router/bgp/block-prefix-sid
            leaf block-prefix-sid {
                type boolean;
                default "false";
                description "Block the prefix SID attribute";
            }

            ///nokia-conf/configure/router/bgp/multihop
            leaf multihop {
                type int32 {
                    range "1..255";
                }
                description "TTL in IP packet headers for EBGP peers multi-hops away";
            }

            ///nokia-conf/configure/router/bgp/med-out
            leaf med-out {
                type union {
                    type uint32;
                    type enumeration {
                        enum igp-cost                       { value -1; }
                    }
                }
                description "Default MED attribute value to advertise to peers";
            }

            ///nokia-conf/configure/router/bgp/authentication-key
            leaf authentication-key {
                type types-sros:encrypted-leaf {
                    length "1..370";
                }
                description "BGP authentication key for all peers";
            }

            ///nokia-conf/configure/router/bgp/client-reflect
            leaf client-reflect {
                type boolean;
                default "true";
                description "Allow client reflection of routes by route reflector";
            }

            ///nokia-conf/configure/router/bgp/vpn-apply-export
            leaf vpn-apply-export {
                type boolean;
                default "false";
                description "Apply base-instance BGP export policies to VPN routes";
            }

            ///nokia-conf/configure/router/bgp/vpn-apply-import
            leaf vpn-apply-import {
                type boolean;
                default "false";
                description "Apply base-instance import route policies to VPN routes";
            }

            ///nokia-conf/configure/router/bgp/asn-4-byte
            leaf asn-4-byte {
                type boolean;
                default "true";
                description "Advertise support for 4-byte ASNs";
            }

            ///nokia-conf/configure/router/bgp/path-mtu-discovery
            leaf path-mtu-discovery {
                type boolean;
                default "false";
                description "Enable Path MTU Discovery";
            }

            ///nokia-conf/configure/router/bgp/enforce-first-as
            leaf enforce-first-as {
                type boolean;
                default "false";
                description "Enforce the configured peer AS value in received routes";
            }

            ///nokia-conf/configure/router/bgp/initial-send-delay-zero
            leaf initial-send-delay-zero {
                type boolean;
                default "false";
                description "Send BGP updates as soon as session comes up";
            }

            ///nokia-conf/configure/router/bgp/router-id
            leaf router-id {
                type types-sros:ipv4-address;
                description "Router ID for the BGP instance in the AS";
            }

            ///nokia-conf/configure/router/bgp/inter-as-vpn
            leaf inter-as-vpn {
                type boolean;
                default "false";
                description "Allow advertisement of VPN routes across AS boundaries";
            }

            ///nokia-conf/configure/router/bgp/purge-timer
            leaf purge-timer {
                type uint32 {
                    range "1..60";
                }
                default "10";
                description "Maximum time before stale routes are purged";
            }

            ///nokia-conf/configure/router/bgp/route-table-install
            leaf route-table-install {
                type boolean;
                default "true";
                description "Install all IPv4 and IPv6 BGP routes in FIB and RTM";
            }

            ///nokia-conf/configure/router/bgp/ibgp-multipath
            leaf ibgp-multipath {
                type boolean;
                default "false";
                description "Enable IBGP multipath load balancing";
            }

            ///nokia-conf/configure/router/bgp/rr-vpn-forwarding
            leaf rr-vpn-forwarding {
                type boolean;
                default "false";
                description "Allow route reflector to forward VPN-IP routes";
            }

            ///nokia-conf/configure/router/bgp/subconfed-vpn-forwarding
            leaf subconfed-vpn-forwarding {
                type boolean;
                default "false";
                description "Allow subconfed route resolution, next hop and labels";
            }

            ///nokia-conf/configure/router/bgp/bfd-liveness
            leaf bfd-liveness {
                type boolean;
                default "false";
                description "Enable BFD";
            }

            ///nokia-conf/configure/router/bgp/fast-external-failover
            leaf fast-external-failover {
                type boolean;
                default "true";
                description "Drop external BGP session immediately when link fails";
            }

            ///nokia-conf/configure/router/bgp/advertise-inactive
            leaf advertise-inactive {
                type boolean;
                default "false";
                description "Advertise inactive BGP routes to peers";
            }

            ///nokia-conf/configure/router/bgp/authentication-keychain
            leaf authentication-keychain {
                type leafref {
                    path "../../../system/security/keychains/keychain/keychain-name";
                }
                description "TCP authentication keychain for the session";
            }

            ///nokia-conf/configure/router/bgp/mvpn-vrf-import-subtype-new
            leaf mvpn-vrf-import-subtype-new {
                type boolean;
                default "false";
                description "Encode the IANA value of 0x010b in advertised routes";
            }

            ///nokia-conf/configure/router/bgp/rapid-withdrawal
            leaf rapid-withdrawal {
                type boolean;
                default "false";
                description "Send BGP withdrawal UPDATE messages immediately";
            }

            ///nokia-conf/configure/router/bgp/mp-bgp-keep
            leaf mp-bgp-keep {
                type boolean;
                default "false";
                description "Keep rejected VPN-IP routes in RIB-IN";
            }

            ///nokia-conf/configure/router/bgp/peer-ip-tracking
            leaf peer-ip-tracking {
                type boolean;
                default "false";
                description "Enable BGP peer tracking";
            }

            ///nokia-conf/configure/router/bgp/split-horizon
            leaf split-horizon {
                type boolean;
                default "false";
                description "Prevent routes being reflected back to best-route peer";
            }

            ///nokia-conf/configure/router/bgp/override-tunnel-elc
            leaf override-tunnel-elc {
                type boolean;
                default "false";
                description "Enable entropy label capability on BGP tunnels";
            }

            ///nokia-conf/configure/router/bgp/link-state-route-export
            leaf link-state-route-export {
                type boolean;
                default "false";
                description "Allow the export of the TED NLRI database";
            }

            ///nokia-conf/configure/router/bgp/link-state-route-import
            leaf link-state-route-import {
                type boolean;
                default "false";
                description "Allow the import of the TED NLRI database";
            }

            ///nokia-conf/configure/router/bgp/third-party-nexthop
            leaf third-party-nexthop {
                type boolean;
                default "false";
                description "Apply third-party next-hop processing to EBGP peers";
            }

            ///nokia-conf/configure/router/bgp/dynamic-neighbor-limit
            leaf dynamic-neighbor-limit {
                type uint32 {
                    range "1..8192";
                }
                description "Max dynamic BGP sessions to accept from remote peers";
            }

            ///nokia-conf/configure/router/bgp/label-preference
            leaf label-preference {
                type uint32 {
                    range "1..255";
                }
                default "170";
                description "Route preference for routes from labeled-unicast peers";
            }

            ///nokia-conf/configure/router/bgp/peer-tracking-policy
            leaf peer-tracking-policy {
                type leafref {
                    path "../../../policy-options/policy-statement/name";
                }
                description "Policy for BGP peer tracking on router instance";
            }

            ///nokia-conf/configure/router/bgp/def-recv-evpn-encap
            leaf def-recv-evpn-encap {
                type types-bgp:encap;
                default "mpls";
                description "Default EVPN encapsulation type";
            }

            ///nokia-conf/configure/router/bgp/sr-policy-import
            leaf sr-policy-import {
                type boolean;
                default "false";
                description "Import all segment routing policies into the BGP RIB";
            }

            ///nokia-conf/configure/router/bgp/bgp-tunnel-preference
            leaf bgp-tunnel-preference {
                type uint32 {
                    range "1..255";
                }
                default "12";
                description "BGP tunnel table preference";
            }

            ///nokia-conf/configure/router/bgp/selective-label-ip
            leaf selective-label-ip {
                type enumeration {
                    enum no-install                     { value 1; }
                    enum route-table-install-only       { value 2; }
                }
                description "Label IP routes installed for local use on NHS router";
            }

            ///nokia-conf/configure/router/bgp/apply-groups
            leaf-list apply-groups {
                type leafref {
                    path "../../../groups/group/name";
                }
                max-elements 8;
                ordered-by user;
                description "Apply a configuration group at this level";
            }

            ///nokia-conf/configure/router/bgp/apply-groups-exclude
            leaf-list apply-groups-exclude {
                type leafref {
                    path "../../../groups/group/name";
                }
                max-elements 8;
                ordered-by user;
                description "Exclude a configuration group at this level";
            }

            ///nokia-conf/configure/router/bgp/hold-time
            container hold-time {
                description "Enter the hold-time context";

                ///nokia-conf/configure/router/bgp/hold-time/seconds
                leaf seconds {
                    type int32 {
                        range "0|3..65535";
                    }
                    default "90";
                    description "Maximum time BGP waits between successive messages";
                }

                ///nokia-conf/configure/router/bgp/hold-time/minimum-hold-time
                leaf minimum-hold-time {
                    type int32 {
                        range "0|3..65535";
                    }
                    default "0";
                    description "Minimum hold time between successive messages";
                }

            } // container hold-time

            ///nokia-conf/configure/router/bgp/family
            container family {
                description "Enter the family context";

                ///nokia-conf/configure/router/bgp/family/ipv4
                leaf ipv4 {
                    type boolean;
                    default "true";
                    description "Advertise MP-BGP support for the IPv4 address family";
                }

                ///nokia-conf/configure/router/bgp/family/vpn-ipv4
                leaf vpn-ipv4 {
                    type boolean;
                    default "false";
                    description "Advertise MP-BGP support for IPv4 VPN address family";
                }

                ///nokia-conf/configure/router/bgp/family/ipv6
                leaf ipv6 {
                    type boolean;
                    default "false";
                    description "Advertise MP-BGP support for the IPv6 address family";
                }

                ///nokia-conf/configure/router/bgp/family/mcast-ipv4
                leaf mcast-ipv4 {
                    type boolean;
                    default "false";
                    description "Advertise support for the MCAST-IPv4 address family";
                }

                ///nokia-conf/configure/router/bgp/family/vpn-ipv6
                leaf vpn-ipv6 {
                    type boolean;
                    default "false";
                    description "Advertise MP-BGP support for IPv6 VPN address family";
                }

                ///nokia-conf/configure/router/bgp/family/l2-vpn
                leaf l2-vpn {
                    type boolean;
                    default "false";
                    description "Advertise MP-BGP support for the L2-VPN address family";
                }

                ///nokia-conf/configure/router/bgp/family/mvpn-ipv4
                leaf mvpn-ipv4 {
                    type boolean;
                    default "false";
                    description "Advertise support for the IPv4 MCAST VPN address family";
                }

                ///nokia-conf/configure/router/bgp/family/mdt-safi
                leaf mdt-safi {
                    type boolean;
                    default "false";
                    description "Advertise MP-BGP support for MDT-SAFI address family";
                }

                ///nokia-conf/configure/router/bgp/family/ms-pw
                leaf ms-pw {
                    type boolean;
                    default "false";
                    description "Advertise support for multi-segment PW address family";
                }

                ///nokia-conf/configure/router/bgp/family/flow-ipv4
                leaf flow-ipv4 {
                    type boolean;
                    default "false";
                    description "Advertise support for the flowspec-IPv4 address family";
                }

                ///nokia-conf/configure/router/bgp/family/route-target
                leaf route-target {
                    type boolean;
                    default "false";
                    description "Advertise MP-BGP support for RT constraint routes";
                }

                ///nokia-conf/configure/router/bgp/family/mcast-vpn-ipv4
                leaf mcast-vpn-ipv4 {
                    type boolean;
                    default "false";
                    description "Advertise support for the IPv4 VPN MCAST address family";
                }

                ///nokia-conf/configure/router/bgp/family/mvpn-ipv6
                leaf mvpn-ipv6 {
                    type boolean;
                    default "false";
                    description "Advertise support for the IPv6 MCAST VPN address family";
                }

                ///nokia-conf/configure/router/bgp/family/flow-ipv6
                leaf flow-ipv6 {
                    type boolean;
                    default "false";
                    description "Advertise support for the flowspec-IPv6 address family";
                }

                ///nokia-conf/configure/router/bgp/family/evpn
                leaf evpn {
                    type boolean;
                    default "false";
                    description "Advertise MP-BGP support for the EVPN address family";
                }

                ///nokia-conf/configure/router/bgp/family/mcast-ipv6
                leaf mcast-ipv6 {
                    type boolean;
                    default "false";
                    description "Advertise support for the MCAST-IPv6 address family";
                }

                ///nokia-conf/configure/router/bgp/family/label-ipv4
                leaf label-ipv4 {
                    type boolean;
                    default "false";
                    description "Advertise support for the label-IPv4 address family";
                }

                ///nokia-conf/configure/router/bgp/family/label-ipv6
                leaf label-ipv6 {
                    type boolean;
                    default "false";
                    description "Advertise support for the label-IPv6 address family";
                }

                ///nokia-conf/configure/router/bgp/family/bgp-ls
                leaf bgp-ls {
                    type boolean;
                    default "false";
                    description "Advertise MP-BGP support for the BGP-LS address family";
                }

                ///nokia-conf/configure/router/bgp/family/mcast-vpn-ipv6
                leaf mcast-vpn-ipv6 {
                    type boolean;
                    default "false";
                    description "Advertise support for the IPv6 VPN MCAST address family";
                }

                ///nokia-conf/configure/router/bgp/family/sr-policy-ipv4
                leaf sr-policy-ipv4 {
                    type boolean;
                    default "false";
                    description "Advertise MP-BGP support for the SR-policy-IPv4 family";
                }

                ///nokia-conf/configure/router/bgp/family/sr-policy-ipv6
                leaf sr-policy-ipv6 {
                    type boolean;
                    default "false";
                    description "Advertise MP-BGP support for the SR-policy-IPv6 family";
                }

                ///nokia-conf/configure/router/bgp/family/flow-vpn-ipv4
                leaf flow-vpn-ipv4 {
                    type boolean;
                    default "false";
                    description "Advertise support for FlowSpec-VPN IPv4 address family";
                }

                ///nokia-conf/configure/router/bgp/family/flow-vpn-ipv6
                leaf flow-vpn-ipv6 {
                    type boolean;
                    default "false";
                    description "Advertise support for FlowSpec-VPN IPv6 address family";
                }

            } // container family

            ///nokia-conf/configure/router/bgp/label-allocation
            container label-allocation {
                description "Enter the label-allocation context";

                ///nokia-conf/configure/router/bgp/label-allocation/label-ipv6
                container label-ipv6 {
                    description "Enter the label-ipv6 context";

                    ///nokia-conf/configure/router/bgp/label-allocation/label-ipv6/explicit-null
                    leaf explicit-null {
                        type boolean;
                        default "true";
                        description "Apply advertised label and associated programming rules";
                    }

                } // container label-ipv6

            } // container label-allocation

            ///nokia-conf/configure/router/bgp/send-default
            container send-default {
                description "Enter the send-default context";

                ///nokia-conf/configure/router/bgp/send-default/ipv4
                leaf ipv4 {
                    type boolean;
                    default "false";
                    description "Enable IPv4 family type";
                }

                ///nokia-conf/configure/router/bgp/send-default/ipv6
                leaf ipv6 {
                    type boolean;
                    default "false";
                    description "Enable IPv6 family type";
                }

                ///nokia-conf/configure/router/bgp/send-default/export-policy
                leaf export-policy {
                    type leafref {
                        path "../../../../policy-options/policy-statement/name";
                    }
                    description "Export policy name";
                }

            } // container send-default

            ///nokia-conf/configure/router/bgp/default-preference
            container default-preference {
                description "Enter the default-preference context";

                ///nokia-conf/configure/router/bgp/default-preference/ebgp
                leaf ebgp {
                    type uint32 {
                        range "0..255";
                    }
                    default "0";
                    description "Default preference for EBGP";
                }

                ///nokia-conf/configure/router/bgp/default-preference/ibgp
                leaf ibgp {
                    type uint32 {
                        range "0..255";
                    }
                    default "0";
                    description "Default preference for IBGP";
                }

            } // container default-preference

            ///nokia-conf/configure/router/bgp/default-label-preference
            container default-label-preference {
                description "Enter the default-label-preference context";

                ///nokia-conf/configure/router/bgp/default-label-preference/ebgp
                leaf ebgp {
                    type uint32 {
                        range "0..255";
                    }
                    default "0";
                    description "Default preference for EBGP";
                }

                ///nokia-conf/configure/router/bgp/default-label-preference/ibgp
                leaf ibgp {
                    type uint32 {
                        range "0..255";
                    }
                    default "0";
                    description "Default preference for IBGP";
                }

            } // container default-label-preference

            ///nokia-conf/configure/router/bgp/remove-private
            container remove-private {
                presence "Enable the remove-private context";
                description "Enable the remove-private context";

                ///nokia-conf/configure/router/bgp/remove-private/limited
                leaf limited {
                    type boolean;
                    default "false";
                    description "Remove private ASNs up to first public ASN encountered";
                }

                ///nokia-conf/configure/router/bgp/remove-private/skip-peer-as
                leaf skip-peer-as {
                    type boolean;
                    default "false";
                    description "Keep private ASN if AS-PATH contains eBGP peer's ASN";
                }

                ///nokia-conf/configure/router/bgp/remove-private/replace
                leaf replace {
                    type boolean;
                    default "false";
                    description "Replace private ASN with global ASN before advertising";
                }

            } // container remove-private

            ///nokia-conf/configure/router/bgp/cluster
            container cluster {
                description "Enter the cluster context";

                ///nokia-conf/configure/router/bgp/cluster/cluster-id
                leaf cluster-id {
                    type types-sros:ipv4-address;
                    description "Route reflector cluster ID";
                }

                ///nokia-conf/configure/router/bgp/cluster/orr-location
                leaf orr-location {
                    type uint32 {
                        range "1..255";
                    }
                    description "Optimal route reflection location for the cluster";
                }

                ///nokia-conf/configure/router/bgp/cluster/allow-local-fallback
                leaf allow-local-fallback {
                    type boolean;
                    default "false";
                    description "Allow fallback to RR topology location for ORR";
                }

            } // container cluster

            ///nokia-conf/configure/router/bgp/ebgp-default-reject-policy
            container ebgp-default-reject-policy {
                description "Enter the ebgp-default-reject-policy context";

                ///nokia-conf/configure/router/bgp/ebgp-default-reject-policy/import
                leaf import {
                    type boolean;
                    default "true";
                    description "Enable default reject import policy for external peers";
                }

                ///nokia-conf/configure/router/bgp/ebgp-default-reject-policy/export
                leaf export {
                    type boolean;
                    default "true";
                    description "Enable default reject export policy for external peers";
                }

            } // container ebgp-default-reject-policy

            ///nokia-conf/configure/router/bgp/bfd-strict-mode
            container bfd-strict-mode {
                description "Enter the bfd-strict-mode context";

                ///nokia-conf/configure/router/bgp/bfd-strict-mode/next-hop-reachability
                leaf next-hop-reachability {
                    type boolean;
                    default "false";
                    description "Consider next hop unreachable if BFD session is down";
                }

                ///nokia-conf/configure/router/bgp/bfd-strict-mode/advertise
                container advertise {
                    presence "Enable the advertise context";
                    description "Enable the advertise context";

                    ///nokia-conf/configure/router/bgp/bfd-strict-mode/advertise/holdtime
                    leaf holdtime {
                        type uint16 {
                            range "1..65535";
                        }
                        units "seconds";
                        default "30";
                        description "Maximum time BGP waits for the BFD session to come up";
                    }

                } // container advertise

            } // container bfd-strict-mode

            ///nokia-conf/configure/router/bgp/local-as
            container local-as {
                description "Enter the local-as context";

                ///nokia-conf/configure/router/bgp/local-as/as-number
                leaf as-number {
                    type uint32 {
                        range "1..4294967295";
                    }
                    description "Local (or virtual) BGP AS number";
                }

                ///nokia-conf/configure/router/bgp/local-as/private
                leaf private {
                    type boolean;
                    default "false";
                    description "Hide the local ASN in sent paths learned from peering";
                }

                ///nokia-conf/configure/router/bgp/local-as/prepend-global-as
                leaf prepend-global-as {
                    type boolean;
                    default "true";
                    description "Prepend global AS when advertising routes to BGP peer";
                }

            } // container local-as

            ///nokia-conf/configure/router/bgp/best-path-selection
            container best-path-selection {
                description "Enter the best-path-selection context";

                ///nokia-conf/configure/router/bgp/best-path-selection/compare-origin-validation-state
                leaf compare-origin-validation-state {
                    type boolean;
                    default "false";
                    description "Compare RPKI origin validation state of usable routes";
                }

                ///nokia-conf/configure/router/bgp/best-path-selection/deterministic-med
                leaf deterministic-med {
                    type boolean;
                    default "false";
                    description "Group paths based on AS before MED attribute comparison";
                }

                ///nokia-conf/configure/router/bgp/best-path-selection/origin-invalid-unusable
                leaf origin-invalid-unusable {
                    type boolean;
                    default "false";
                    description "Deem invalid routes unusable for best-path selection";
                }

                ///nokia-conf/configure/router/bgp/best-path-selection/ignore-nh-metric
                leaf ignore-nh-metric {
                    type boolean;
                    default "false";
                    description "Ignore next-hop distance in best path selection";
                }

                ///nokia-conf/configure/router/bgp/best-path-selection/d-path-length-ignore
                leaf d-path-length-ignore {
                    type boolean;
                    default "false";
                    description "Enable D-PATH length ignore";
                }

                ///nokia-conf/configure/router/bgp/best-path-selection/always-compare-med
                container always-compare-med {
                    description "Enter the always-compare-med context";

                    ///nokia-conf/configure/router/bgp/best-path-selection/always-compare-med/med-value
                    leaf med-value {
                        type types-bgp:med-value;
                        default "off";
                        description "Action for a missing MED attribute";
                    }

                    ///nokia-conf/configure/router/bgp/best-path-selection/always-compare-med/strict-as
                    leaf strict-as {
                        type boolean;
                        default "true";
                        description "Compare MED only for routes from same neighbor AS";
                    }

                } // container always-compare-med

                ///nokia-conf/configure/router/bgp/best-path-selection/as-path-ignore
                container as-path-ignore {
                    description "Enter the as-path-ignore context";

                    ///nokia-conf/configure/router/bgp/best-path-selection/as-path-ignore/ipv4
                    leaf ipv4 {
                        type boolean;
                        default "false";
                        description "Ignore AS path length for unlabeled unicast IPv4 routes";
                    }

                    ///nokia-conf/configure/router/bgp/best-path-selection/as-path-ignore/vpn-ipv4
                    leaf vpn-ipv4 {
                        type boolean;
                        default "false";
                        description "Ignore AS path length for VPN IPv4 (SAFI 128) routes";
                    }

                    ///nokia-conf/configure/router/bgp/best-path-selection/as-path-ignore/ipv6
                    leaf ipv6 {
                        type boolean;
                        default "false";
                        description "Ignore AS path length for unlabeled unicast IPv6 routes";
                    }

                    ///nokia-conf/configure/router/bgp/best-path-selection/as-path-ignore/mcast-ipv4
                    leaf mcast-ipv4 {
                        type boolean;
                        default "false";
                        description "Ignore AS path length for IPv4 multicast routes";
                    }

                    ///nokia-conf/configure/router/bgp/best-path-selection/as-path-ignore/vpn-ipv6
                    leaf vpn-ipv6 {
                        type boolean;
                        default "false";
                        description "Ignore AS path length for VPN IPv6 (SAFI 128) routes";
                    }

                    ///nokia-conf/configure/router/bgp/best-path-selection/as-path-ignore/l2-vpn
                    leaf l2-vpn {
                        type boolean;
                        default "false";
                        description "Ignore AS path length for L2-VPN routes";
                    }

                    ///nokia-conf/configure/router/bgp/best-path-selection/as-path-ignore/mvpn-ipv4
                    leaf mvpn-ipv4 {
                        type boolean;
                        default "false";
                        description "Ignore AS path length for IPv4 MVPN routes";
                    }

                    ///nokia-conf/configure/router/bgp/best-path-selection/as-path-ignore/mvpn-ipv6
                    leaf mvpn-ipv6 {
                        type boolean;
                        default "false";
                        description "Ignore AS path length for IPv6 MVPN routes";
                    }

                    ///nokia-conf/configure/router/bgp/best-path-selection/as-path-ignore/mcast-ipv6
                    leaf mcast-ipv6 {
                        type boolean;
                        default "false";
                        description "Ignore AS path length for IPv6 multicast routes";
                    }

                    ///nokia-conf/configure/router/bgp/best-path-selection/as-path-ignore/label-ipv4
                    leaf label-ipv4 {
                        type boolean;
                        default "false";
                        description "Ignore AS path length for labeled-unicast IPv4 routes";
                    }

                    ///nokia-conf/configure/router/bgp/best-path-selection/as-path-ignore/label-ipv6
                    leaf label-ipv6 {
                        type boolean;
                        default "false";
                        description "Ignore AS path length for labeled-unicast IPv6 routes";
                    }

                } // container as-path-ignore

                ///nokia-conf/configure/router/bgp/best-path-selection/ignore-router-id
                container ignore-router-id {
                    presence "Enable the ignore-router-id context";
                    description "Enable the ignore-router-id context";

                    ///nokia-conf/configure/router/bgp/best-path-selection/ignore-router-id/include-internal
                    container include-internal {
                        description "Enter the include-internal context";

                        ///nokia-conf/configure/router/bgp/best-path-selection/ignore-router-id/include-internal/mvpn-ipv4
                        leaf mvpn-ipv4 {
                            type boolean;
                            default "false";
                            description "Ignore the router IDs of MVPN-IPv4 routes";
                        }

                        ///nokia-conf/configure/router/bgp/best-path-selection/ignore-router-id/include-internal/mvpn-ipv6
                        leaf mvpn-ipv6 {
                            type boolean;
                            default "false";
                            description "Ignore the router IDs of MVPN-IPv6 routes";
                        }

                    } // container include-internal

                } // container ignore-router-id

                ///nokia-conf/configure/router/bgp/best-path-selection/ebgp-ibgp-equal
                container ebgp-ibgp-equal {
                    description "Enter the ebgp-ibgp-equal context";

                    ///nokia-conf/configure/router/bgp/best-path-selection/ebgp-ibgp-equal/ipv4
                    leaf ipv4 {
                        type boolean;
                        default "false";
                        description "Consider EBGP and IBGP IPv4 routes equal";
                    }

                    ///nokia-conf/configure/router/bgp/best-path-selection/ebgp-ibgp-equal/ipv6
                    leaf ipv6 {
                        type boolean;
                        default "false";
                        description "Consider EBGP and IBGP IPv6 routes equal";
                    }

                    ///nokia-conf/configure/router/bgp/best-path-selection/ebgp-ibgp-equal/vpn-ipv4
                    leaf vpn-ipv4 {
                        type boolean;
                        default "false";
                        description "Consider EBGP and IBGP VPN-IPv4 routes equal";
                    }

                    ///nokia-conf/configure/router/bgp/best-path-selection/ebgp-ibgp-equal/vpn-ipv6
                    leaf vpn-ipv6 {
                        type boolean;
                        default "false";
                        description "Consider EBGP and IBGP VPN-IPv6 routes equal";
                    }

                    ///nokia-conf/configure/router/bgp/best-path-selection/ebgp-ibgp-equal/label-ipv4
                    leaf label-ipv4 {
                        type boolean;
                        default "false";
                        description "Consider EBGP and IBGP label-IPv4 routes equal";
                    }

                    ///nokia-conf/configure/router/bgp/best-path-selection/ebgp-ibgp-equal/label-ipv6
                    leaf label-ipv6 {
                        type boolean;
                        default "false";
                        description "Consider EBGP and IBGP label-IPv6 routes equal";
                    }

                    ///nokia-conf/configure/router/bgp/best-path-selection/ebgp-ibgp-equal/evpn
                    leaf evpn {
                        type boolean;
                        default "false";
                        description "Consider EBGP and IBGP EVPN routes equal";
                    }

                } // container ebgp-ibgp-equal

            } // container best-path-selection

            ///nokia-conf/configure/router/bgp/send-communities
            container send-communities {
                description "Enter the send-communities context";

                ///nokia-conf/configure/router/bgp/send-communities/standard
                leaf standard {
                    type boolean;
                    default "true";
                    description "Advertise the Communities attribute to peers";
                }

                ///nokia-conf/configure/router/bgp/send-communities/extended
                leaf extended {
                    type boolean;
                    default "true";
                    description "Advertise the Extended Communities attribute to peers";
                }

                ///nokia-conf/configure/router/bgp/send-communities/large
                leaf large {
                    type boolean;
                    default "true";
                    description "Advertise the Large Communities attribute to peers";
                }

            } // container send-communities

            ///nokia-conf/configure/router/bgp/error-handling
            container error-handling {
                description "Enter the error-handling context";

                ///nokia-conf/configure/router/bgp/error-handling/update-fault-tolerance
                leaf update-fault-tolerance {
                    type boolean;
                    default "false";
                    description "Tolerate non-critical errors in UPDATE messages";
                }

            } // container error-handling

            ///nokia-conf/configure/router/bgp/damp-peer-oscillations
            container damp-peer-oscillations {
                presence "Enable the damp-peer-oscillations context";
                description "Enable the damp-peer-oscillations context";

                ///nokia-conf/configure/router/bgp/damp-peer-oscillations/error-interval
                leaf error-interval {
                    type uint32 {
                        range "0..2048";
                    }
                    default "30";
                    description "Time after a reset that the session must be error-free";
                }

                ///nokia-conf/configure/router/bgp/damp-peer-oscillations/idle-hold-time
                container idle-hold-time {
                    description "Enter the idle-hold-time context";

                    ///nokia-conf/configure/router/bgp/damp-peer-oscillations/idle-hold-time/initial-wait
                    leaf initial-wait {
                        type uint32 {
                            range "0..2048";
                        }
                        default "0";
                        description "Time session remains in idle state after stabilization";
                    }

                    ///nokia-conf/configure/router/bgp/damp-peer-oscillations/idle-hold-time/second-wait
                    leaf second-wait {
                        type uint32 {
                            range "1..2048";
                        }
                        default "5";
                        description "Time that doubles after each session failure";
                    }

                    ///nokia-conf/configure/router/bgp/damp-peer-oscillations/idle-hold-time/max-wait
                    leaf max-wait {
                        type uint32 {
                            range "1..2048";
                        }
                        default "60";
                        description "Maximum session idle time after repeated instability";
                    }

                } // container idle-hold-time

            } // container damp-peer-oscillations

            ///nokia-conf/configure/router/bgp/rapid-update
            container rapid-update {
                description "Enter the rapid-update context";

                ///nokia-conf/configure/router/bgp/rapid-update/vpn-ipv4
                leaf vpn-ipv4 {
                    type boolean;
                    default "false";
                    description "Include VPN IPv4 address family routes";
                }

                ///nokia-conf/configure/router/bgp/rapid-update/vpn-ipv6
                leaf vpn-ipv6 {
                    type boolean;
                    default "false";
                    description "Include VPN IPv6 address family routes";
                }

                ///nokia-conf/configure/router/bgp/rapid-update/l2-vpn
                leaf l2-vpn {
                    type boolean;
                    default "false";
                    description "Include L2 VPN address family routes";
                }

                ///nokia-conf/configure/router/bgp/rapid-update/mvpn-ipv4
                leaf mvpn-ipv4 {
                    type boolean;
                    default "false";
                    description "Include MVPN IPv4 address family routes";
                }

                ///nokia-conf/configure/router/bgp/rapid-update/mdt-safi
                leaf mdt-safi {
                    type boolean;
                    default "false";
                    description "Include MDT SAFI address family routes";
                }

                ///nokia-conf/configure/router/bgp/rapid-update/mcast-vpn-ipv4
                leaf mcast-vpn-ipv4 {
                    type boolean;
                    default "false";
                    description "Include multicast VPN IPv4 address family routes";
                }

                ///nokia-conf/configure/router/bgp/rapid-update/mvpn-ipv6
                leaf mvpn-ipv6 {
                    type boolean;
                    default "false";
                    description "Include MVPN IPv6 address family routes";
                }

                ///nokia-conf/configure/router/bgp/rapid-update/evpn
                leaf evpn {
                    type boolean;
                    default "false";
                    description "Include EVPN address family routes";
                }

                ///nokia-conf/configure/router/bgp/rapid-update/label-ipv4
                leaf label-ipv4 {
                    type boolean;
                    default "false";
                    description "Include labeled IPv4 address family routes";
                }

                ///nokia-conf/configure/router/bgp/rapid-update/label-ipv6
                leaf label-ipv6 {
                    type boolean;
                    default "false";
                    description "Include labeled IPv6 address family routes";
                }

                ///nokia-conf/configure/router/bgp/rapid-update/mcast-vpn-ipv6
                leaf mcast-vpn-ipv6 {
                    type boolean;
                    default "false";
                    description "Include multicast VPN IPv6 address family routes";
                }

            } // container rapid-update

            ///nokia-conf/configure/router/bgp/advertise-external
            container advertise-external {
                description "Enter the advertise-external context";

                ///nokia-conf/configure/router/bgp/advertise-external/ipv4
                leaf ipv4 {
                    type boolean;
                    default "false";
                    description "Enable support for unlabeled unicast IPv4 routes";
                }

                ///nokia-conf/configure/router/bgp/advertise-external/ipv6
                leaf ipv6 {
                    type boolean;
                    default "false";
                    description "Enable support for unlabeled unicast IPv6 routes";
                }

                ///nokia-conf/configure/router/bgp/advertise-external/label-ipv4
                leaf label-ipv4 {
                    type boolean;
                    default "false";
                    description "Enable support for labeled-unicast IPv4 routes";
                }

                ///nokia-conf/configure/router/bgp/advertise-external/label-ipv6
                leaf label-ipv6 {
                    type boolean;
                    default "false";
                    description "Enable support for labeled-unicast IPv6 routes";
                }

            } // container advertise-external

            ///nokia-conf/configure/router/bgp/backup-path
            container backup-path {
                description "Enter the backup-path context";

                ///nokia-conf/configure/router/bgp/backup-path/ipv4
                leaf ipv4 {
                    type boolean;
                    default "false";
                    description "Enable support for unlabeled unicast IPv4 routes";
                }

                ///nokia-conf/configure/router/bgp/backup-path/ipv6
                leaf ipv6 {
                    type boolean;
                    default "false";
                    description "Enable support for unlabeled unicast IPv6 routes";
                }

                ///nokia-conf/configure/router/bgp/backup-path/label-ipv4
                leaf label-ipv4 {
                    type boolean;
                    default "false";
                    description "Enable support for labeled-unicast IPv4 routes";
                }

                ///nokia-conf/configure/router/bgp/backup-path/label-ipv6
                leaf label-ipv6 {
                    type boolean;
                    default "false";
                    description "Enable support for labeled-unicast IPv6 routes";
                }

            } // container backup-path

            ///nokia-conf/configure/router/bgp/flowspec
            container flowspec {
                description "Enter the flowspec context";

                ///nokia-conf/configure/router/bgp/flowspec/validate-dest-prefix
                leaf validate-dest-prefix {
                    type boolean;
                    default "false";
                    description "Validate destination prefix in FlowSpec-IPv4/IPv6 route";
                }

                ///nokia-conf/configure/router/bgp/flowspec/validate-redirect-ip
                leaf validate-redirect-ip {
                    type boolean;
                    default "false";
                    description "Validate the redirect-to-IPv4 action in FlowSpec route";
                }

            } // container flowspec

            ///nokia-conf/configure/router/bgp/neighbor-trust
            container neighbor-trust {
                description "Enter the neighbor-trust context";

                ///nokia-conf/configure/router/bgp/neighbor-trust/vpn-ipv4
                leaf vpn-ipv4 {
                    type boolean;
                    default "false";
                    description "Enable inter-AS label security for the VPN-IPv4 family";
                }

                ///nokia-conf/configure/router/bgp/neighbor-trust/vpn-ipv6
                leaf vpn-ipv6 {
                    type boolean;
                    default "false";
                    description "Enable inter-AS label security for the VPN-IPv6 family";
                }

                ///nokia-conf/configure/router/bgp/neighbor-trust/evpn
                leaf evpn {
                    type boolean;
                    default "false";
                    description "Enable inter-AS label security for the EVPN family";
                }

            } // container neighbor-trust

            ///nokia-conf/configure/router/bgp/convergence
            container convergence {
                description "Enter the convergence context";

                ///nokia-conf/configure/router/bgp/convergence/min-wait-to-advertise
                leaf min-wait-to-advertise {
                    type uint32 {
                        range "0..3600";
                    }
                    default "0";
                    description "Minimum wait time before advertising routes";
                }

                ///nokia-conf/configure/router/bgp/convergence/family
                list family {
                    key "family-type";
                    description "Enter the family list instance";

                    ///nokia-conf/configure/router/bgp/convergence/family/family-type
                    leaf family-type {
                        type enumeration {
                            enum ipv4                           { value 1; }
                            enum vpn-ipv4                       { value 2; }
                            enum ipv6                           { value 3; }
                            enum vpn-ipv6                       { value 5; }
                            enum label-ipv4                     { value 17; }
                            enum label-ipv6                     { value 18; }
                        }
                        description "Address family for which convergence selection applies";
                    }

                    ///nokia-conf/configure/router/bgp/convergence/family/max-wait-to-advertise
                    leaf max-wait-to-advertise {
                        type uint32 {
                            range "0..3600";
                        }
                        default "0";
                        description "Maximum wait time before advertising routes";
                    }

                    ///nokia-conf/configure/router/bgp/convergence/family/apply-groups
                    leaf-list apply-groups {
                        type leafref {
                            path "../../../../../groups/group/name";
                        }
                        max-elements 8;
                        ordered-by user;
                        description "Apply a configuration group at this level";
                    }

                    ///nokia-conf/configure/router/bgp/convergence/family/apply-groups-exclude
                    leaf-list apply-groups-exclude {
                        type leafref {
                            path "../../../../../groups/group/name";
                        }
                        max-elements 8;
                        ordered-by user;
                        description "Exclude a configuration group at this level";
                    }

                } // list family

            } // container convergence

            ///nokia-conf/configure/router/bgp/add-paths
            container add-paths {
                presence "Enable the add-paths context";
                description "Enable the add-paths context";

                ///nokia-conf/configure/router/bgp/add-paths/ipv4
                container ipv4 {
                    description "Enter the ipv4 context";

                    ///nokia-conf/configure/router/bgp/add-paths/ipv4/send
                    leaf send {
                        type types-bgp:add-paths-send-limit;
                        description "Maximum paths per unlabeled IPv4 unicast prefix";
                    }

                    ///nokia-conf/configure/router/bgp/add-paths/ipv4/receive
                    leaf receive {
                        type boolean;
                        default "false";
                        description "Receive multiple routes per unlabeled IPv4 prefix";
                    }

                } // container ipv4

                ///nokia-conf/configure/router/bgp/add-paths/ipv6
                container ipv6 {
                    description "Enter the ipv6 context";

                    ///nokia-conf/configure/router/bgp/add-paths/ipv6/send
                    leaf send {
                        type types-bgp:add-paths-send-limit;
                        description "Maximum paths per unlabeled IPv6 unicast prefix";
                    }

                    ///nokia-conf/configure/router/bgp/add-paths/ipv6/receive
                    leaf receive {
                        type boolean;
                        default "false";
                        description "Receive multiple routes per unlabeled IPv6 prefix";
                    }

                } // container ipv6

                ///nokia-conf/configure/router/bgp/add-paths/label-ipv4
                container label-ipv4 {
                    description "Enter the label-ipv4 context";

                    ///nokia-conf/configure/router/bgp/add-paths/label-ipv4/send
                    leaf send {
                        type types-bgp:add-paths-send-limit;
                        description "Paths advertised per labeled IPv4 unicast prefix";
                    }

                    ///nokia-conf/configure/router/bgp/add-paths/label-ipv4/receive
                    leaf receive {
                        type boolean;
                        default "false";
                        description "Receive multiple labeled-unicast routes per IPv4 prefix";
                    }

                } // container label-ipv4

                ///nokia-conf/configure/router/bgp/add-paths/label-ipv6
                container label-ipv6 {
                    description "Enter the label-ipv6 context";

                    ///nokia-conf/configure/router/bgp/add-paths/label-ipv6/send
                    leaf send {
                        type types-bgp:add-paths-send-limit;
                        description "Paths advertised per labeled IPv6 unicast prefix";
                    }

                    ///nokia-conf/configure/router/bgp/add-paths/label-ipv6/receive
                    leaf receive {
                        type boolean;
                        default "false";
                        description "Receive multiple labeled-unicast routes per IPv6 prefix";
                    }

                } // container label-ipv6

                ///nokia-conf/configure/router/bgp/add-paths/vpn-ipv4
                container vpn-ipv4 {
                    description "Enter the vpn-ipv4 context";

                    ///nokia-conf/configure/router/bgp/add-paths/vpn-ipv4/send
                    leaf send {
                        type types-bgp:add-paths-send-limit;
                        description "Maximum paths advertised per VPN-IPv4 prefix";
                    }

                    ///nokia-conf/configure/router/bgp/add-paths/vpn-ipv4/receive
                    leaf receive {
                        type boolean;
                        default "false";
                        description "Receive multiple routes per VPN-IPv4 prefix";
                    }

                } // container vpn-ipv4

                ///nokia-conf/configure/router/bgp/add-paths/vpn-ipv6
                container vpn-ipv6 {
                    description "Enter the vpn-ipv6 context";

                    ///nokia-conf/configure/router/bgp/add-paths/vpn-ipv6/send
                    leaf send {
                        type types-bgp:add-paths-send-limit;
                        description "Maximum paths advertised per VPN-IPv6 prefix";
                    }

                    ///nokia-conf/configure/router/bgp/add-paths/vpn-ipv6/receive
                    leaf receive {
                        type boolean;
                        default "false";
                        description "Receive multiple routes per VPN-IPv6 prefix";
                    }

                } // container vpn-ipv6

                ///nokia-conf/configure/router/bgp/add-paths/mvpn-ipv4
                container mvpn-ipv4 {
                    description "Enter the mvpn-ipv4 context";

                    ///nokia-conf/configure/router/bgp/add-paths/mvpn-ipv4/send
                    leaf send {
                        type int32 {
                            range "1..16";
                        }
                        description "Maximum paths advertised per multicast VPN IPv4 NRLI";
                    }

                    ///nokia-conf/configure/router/bgp/add-paths/mvpn-ipv4/receive
                    leaf receive {
                        type boolean;
                        default "false";
                        description "Receive multiple routes per multicast VPN IPv4 NRLI";
                    }

                } // container mvpn-ipv4

                ///nokia-conf/configure/router/bgp/add-paths/mvpn-ipv6
                container mvpn-ipv6 {
                    description "Enter the mvpn-ipv6 context";

                    ///nokia-conf/configure/router/bgp/add-paths/mvpn-ipv6/send
                    leaf send {
                        type int32 {
                            range "1..16";
                        }
                        description "Maximum paths advertised per multicast VPN IPv6 NRLI";
                    }

                    ///nokia-conf/configure/router/bgp/add-paths/mvpn-ipv6/receive
                    leaf receive {
                        type boolean;
                        default "false";
                        description "Receive multiple routes per multicast VPN IPv6 NRLI";
                    }

                } // container mvpn-ipv6

                ///nokia-conf/configure/router/bgp/add-paths/mcast-vpn-ipv4
                container mcast-vpn-ipv4 {
                    description "Enter the mcast-vpn-ipv4 context";

                    ///nokia-conf/configure/router/bgp/add-paths/mcast-vpn-ipv4/send
                    leaf send {
                        type int32 {
                            range "1..16";
                        }
                        description "Maximum paths advertised per multicast IPv4 VPN prefix";
                    }

                    ///nokia-conf/configure/router/bgp/add-paths/mcast-vpn-ipv4/receive
                    leaf receive {
                        type boolean;
                        default "false";
                        description "Receive multiple multicast routes per IPv4 VPN prefix";
                    }

                } // container mcast-vpn-ipv4

                ///nokia-conf/configure/router/bgp/add-paths/mcast-vpn-ipv6
                container mcast-vpn-ipv6 {
                    description "Enter the mcast-vpn-ipv6 context";

                    ///nokia-conf/configure/router/bgp/add-paths/mcast-vpn-ipv6/send
                    leaf send {
                        type int32 {
                            range "1..16";
                        }
                        description "Maximum paths advertised per multicast IPv6 VPN prefix";
                    }

                    ///nokia-conf/configure/router/bgp/add-paths/mcast-vpn-ipv6/receive
                    leaf receive {
                        type boolean;
                        default "false";
                        description "Receive multiple multicast routes per IPv6 VPN prefix";
                    }

                } // container mcast-vpn-ipv6

                ///nokia-conf/configure/router/bgp/add-paths/evpn
                container evpn {
                    description "Enter the evpn context";

                    ///nokia-conf/configure/router/bgp/add-paths/evpn/send
                    leaf send {
                        type types-bgp:add-paths-send-limit;
                        description "Maximum number of EVPN paths to send";
                    }

                    ///nokia-conf/configure/router/bgp/add-paths/evpn/receive
                    leaf receive {
                        type boolean;
                        default "false";
                        description "Receive multiple EVPN paths per prefix from a peer";
                    }

                } // container evpn

            } // container add-paths

            ///nokia-conf/configure/router/bgp/import
            container import {
                presence "Enable the import context";
                description "Enable the import context";

                ///nokia-conf/configure/router/bgp/import/policy
                leaf-list policy {
                    type union {
                        type types-sros:policy-expr-string;
                        type string;
                    }
                    min-elements 1;
                    max-elements 15;
                    ordered-by user;
                    description "BGP import policy name";
                }

                ///nokia-conf/configure/router/bgp/import/apply-groups
                leaf-list apply-groups {
                    type leafref {
                        path "../../../../groups/group/name";
                    }
                    max-elements 8;
                    ordered-by user;
                    description "Apply a configuration group at this level";
                }

                ///nokia-conf/configure/router/bgp/import/apply-groups-exclude
                leaf-list apply-groups-exclude {
                    type leafref {
                        path "../../../../groups/group/name";
                    }
                    max-elements 8;
                    ordered-by user;
                    description "Exclude a configuration group at this level";
                }

            } // container import

            ///nokia-conf/configure/router/bgp/export
            container export {
                presence "Enable the export context";
                description "Enable the export context";

                ///nokia-conf/configure/router/bgp/export/policy
                leaf-list policy {
                    type union {
                        type types-sros:policy-expr-string;
                        type string;
                    }
                    min-elements 1;
                    max-elements 15;
                    ordered-by user;
                    description "List of export policy names";
                }

                ///nokia-conf/configure/router/bgp/export/apply-groups
                leaf-list apply-groups {
                    type leafref {
                        path "../../../../groups/group/name";
                    }
                    max-elements 8;
                    ordered-by user;
                    description "Apply a configuration group at this level";
                }

                ///nokia-conf/configure/router/bgp/export/apply-groups-exclude
                leaf-list apply-groups-exclude {
                    type leafref {
                        path "../../../../groups/group/name";
                    }
                    max-elements 8;
                    ordered-by user;
                    description "Exclude a configuration group at this level";
                }

            } // container export

            ///nokia-conf/configure/router/bgp/extended-nh-encoding
            container extended-nh-encoding {
                description "Enter the extended-nh-encoding context";

                ///nokia-conf/configure/router/bgp/extended-nh-encoding/vpn-ipv4
                leaf vpn-ipv4 {
                    type boolean;
                    default "false";
                    description "Advertise encoding capability for VPN-IPv4 routes";
                }

                ///nokia-conf/configure/router/bgp/extended-nh-encoding/label-ipv4
                leaf label-ipv4 {
                    type boolean;
                    default "false";
                    description "Advertise encoding capability for label-IPv4 routes";
                }

                ///nokia-conf/configure/router/bgp/extended-nh-encoding/ipv4
                leaf ipv4 {
                    type boolean;
                    default "false";
                    description "Advertise encoding capability for IPv4 routes";
                }

            } // container extended-nh-encoding

            ///nokia-conf/configure/router/bgp/advertise-ipv6-next-hops
            container advertise-ipv6-next-hops {
                description "Enter the advertise-ipv6-next-hops context";

                ///nokia-conf/configure/router/bgp/advertise-ipv6-next-hops/vpn-ipv6
                leaf vpn-ipv6 {
                    type boolean;
                    default "false";
                    description "Advertise VPN IPv6 route with IPv6 next-hop address";
                }

                ///nokia-conf/configure/router/bgp/advertise-ipv6-next-hops/label-ipv6
                leaf label-ipv6 {
                    type boolean;
                    default "false";
                    description "Advertise label IPv6 route with IPv6 next-hop address";
                }

                ///nokia-conf/configure/router/bgp/advertise-ipv6-next-hops/evpn
                leaf evpn {
                    type boolean;
                    default "false";
                    description "Advertise EVPN route with IPv6 next-hop address";
                }

                ///nokia-conf/configure/router/bgp/advertise-ipv6-next-hops/vpn-ipv4
                leaf vpn-ipv4 {
                    type boolean;
                    default "false";
                    description "Advertise VPN IPv4 route with IPv6 next-hop address";
                }

                ///nokia-conf/configure/router/bgp/advertise-ipv6-next-hops/label-ipv4
                leaf label-ipv4 {
                    type boolean;
                    default "false";
                    description "Advertise label IPv4 route with IPv6 next-hop address";
                }

                ///nokia-conf/configure/router/bgp/advertise-ipv6-next-hops/ipv4
                leaf ipv4 {
                    type boolean;
                    default "false";
                    description "Advertise IPv4 route with IPv6 next-hop address";
                }

            } // container advertise-ipv6-next-hops

            ///nokia-conf/configure/router/bgp/graceful-restart
            container graceful-restart {
                presence "Enable the graceful-restart context";
                description "Enable the graceful-restart context";

                ///nokia-conf/configure/router/bgp/graceful-restart/restart-time
                leaf restart-time {
                    type uint32 {
                        range "0..4095";
                    }
                    default "120";
                    description "Restart time advertised by GR capability";
                }

                ///nokia-conf/configure/router/bgp/graceful-restart/stale-routes-time
                leaf stale-routes-time {
                    type uint32 {
                        range "1..3600";
                    }
                    default "360";
                    description "Maximum time to maintain routes after graceful restart";
                }

                ///nokia-conf/configure/router/bgp/graceful-restart/gr-notification
                leaf gr-notification {
                    type boolean;
                    default "false";
                    description "Perform Graceful Restart procedures";
                }

                ///nokia-conf/configure/router/bgp/graceful-restart/long-lived
                container long-lived {
                    presence "Enable the long-lived context";
                    description "Enable the long-lived context";

                    ///nokia-conf/configure/router/bgp/graceful-restart/long-lived/advertised-stale-time
                    leaf advertised-stale-time {
                        type uint32 {
                            range "0..16777215";
                        }
                        default "86400";
                        description "LLGR stale routes time";
                    }

                    ///nokia-conf/configure/router/bgp/graceful-restart/long-lived/helper-override-stale-time
                    leaf helper-override-stale-time {
                        type uint32 {
                            range "0..16777215";
                        }
                        description "Locally-configured stale routes override time";
                    }

                    ///nokia-conf/configure/router/bgp/graceful-restart/long-lived/helper-override-restart-time
                    leaf helper-override-restart-time {
                        type uint32 {
                            range "0..4095";
                        }
                        description "Locally-configured override for restart time";
                    }

                    ///nokia-conf/configure/router/bgp/graceful-restart/long-lived/forwarding-bits-set
                    leaf forwarding-bits-set {
                        type enumeration {
                            enum none                           { value 0; }
                            enum all                            { value 1; }
                            enum non-fwd                        { value 2; }
                        }
                        default "none";
                        description "BGP LLGR forwarding-bit behavior for address family";
                    }

                    ///nokia-conf/configure/router/bgp/graceful-restart/long-lived/advertise-stale-to-all-neighbors
                    leaf advertise-stale-to-all-neighbors {
                        type boolean;
                        default "false";
                        description "Advertise stale routes to all BGP peers";
                    }

                    ///nokia-conf/configure/router/bgp/graceful-restart/long-lived/without-no-export
                    leaf without-no-export {
                        type boolean;
                        default "false";
                        description "Advertise LLGR stale routes to non-LLGR peers";
                    }

                    ///nokia-conf/configure/router/bgp/graceful-restart/long-lived/family
                    list family {
                        key "family-type";
                        description "Enter the family list instance";

                        ///nokia-conf/configure/router/bgp/graceful-restart/long-lived/family/family-type
                        leaf family-type {
                            type types-bgp:llgr-family-identifiers;
                            description "Family type for family-specific LLGR configuration";
                        }

                        ///nokia-conf/configure/router/bgp/graceful-restart/long-lived/family/advertised-stale-time
                        leaf advertised-stale-time {
                            type uint32 {
                                range "0..16777215";
                            }
                            default "86400";
                            description "LLGR stale routes time for family override";
                        }

                        ///nokia-conf/configure/router/bgp/graceful-restart/long-lived/family/helper-override-stale-time
                        leaf helper-override-stale-time {
                            type uint32 {
                                range "0..16777215";
                            }
                            description "Locally-configured stale routes override time";
                        }

                        ///nokia-conf/configure/router/bgp/graceful-restart/long-lived/family/apply-groups
                        leaf-list apply-groups {
                            type leafref {
                                path "../../../../../../groups/group/name";
                            }
                            max-elements 8;
                            ordered-by user;
                            description "Apply a configuration group at this level";
                        }

                        ///nokia-conf/configure/router/bgp/graceful-restart/long-lived/family/apply-groups-exclude
                        leaf-list apply-groups-exclude {
                            type leafref {
                                path "../../../../../../groups/group/name";
                            }
                            max-elements 8;
                            ordered-by user;
                            description "Exclude a configuration group at this level";
                        }

                    } // list family

                } // container long-lived

            } // container graceful-restart

            ///nokia-conf/configure/router/bgp/optimal-route-reflection
            container optimal-route-reflection {
                description "Enter the optimal-route-reflection context";

                ///nokia-conf/configure/router/bgp/optimal-route-reflection/spf-wait
                container spf-wait {
                    description "Enter the spf-wait context";

                    ///nokia-conf/configure/router/bgp/optimal-route-reflection/spf-wait/max-wait
                    leaf max-wait {
                        type uint32 {
                            range "1..600";
                        }
                        default "60";
                        description "Maximum interval between consecutive SPF calculations";
                    }

                    ///nokia-conf/configure/router/bgp/optimal-route-reflection/spf-wait/initial-wait
                    leaf initial-wait {
                        type uint32 {
                            range "1..300";
                        }
                        default "5";
                        description "Initial SPF calculation delay after a topology change";
                    }

                    ///nokia-conf/configure/router/bgp/optimal-route-reflection/spf-wait/second-wait
                    leaf second-wait {
                        type uint32 {
                            range "1..300";
                        }
                        default "15";
                        description "Delay between first and second SPF calculation";
                    }

                } // container spf-wait

                ///nokia-conf/configure/router/bgp/optimal-route-reflection/location
                list location {
                    key "location-id";
                    description "Enter the location list instance";

                    ///nokia-conf/configure/router/bgp/optimal-route-reflection/location/location-id
                    leaf location-id {
                        type uint32 {
                            range "1..255";
                        }
                        description "Optimal route reflection location ID";
                    }

                    ///nokia-conf/configure/router/bgp/optimal-route-reflection/location/primary-ip-address
                    leaf primary-ip-address {
                        type types-sros:ipv4-unicast-address;
                        description "Primary IPv4 address of the reference location for ORR";
                    }

                    ///nokia-conf/configure/router/bgp/optimal-route-reflection/location/secondary-ip-address
                    leaf secondary-ip-address {
                        type types-sros:ipv4-unicast-address;
                        description "Secondary IPv4 address of reference location for ORR";
                    }

                    ///nokia-conf/configure/router/bgp/optimal-route-reflection/location/tertiary-ip-address
                    leaf tertiary-ip-address {
                        type types-sros:ipv4-unicast-address;
                        description "Tertiary IPv4 address of the reference location for ORR";
                    }

                    ///nokia-conf/configure/router/bgp/optimal-route-reflection/location/primary-ipv6-address
                    leaf primary-ipv6-address {
                        type types-sros:ipv6-unicast-address;
                        description "Primary IPv6 address of the reference location for ORR";
                    }

                    ///nokia-conf/configure/router/bgp/optimal-route-reflection/location/secondary-ipv6-address
                    leaf secondary-ipv6-address {
                        type types-sros:ipv6-unicast-address;
                        description "Secondary IPv6 address of reference location for ORR";
                    }

                    ///nokia-conf/configure/router/bgp/optimal-route-reflection/location/tertiary-ipv6-address
                    leaf tertiary-ipv6-address {
                        type types-sros:ipv6-unicast-address;
                        description "Tertiary IPv6 address of the reference location for ORR";
                    }

                    ///nokia-conf/configure/router/bgp/optimal-route-reflection/location/apply-groups
                    leaf-list apply-groups {
                        type leafref {
                            path "../../../../../groups/group/name";
                        }
                        max-elements 8;
                        ordered-by user;
                        description "Apply a configuration group at this level";
                    }

                    ///nokia-conf/configure/router/bgp/optimal-route-reflection/location/apply-groups-exclude
                    leaf-list apply-groups-exclude {
                        type leafref {
                            path "../../../../../groups/group/name";
                        }
                        max-elements 8;
                        ordered-by user;
                        description "Exclude a configuration group at this level";
                    }

                } // list location

            } // container optimal-route-reflection

            ///nokia-conf/configure/router/bgp/next-hop-resolution
            container next-hop-resolution {
                description "Enter the next-hop-resolution context";

                ///nokia-conf/configure/router/bgp/next-hop-resolution/use-bgp-routes
                leaf use-bgp-routes {
                    type boolean;
                    default "false";
                    description "Use BGP routes to resolve BGP next hops";
                }

                ///nokia-conf/configure/router/bgp/next-hop-resolution/weighted-ecmp
                leaf weighted-ecmp {
                    type boolean;
                    default "false";
                    description "Use weighted ECMP for next-hop tunnel selection for 6PE";
                }

                ///nokia-conf/configure/router/bgp/next-hop-resolution/allow-unresolved-leaking
                leaf allow-unresolved-leaking {
                    type boolean;
                    default "false";
                    description "Allow unresolved BGP routes to be leaked to VPRN routes";
                }

                ///nokia-conf/configure/router/bgp/next-hop-resolution/policy
                leaf policy {
                    type leafref {
                        path "../../../../policy-options/policy-statement/name";
                    }
                    description "Policy that filters routes for BGP next-hop resolution";
                }

                ///nokia-conf/configure/router/bgp/next-hop-resolution/vpn-family-policy
                leaf vpn-family-policy {
                    type leafref {
                        path "../../../../policy-options/policy-statement/name";
                    }
                    description "Policy to filter routes for next-hop resolution";
                }

                ///nokia-conf/configure/router/bgp/next-hop-resolution/shortcut-tunnel
                container shortcut-tunnel {
                    description "Enter the shortcut-tunnel context";

                    ///nokia-conf/configure/router/bgp/next-hop-resolution/shortcut-tunnel/family
                    list family {
                        key "family-type";
                        description "Enter the family list instance";

                        ///nokia-conf/configure/router/bgp/next-hop-resolution/shortcut-tunnel/family/family-type
                        leaf family-type {
                            type enumeration {
                                enum ipv4                           { value 1; }
                                enum ipv6                           { value 3; }
                            }
                            description "Address family type for shortcut tunnel selection";
                        }

                        ///nokia-conf/configure/router/bgp/next-hop-resolution/shortcut-tunnel/family/resolution
                        leaf resolution {
                            type enumeration {
                                enum none                           { value 0; }
                                enum filter                         { value 1; }
                                enum any                            { value 2; }
                            }
                            default "none";
                            description "Resolution mode for binding BGP routes to tunnel types";
                        }

                        ///nokia-conf/configure/router/bgp/next-hop-resolution/shortcut-tunnel/family/disallow-igp
                        leaf disallow-igp {
                            type boolean;
                            default "false";
                            description "Do not perform route table lookup to resolve BGP route";
                        }

                        ///nokia-conf/configure/router/bgp/next-hop-resolution/shortcut-tunnel/family/enforce-strict-tunnel-tagging
                        leaf enforce-strict-tunnel-tagging {
                            type boolean;
                            default "false";
                            description "Consider only LSPs with an admin-tag for next hop";
                        }

                        ///nokia-conf/configure/router/bgp/next-hop-resolution/shortcut-tunnel/family/allow-flex-algo-fallback
                        leaf allow-flex-algo-fallback {
                            type boolean;
                            default "false";
                            description "Enable flexible algorithm fallback";
                        }

                        ///nokia-conf/configure/router/bgp/next-hop-resolution/shortcut-tunnel/family/apply-groups
                        leaf-list apply-groups {
                            type leafref {
                                path "../../../../../../groups/group/name";
                            }
                            max-elements 8;
                            ordered-by user;
                            description "Apply a configuration group at this level";
                        }

                        ///nokia-conf/configure/router/bgp/next-hop-resolution/shortcut-tunnel/family/apply-groups-exclude
                        leaf-list apply-groups-exclude {
                            type leafref {
                                path "../../../../../../groups/group/name";
                            }
                            max-elements 8;
                            ordered-by user;
                            description "Exclude a configuration group at this level";
                        }

                        ///nokia-conf/configure/router/bgp/next-hop-resolution/shortcut-tunnel/family/resolution-filter
                        container resolution-filter {
                            description "Enter the resolution-filter context";

                            ///nokia-conf/configure/router/bgp/next-hop-resolution/shortcut-tunnel/family/resolution-filter/bgp
                            leaf bgp {
                                type boolean;
                                default "false";
                                description "Use BGP tunneling for next-hop resolution";
                            }

                            ///nokia-conf/configure/router/bgp/next-hop-resolution/shortcut-tunnel/family/resolution-filter/ldp
                            leaf ldp {
                                type boolean;
                                default "false";
                                description "Use LDP tunneling for next-hop resolution";
                            }

                            ///nokia-conf/configure/router/bgp/next-hop-resolution/shortcut-tunnel/family/resolution-filter/rsvp
                            leaf rsvp {
                                type boolean;
                                default "false";
                                description "Use RSVP tunneling for next-hop resolution";
                            }

                            ///nokia-conf/configure/router/bgp/next-hop-resolution/shortcut-tunnel/family/resolution-filter/sr-isis
                            leaf sr-isis {
                                type boolean;
                                default "false";
                                description "Use IS-IS SR tunneling for next-hop resolution";
                            }

                            ///nokia-conf/configure/router/bgp/next-hop-resolution/shortcut-tunnel/family/resolution-filter/sr-ospf
                            leaf sr-ospf {
                                type boolean;
                                default "false";
                                description "Use OSPF SR tunneling for next-hop resolution";
                            }

                            ///nokia-conf/configure/router/bgp/next-hop-resolution/shortcut-tunnel/family/resolution-filter/sr-te
                            leaf sr-te {
                                type boolean;
                                default "false";
                                description "Use SR-TE tunneling for next-hop resolution";
                            }

                            ///nokia-conf/configure/router/bgp/next-hop-resolution/shortcut-tunnel/family/resolution-filter/sr-policy
                            leaf sr-policy {
                                type boolean;
                                default "false";
                                description "Use SR policies for next-hop resolution";
                            }

                            ///nokia-conf/configure/router/bgp/next-hop-resolution/shortcut-tunnel/family/resolution-filter/rib-api
                            leaf rib-api {
                                type boolean;
                                default "false";
                                description "Use RIB API gRPC service for next-hop resolution";
                            }

                            ///nokia-conf/configure/router/bgp/next-hop-resolution/shortcut-tunnel/family/resolution-filter/mpls-fwd-policy
                            leaf mpls-fwd-policy {
                                type boolean;
                                default "false";
                                description "Use MPLS forwarding policy for next-hop resolution";
                            }

                            ///nokia-conf/configure/router/bgp/next-hop-resolution/shortcut-tunnel/family/resolution-filter/sr-ospf3
                            leaf sr-ospf3 {
                                type boolean;
                                default "false";
                                description "Use OSPFv3 SR tunneling for next-hop resolution";
                            }

                        } // container resolution-filter

                    } // list family

                } // container shortcut-tunnel

                ///nokia-conf/configure/router/bgp/next-hop-resolution/labeled-routes
                container labeled-routes {
                    description "Enter the labeled-routes context";

                    ///nokia-conf/configure/router/bgp/next-hop-resolution/labeled-routes/allow-static
                    leaf allow-static {
                        type boolean;
                        default "false";
                        description "Allow static routes to resolve BGP next-hop";
                    }

                    ///nokia-conf/configure/router/bgp/next-hop-resolution/labeled-routes/prefer-transport-frr
                    leaf prefer-transport-frr {
                        type boolean;
                        default "false";
                        description "Enable prefer transport for resolved routes";
                    }

                    ///nokia-conf/configure/router/bgp/next-hop-resolution/labeled-routes/rr-use-route-table
                    leaf rr-use-route-table {
                        type boolean;
                        default "false";
                        description "Use RTM to resolve BGP next-hop if TTM resolution fails";
                    }

                    ///nokia-conf/configure/router/bgp/next-hop-resolution/labeled-routes/use-bgp-routes
                    container use-bgp-routes {
                        description "Enter the use-bgp-routes context";

                        ///nokia-conf/configure/router/bgp/next-hop-resolution/labeled-routes/use-bgp-routes/label-ipv6-explicit-null
                        leaf label-ipv6-explicit-null {
                            type boolean;
                            default "false";
                            description "Use BGP routes to resolve address family routes";
                        }

                    } // container use-bgp-routes

                    ///nokia-conf/configure/router/bgp/next-hop-resolution/labeled-routes/transport-tunnel
                    container transport-tunnel {
                        description "Enter the transport-tunnel context";

                        ///nokia-conf/configure/router/bgp/next-hop-resolution/labeled-routes/transport-tunnel/family
                        list family {
                            key "family-type";
                            description "Enter the family list instance";

                            ///nokia-conf/configure/router/bgp/next-hop-resolution/labeled-routes/transport-tunnel/family/family-type
                            leaf family-type {
                                type enumeration {
                                    enum vpn                            { value 2; }
                                    enum label-ipv4                     { value 17; }
                                    enum label-ipv6                     { value 18; }
                                }
                                description "Address family type for tunnel selection";
                            }

                            ///nokia-conf/configure/router/bgp/next-hop-resolution/labeled-routes/transport-tunnel/family/resolution
                            leaf resolution {
                                type enumeration {
                                    enum none                           { value 0; }
                                    enum filter                         { value 1; }
                                    enum any                            { value 2; }
                                }
                                default "filter";
                                description "Resolution mode for binding BGP routes to tunnel types";
                            }

                            ///nokia-conf/configure/router/bgp/next-hop-resolution/labeled-routes/transport-tunnel/family/enforce-strict-tunnel-tagging
                            leaf enforce-strict-tunnel-tagging {
                                type boolean;
                                default "false";
                                description "Consider only LSPs with an admin-tag for next hop";
                            }

                            ///nokia-conf/configure/router/bgp/next-hop-resolution/labeled-routes/transport-tunnel/family/allow-flex-algo-fallback
                            leaf allow-flex-algo-fallback {
                                type boolean;
                                default "false";
                                description "Enable flexible algorithm fallback";
                            }

                            ///nokia-conf/configure/router/bgp/next-hop-resolution/labeled-routes/transport-tunnel/family/apply-groups
                            leaf-list apply-groups {
                                type leafref {
                                    path "../../../../../../../groups/group/name";
                                }
                                max-elements 8;
                                ordered-by user;
                                description "Apply a configuration group at this level";
                            }

                            ///nokia-conf/configure/router/bgp/next-hop-resolution/labeled-routes/transport-tunnel/family/apply-groups-exclude
                            leaf-list apply-groups-exclude {
                                type leafref {
                                    path "../../../../../../../groups/group/name";
                                }
                                max-elements 8;
                                ordered-by user;
                                description "Exclude a configuration group at this level";
                            }

                            ///nokia-conf/configure/router/bgp/next-hop-resolution/labeled-routes/transport-tunnel/family/resolution-filter
                            container resolution-filter {
                                description "Enter the resolution-filter context";

                                ///nokia-conf/configure/router/bgp/next-hop-resolution/labeled-routes/transport-tunnel/family/resolution-filter/bgp
                                leaf bgp {
                                    type boolean;
                                    description "Use BGP tunneling for next-hop resolution";
                                }

                                ///nokia-conf/configure/router/bgp/next-hop-resolution/labeled-routes/transport-tunnel/family/resolution-filter/ldp
                                leaf ldp {
                                    type boolean;
                                    default "true";
                                    description "Use LDP tunneling for next-hop resolution";
                                }

                                ///nokia-conf/configure/router/bgp/next-hop-resolution/labeled-routes/transport-tunnel/family/resolution-filter/rsvp
                                leaf rsvp {
                                    type boolean;
                                    default "false";
                                    description "Use RSVP tunneling for next-hop resolution";
                                }

                                ///nokia-conf/configure/router/bgp/next-hop-resolution/labeled-routes/transport-tunnel/family/resolution-filter/sr-isis
                                leaf sr-isis {
                                    type boolean;
                                    default "false";
                                    description "Use IS-IS SR tunneling for next-hop resolution";
                                }

                                ///nokia-conf/configure/router/bgp/next-hop-resolution/labeled-routes/transport-tunnel/family/resolution-filter/sr-ospf
                                leaf sr-ospf {
                                    type boolean;
                                    default "false";
                                    description "Use OSPF SR tunneling for next-hop resolution";
                                }

                                ///nokia-conf/configure/router/bgp/next-hop-resolution/labeled-routes/transport-tunnel/family/resolution-filter/sr-te
                                leaf sr-te {
                                    type boolean;
                                    default "false";
                                    description "Use SR-TE tunneling for next-hop resolution";
                                }

                                ///nokia-conf/configure/router/bgp/next-hop-resolution/labeled-routes/transport-tunnel/family/resolution-filter/udp
                                leaf udp {
                                    type boolean;
                                    default "false";
                                    description "Use MPLS over UDP tunneling for next-hop resolution";
                                }

                                ///nokia-conf/configure/router/bgp/next-hop-resolution/labeled-routes/transport-tunnel/family/resolution-filter/sr-policy
                                leaf sr-policy {
                                    type boolean;
                                    default "false";
                                    description "Use SR policies for next-hop resolution";
                                }

                                ///nokia-conf/configure/router/bgp/next-hop-resolution/labeled-routes/transport-tunnel/family/resolution-filter/rib-api
                                leaf rib-api {
                                    type boolean;
                                    default "false";
                                    description "Use RIB API gRPC service for next-hop resolution";
                                }

                                ///nokia-conf/configure/router/bgp/next-hop-resolution/labeled-routes/transport-tunnel/family/resolution-filter/mpls-fwd-policy
                                leaf mpls-fwd-policy {
                                    type boolean;
                                    default "false";
                                    description "Use MPLS forwarding policy for next-hop resolution";
                                }

                                ///nokia-conf/configure/router/bgp/next-hop-resolution/labeled-routes/transport-tunnel/family/resolution-filter/sr-ospf3
                                leaf sr-ospf3 {
                                    type boolean;
                                    default "false";
                                    description "Use OSPFv3 SR tunneling for next-hop resolution";
                                }

                            } // container resolution-filter

                        } // list family

                    } // container transport-tunnel

                } // container labeled-routes

                ///nokia-conf/configure/router/bgp/next-hop-resolution/use-leaked-routes
                container use-leaked-routes {
                    description "Enter the use-leaked-routes context";

                    ///nokia-conf/configure/router/bgp/next-hop-resolution/use-leaked-routes/static
                    leaf static {
                        type boolean;
                        default "false";
                        description "Use leaked static routes to resolve BGP next hop";
                    }

                } // container use-leaked-routes

            } // container next-hop-resolution

            ///nokia-conf/configure/router/bgp/multipath
            container multipath {
                description "Enter the multipath context";

                ///nokia-conf/configure/router/bgp/multipath/max-paths
                leaf max-paths {
                    type types-router:ip-ecmp;
                    default "1";
                    description "Maximum multipaths per prefix";
                }

                ///nokia-conf/configure/router/bgp/multipath/ebgp
                leaf ebgp {
                    type types-router:ip-ecmp;
                    description "Maximum multipaths per prefix for EBGP learned routes";
                }

                ///nokia-conf/configure/router/bgp/multipath/ibgp
                leaf ibgp {
                    type types-router:ip-ecmp;
                    description "Maximum multipaths per prefix for IBGP learned routes";
                }

                ///nokia-conf/configure/router/bgp/multipath/restrict
                leaf restrict {
                    type types-bgp:restrict;
                    default "same-as-path-length";
                    description "AS path restriction for the non-best path";
                }

                ///nokia-conf/configure/router/bgp/multipath/unequal-cost
                leaf unequal-cost {
                    type boolean;
                    default "false";
                    description "Ignore differences in the next-hop cost for multipath";
                }

                ///nokia-conf/configure/router/bgp/multipath/family
                list family {
                    key "family-type";
                    description "Enter the family list instance";

                    ///nokia-conf/configure/router/bgp/multipath/family/family-type
                    leaf family-type {
                        type enumeration {
                            enum ipv4                           { value 1; }
                            enum ipv6                           { value 3; }
                            enum label-ipv4                     { value 17; }
                            enum label-ipv6                     { value 18; }
                        }
                        description "Address family for which multipath selection applies";
                    }

                    ///nokia-conf/configure/router/bgp/multipath/family/max-paths
                    leaf max-paths {
                        type types-router:ip-ecmp;
                        description "Maximum number of multipaths per prefix or NLRI";
                    }

                    ///nokia-conf/configure/router/bgp/multipath/family/ebgp
                    leaf ebgp {
                        type types-router:ip-ecmp;
                        description "Maximum multipaths when best path is EBGP learned route";
                    }

                    ///nokia-conf/configure/router/bgp/multipath/family/ibgp
                    leaf ibgp {
                        type types-router:ip-ecmp;
                        description "Maximum multipaths when best path is IBGP learned route";
                    }

                    ///nokia-conf/configure/router/bgp/multipath/family/restrict
                    leaf restrict {
                        type types-bgp:restrict;
                        default "same-as-path-length";
                        description "AS path restriction for the non-best path";
                    }

                    ///nokia-conf/configure/router/bgp/multipath/family/unequal-cost
                    leaf unequal-cost {
                        type boolean;
                        default "false";
                        description "Ignore differences in the next-hop cost for multipath";
                    }

                    ///nokia-conf/configure/router/bgp/multipath/family/apply-groups
                    leaf-list apply-groups {
                        type leafref {
                            path "../../../../../groups/group/name";
                        }
                        max-elements 8;
                        ordered-by user;
                        description "Apply a configuration group at this level";
                    }

                    ///nokia-conf/configure/router/bgp/multipath/family/apply-groups-exclude
                    leaf-list apply-groups-exclude {
                        type leafref {
                            path "../../../../../groups/group/name";
                        }
                        max-elements 8;
                        ordered-by user;
                        description "Exclude a configuration group at this level";
                    }

                } // list family

            } // container multipath

            ///nokia-conf/configure/router/bgp/route-target-list
            list route-target-list {
                key "community-name";
                description "Add a list entry for route-target-list";

                ///nokia-conf/configure/router/bgp/route-target-list/community-name
                leaf community-name {
                    type types-sros:named-item;
                    description "Route target community name";
                }

            } // list route-target-list

            ///nokia-conf/configure/router/bgp/outbound-route-filtering
            container outbound-route-filtering {
                presence "Enable the outbound-route-filtering context";
                description "Enable the outbound-route-filtering context";

                ///nokia-conf/configure/router/bgp/outbound-route-filtering/extended-community
                container extended-community {
                    presence "Enable the extended-community context";
                    description "Enable the extended-community context";

                    ///nokia-conf/configure/router/bgp/outbound-route-filtering/extended-community/accept-orf
                    leaf accept-orf {
                        type boolean;
                        default "false";
                        description "Negotiate with peer to accept BGP ORF filters";
                    }

                    ///nokia-conf/configure/router/bgp/outbound-route-filtering/extended-community/send-orf
                    container send-orf {
                        presence "Enable the send-orf context";
                        description "Enable the send-orf context";

                        ///nokia-conf/configure/router/bgp/outbound-route-filtering/extended-community/send-orf/route-target
                        list route-target {
                            key "community-name";
                            description "Add a list entry for route-target";

                            ///nokia-conf/configure/router/bgp/outbound-route-filtering/extended-community/send-orf/route-target/community-name
                            leaf community-name {
                                type types-sros:named-item;
                                description "Route target community name";
                            }

                        } // list route-target

                    } // container send-orf

                } // container extended-community

            } // container outbound-route-filtering

            ///nokia-conf/configure/router/bgp/monitor
            container monitor {
                presence "Enable the monitor context";
                description "Enable the monitor context";

                ///nokia-conf/configure/router/bgp/monitor/all-stations
                leaf all-stations {
                    type boolean;
                    default "false";
                    description "Send BMP messages to all configured stations";
                }

                ///nokia-conf/configure/router/bgp/monitor/admin-state
                leaf admin-state {
                    type types-sros:admin-state;
                    default "disable";
                    description "Administrative state of BMP monitoring";
                }

                ///nokia-conf/configure/router/bgp/monitor/apply-groups
                leaf-list apply-groups {
                    type leafref {
                        path "../../../../groups/group/name";
                    }
                    max-elements 8;
                    ordered-by user;
                    description "Apply a configuration group at this level";
                }

                ///nokia-conf/configure/router/bgp/monitor/apply-groups-exclude
                leaf-list apply-groups-exclude {
                    type leafref {
                        path "../../../../groups/group/name";
                    }
                    max-elements 8;
                    ordered-by user;
                    description "Exclude a configuration group at this level";
                }

                ///nokia-conf/configure/router/bgp/monitor/route-monitoring
                container route-monitoring {
                    description "Enter the route-monitoring context";

                    ///nokia-conf/configure/router/bgp/monitor/route-monitoring/pre-policy
                    leaf pre-policy {
                        type boolean;
                        default "false";
                        description "Allow pre-policy route-monitoring messages to be sent";
                    }

                    ///nokia-conf/configure/router/bgp/monitor/route-monitoring/post-policy
                    leaf post-policy {
                        type boolean;
                        default "false";
                        description "Allow post-policy route-monitoring messages to be sent";
                    }

                } // container route-monitoring

                ///nokia-conf/configure/router/bgp/monitor/station
                list station {
                    key "station-name";
                    max-elements 8;
                    description "Add a list entry for station";

                    ///nokia-conf/configure/router/bgp/monitor/station/station-name
                    leaf station-name {
                        type leafref {
                            path "../../../../../bmp/station/name";
                        }
                        description "BMP monitoring station";
                    }

                } // list station

            } // container monitor

            ///nokia-conf/configure/router/bgp/rib-management
            container rib-management {
                description "Enter the rib-management context";

                ///nokia-conf/configure/router/bgp/rib-management/ipv4
                container ipv4 {
                    description "Enter the ipv4 context";

                    ///nokia-conf/configure/router/bgp/rib-management/ipv4/route-table-import
                    container route-table-import {
                        description "Enter the route-table-import context";

                        ///nokia-conf/configure/router/bgp/rib-management/ipv4/route-table-import/policy-name
                        leaf policy-name {
                            type leafref {
                                path "../../../../../../policy-options/policy-statement/name";
                            }
                            description "Name of policy that controls route importation into RIB";
                        }

                        ///nokia-conf/configure/router/bgp/rib-management/ipv4/route-table-import/apply-groups
                        leaf-list apply-groups {
                            type leafref {
                                path "../../../../../../groups/group/name";
                            }
                            max-elements 8;
                            ordered-by user;
                            description "Apply a configuration group at this level";
                        }

                        ///nokia-conf/configure/router/bgp/rib-management/ipv4/route-table-import/apply-groups-exclude
                        leaf-list apply-groups-exclude {
                            type leafref {
                                path "../../../../../../groups/group/name";
                            }
                            max-elements 8;
                            ordered-by user;
                            description "Exclude a configuration group at this level";
                        }

                    } // container route-table-import

                    ///nokia-conf/configure/router/bgp/rib-management/ipv4/leak-import
                    container leak-import {
                        description "Enter the leak-import context";

                        ///nokia-conf/configure/router/bgp/rib-management/ipv4/leak-import/policy
                        leaf-list policy {
                            type union {
                                type types-sros:policy-expr-string;
                                type string;
                            }
                            max-elements 15;
                            ordered-by user;
                            description "Leak import policy name";
                        }

                        ///nokia-conf/configure/router/bgp/rib-management/ipv4/leak-import/apply-groups
                        leaf-list apply-groups {
                            type leafref {
                                path "../../../../../../groups/group/name";
                            }
                            max-elements 8;
                            ordered-by user;
                            description "Apply a configuration group at this level";
                        }

                        ///nokia-conf/configure/router/bgp/rib-management/ipv4/leak-import/apply-groups-exclude
                        leaf-list apply-groups-exclude {
                            type leafref {
                                path "../../../../../../groups/group/name";
                            }
                            max-elements 8;
                            ordered-by user;
                            description "Exclude a configuration group at this level";
                        }

                    } // container leak-import

                } // container ipv4

                ///nokia-conf/configure/router/bgp/rib-management/ipv6
                container ipv6 {
                    description "Enter the ipv6 context";

                    ///nokia-conf/configure/router/bgp/rib-management/ipv6/route-table-import
                    container route-table-import {
                        description "Enter the route-table-import context";

                        ///nokia-conf/configure/router/bgp/rib-management/ipv6/route-table-import/policy-name
                        leaf policy-name {
                            type leafref {
                                path "../../../../../../policy-options/policy-statement/name";
                            }
                            description "Name of policy that controls route importation into RIB";
                        }

                        ///nokia-conf/configure/router/bgp/rib-management/ipv6/route-table-import/apply-groups
                        leaf-list apply-groups {
                            type leafref {
                                path "../../../../../../groups/group/name";
                            }
                            max-elements 8;
                            ordered-by user;
                            description "Apply a configuration group at this level";
                        }

                        ///nokia-conf/configure/router/bgp/rib-management/ipv6/route-table-import/apply-groups-exclude
                        leaf-list apply-groups-exclude {
                            type leafref {
                                path "../../../../../../groups/group/name";
                            }
                            max-elements 8;
                            ordered-by user;
                            description "Exclude a configuration group at this level";
                        }

                    } // container route-table-import

                    ///nokia-conf/configure/router/bgp/rib-management/ipv6/leak-import
                    container leak-import {
                        description "Enable the leak-import context";

                        ///nokia-conf/configure/router/bgp/rib-management/ipv6/leak-import/policy
                        leaf-list policy {
                            type union {
                                type types-sros:policy-expr-string;
                                type string;
                            }
                            max-elements 15;
                            ordered-by user;
                            description "Leak import policy name";
                        }

                        ///nokia-conf/configure/router/bgp/rib-management/ipv6/leak-import/apply-groups
                        leaf-list apply-groups {
                            type leafref {
                                path "../../../../../../groups/group/name";
                            }
                            max-elements 8;
                            ordered-by user;
                            description "Apply a configuration group at this level";
                        }

                        ///nokia-conf/configure/router/bgp/rib-management/ipv6/leak-import/apply-groups-exclude
                        leaf-list apply-groups-exclude {
                            type leafref {
                                path "../../../../../../groups/group/name";
                            }
                            max-elements 8;
                            ordered-by user;
                            description "Exclude a configuration group at this level";
                        }

                    } // container leak-import

                } // container ipv6

                ///nokia-conf/configure/router/bgp/rib-management/label-ipv4
                container label-ipv4 {
                    description "Enter the label-ipv4 context";

                    ///nokia-conf/configure/router/bgp/rib-management/label-ipv4/route-table-import
                    container route-table-import {
                        description "Enter the route-table-import context";

                        ///nokia-conf/configure/router/bgp/rib-management/label-ipv4/route-table-import/policy-name
                        leaf policy-name {
                            type leafref {
                                path "../../../../../../policy-options/policy-statement/name";
                            }
                            description "Name of policy that controls route importation into RIB";
                        }

                        ///nokia-conf/configure/router/bgp/rib-management/label-ipv4/route-table-import/apply-groups
                        leaf-list apply-groups {
                            type leafref {
                                path "../../../../../../groups/group/name";
                            }
                            max-elements 8;
                            ordered-by user;
                            description "Apply a configuration group at this level";
                        }

                        ///nokia-conf/configure/router/bgp/rib-management/label-ipv4/route-table-import/apply-groups-exclude
                        leaf-list apply-groups-exclude {
                            type leafref {
                                path "../../../../../../groups/group/name";
                            }
                            max-elements 8;
                            ordered-by user;
                            description "Exclude a configuration group at this level";
                        }

                    } // container route-table-import

                    ///nokia-conf/configure/router/bgp/rib-management/label-ipv4/leak-import
                    container leak-import {
                        description "Enable the leak-import context";

                        ///nokia-conf/configure/router/bgp/rib-management/label-ipv4/leak-import/policy
                        leaf-list policy {
                            type union {
                                type types-sros:policy-expr-string;
                                type string;
                            }
                            max-elements 15;
                            ordered-by user;
                            description "Leak import policy name";
                        }

                        ///nokia-conf/configure/router/bgp/rib-management/label-ipv4/leak-import/apply-groups
                        leaf-list apply-groups {
                            type leafref {
                                path "../../../../../../groups/group/name";
                            }
                            max-elements 8;
                            ordered-by user;
                            description "Apply a configuration group at this level";
                        }

                        ///nokia-conf/configure/router/bgp/rib-management/label-ipv4/leak-import/apply-groups-exclude
                        leaf-list apply-groups-exclude {
                            type leafref {
                                path "../../../../../../groups/group/name";
                            }
                            max-elements 8;
                            ordered-by user;
                            description "Exclude a configuration group at this level";
                        }

                    } // container leak-import

                } // container label-ipv4

                ///nokia-conf/configure/router/bgp/rib-management/label-ipv6
                container label-ipv6 {
                    description "Enter the label-ipv6 context";

                    ///nokia-conf/configure/router/bgp/rib-management/label-ipv6/route-table-import
                    container route-table-import {
                        description "Enter the route-table-import context";

                        ///nokia-conf/configure/router/bgp/rib-management/label-ipv6/route-table-import/policy-name
                        leaf policy-name {
                            type leafref {
                                path "../../../../../../policy-options/policy-statement/name";
                            }
                            description "Name of policy that controls route importation into RIB";
                        }

                        ///nokia-conf/configure/router/bgp/rib-management/label-ipv6/route-table-import/apply-groups
                        leaf-list apply-groups {
                            type leafref {
                                path "../../../../../../groups/group/name";
                            }
                            max-elements 8;
                            ordered-by user;
                            description "Apply a configuration group at this level";
                        }

                        ///nokia-conf/configure/router/bgp/rib-management/label-ipv6/route-table-import/apply-groups-exclude
                        leaf-list apply-groups-exclude {
                            type leafref {
                                path "../../../../../../groups/group/name";
                            }
                            max-elements 8;
                            ordered-by user;
                            description "Exclude a configuration group at this level";
                        }

                    } // container route-table-import

                } // container label-ipv6

            } // container rib-management

            ///nokia-conf/configure/router/bgp/segment-routing
            container segment-routing {
                description "Enable the segment-routing context";

                ///nokia-conf/configure/router/bgp/segment-routing/admin-state
                leaf admin-state {
                    type types-sros:admin-state;
                    default "disable";
                    description "Administrative state of segment routing";
                }

                ///nokia-conf/configure/router/bgp/segment-routing/apply-groups
                leaf-list apply-groups {
                    type leafref {
                        path "../../../../groups/group/name";
                    }
                    max-elements 8;
                    ordered-by user;
                    description "Apply a configuration group at this level";
                }

                ///nokia-conf/configure/router/bgp/segment-routing/apply-groups-exclude
                leaf-list apply-groups-exclude {
                    type leafref {
                        path "../../../../groups/group/name";
                    }
                    max-elements 8;
                    ordered-by user;
                    description "Exclude a configuration group at this level";
                }

                ///nokia-conf/configure/router/bgp/segment-routing/prefix-sid-range
                container prefix-sid-range {
                    presence "Enable the prefix-sid-range context";
                    description "Enable the prefix-sid-range context";

                    ///nokia-conf/configure/router/bgp/segment-routing/prefix-sid-range/type
                    choice type {
                        ///nokia-conf/configure/router/bgp/segment-routing/prefix-sid-range/type/global
                        case global {

                            ///nokia-conf/configure/router/bgp/segment-routing/prefix-sid-range/type/global/global
                            leaf global {
                                type empty;
                                description "Allow label allocation from entire SRBG space";
                            }

                        }
                        ///nokia-conf/configure/router/bgp/segment-routing/prefix-sid-range/type/local
                        case local {

                            ///nokia-conf/configure/router/bgp/segment-routing/prefix-sid-range/type/local/start-label
                            leaf start-label {
                                type uint32 {
                                    range "0..524287";
                                }
                                sros-ext:auto-restart-to-modify;
                                default "0";
                                description "First label value available in a contiguous range";
                            }

                            ///nokia-conf/configure/router/bgp/segment-routing/prefix-sid-range/type/local/max-index
                            leaf max-index {
                                type uint32 {
                                    range "0..524287";
                                }
                                sros-ext:auto-restart-to-modify;
                                default "1";
                                description "Last label value available in contiguous range";
                            }

                        }
                    }
                } // container prefix-sid-range

            } // container segment-routing

            ///nokia-conf/configure/router/bgp/egress-peer-engineering
            container egress-peer-engineering {
                presence "Enable the egress-peer-engineering context";
                description "Enable the egress-peer-engineering context";

                ///nokia-conf/configure/router/bgp/egress-peer-engineering/admin-state
                leaf admin-state {
                    type types-sros:admin-state;
                    default "disable";
                    description "Administrative state of BGP egress engineering";
                }

                ///nokia-conf/configure/router/bgp/egress-peer-engineering/apply-groups
                leaf-list apply-groups {
                    type leafref {
                        path "../../../../groups/group/name";
                    }
                    max-elements 8;
                    ordered-by user;
                    description "Apply a configuration group at this level";
                }

                ///nokia-conf/configure/router/bgp/egress-peer-engineering/apply-groups-exclude
                leaf-list apply-groups-exclude {
                    type leafref {
                        path "../../../../groups/group/name";
                    }
                    max-elements 8;
                    ordered-by user;
                    description "Exclude a configuration group at this level";
                }

            } // container egress-peer-engineering

            ///nokia-conf/configure/router/bgp/group
            list group {
                key "group-name";
                description "Enter the group list instance";

                ///nokia-conf/configure/router/bgp/group/group-name
                leaf group-name {
                    type types-sros:named-item-64;
                    description "BGP peer group name";
                }

                ///nokia-conf/configure/router/bgp/group/description
                leaf description {
                    type types-sros:description;
                    description "Text description";
                }

                ///nokia-conf/configure/router/bgp/group/connect-retry
                leaf connect-retry {
                    type int32 {
                        range "1..65535";
                    }
                    description "BGP connect retry timer value";
                }

                ///nokia-conf/configure/router/bgp/group/admin-state
                leaf admin-state {
                    type types-sros:admin-state;
                    default "enable";
                    description "Administrative state of the BGP group";
                }

                ///nokia-conf/configure/router/bgp/group/static-group
                leaf static-group {
                    type boolean;
                    default "true";
                    description "Use group for static peers";
                }

                ///nokia-conf/configure/router/bgp/group/keepalive
                leaf keepalive {
                    type int32 {
                        range "0..21845";
                    }
                    description "Time after which the BGP KEEPALIVE message is sent";
                }

                ///nokia-conf/configure/router/bgp/group/damping
                leaf damping {
                    type boolean;
                    description "Use BGP route damping to reduce route flap";
                }

                ///nokia-conf/configure/router/bgp/group/local-preference
                leaf local-preference {
                    type int64 {
                        range "0..4294967295";
                    }
                    description "Default local preference if not in incoming routes";
                }

                ///nokia-conf/configure/router/bgp/group/loop-detect
                leaf loop-detect {
                    type types-bgp:loop-detect;
                    description "Strategy for loop detection in the AS path";
                }

                ///nokia-conf/configure/router/bgp/group/loop-detect-threshold
                leaf loop-detect-threshold {
                    type uint32 {
                        range "0..15";
                    }
                    description "Threshold for the global ASN in a received AS path";
                }

                ///nokia-conf/configure/router/bgp/group/tcp-mss
                leaf tcp-mss {
                    type union {
                        type uint32 {
                            range "384..9746";
                        }
                        type enumeration {
                            enum ip-stack                       { value 0; }
                        }
                    }
                    description "TCP maximum segment size override";
                }

                ///nokia-conf/configure/router/bgp/group/selective-label-ipv4-install
                leaf selective-label-ipv4-install {
                    type boolean;
                    description "Enable selective download for bgp label-ipv4 routes";
                }

                ///nokia-conf/configure/router/bgp/group/min-route-advertisement
                leaf min-route-advertisement {
                    type int16 {
                        range "1..255";
                    }
                    description "Minimum time before a prefix can be advertised to peer";
                }

                ///nokia-conf/configure/router/bgp/group/aggregator-id-zero
                leaf aggregator-id-zero {
                    type boolean;
                    description "Set router ID in the BGP AGGREGATOR attribute to zero";
                }

                ///nokia-conf/configure/router/bgp/group/preference
                leaf preference {
                    type uint32 {
                        range "1..255";
                    }
                    description "Route preference for routes learned from all peers";
                }

                ///nokia-conf/configure/router/bgp/group/block-prefix-sid
                leaf block-prefix-sid {
                    type boolean;
                    default "false";
                    description "Block the prefix SID attribute";
                }

                ///nokia-conf/configure/router/bgp/group/multihop
                leaf multihop {
                    type int32 {
                        range "1..255";
                    }
                    description "TTL in IP packet headers for EBGP peers multi-hops away";
                }

                ///nokia-conf/configure/router/bgp/group/med-out
                leaf med-out {
                    type union {
                        type uint32;
                        type enumeration {
                            enum igp-cost                       { value -1; }
                        }
                    }
                    description "Default MED attribute value to advertise to peers";
                }

                ///nokia-conf/configure/router/bgp/group/authentication-key
                leaf authentication-key {
                    type types-sros:encrypted-leaf {
                        length "1..370";
                    }
                    description "BGP authentication key for peers in the group";
                }

                ///nokia-conf/configure/router/bgp/group/client-reflect
                leaf client-reflect {
                    type boolean;
                    description "Allow cluster RR to advertise routes to its clients";
                }

                ///nokia-conf/configure/router/bgp/group/vpn-apply-export
                leaf vpn-apply-export {
                    type boolean;
                    description "Apply base-instance BGP export policies to VPN routes";
                }

                ///nokia-conf/configure/router/bgp/group/vpn-apply-import
                leaf vpn-apply-import {
                    type boolean;
                    description "Apply base-instance BGP import policies to VPN routes";
                }

                ///nokia-conf/configure/router/bgp/group/as-override
                leaf as-override {
                    type boolean;
                    default "false";
                    description "Replace the peer ASN with the local ASN in AS Path";
                }

                ///nokia-conf/configure/router/bgp/group/asn-4-byte
                leaf asn-4-byte {
                    type boolean;
                    description "Advertise the use of 4-byte ASNs";
                }

                ///nokia-conf/configure/router/bgp/group/path-mtu-discovery
                leaf path-mtu-discovery {
                    type boolean;
                    description "Enable Path MTU Discovery";
                }

                ///nokia-conf/configure/router/bgp/group/next-hop-self
                leaf next-hop-self {
                    type boolean;
                    default "false";
                    description "Advertise routes with local address as next-hop address";
                }

                ///nokia-conf/configure/router/bgp/group/passive
                leaf passive {
                    type boolean;
                    default "false";
                    description "Enable passive mode for BGP communication";
                }

                ///nokia-conf/configure/router/bgp/group/type
                leaf type {
                    type types-bgp:peer-type;
                    default "no-type";
                    description "BGP peer type";
                }

                ///nokia-conf/configure/router/bgp/group/peer-as
                leaf peer-as {
                    type uint32 {
                        range "1..4294967295";
                    }
                    description "Peer AS number";
                }

                ///nokia-conf/configure/router/bgp/group/capability-negotiation
                leaf capability-negotiation {
                    type boolean;
                    default "true";
                    description "Enable capability negotiation";
                }

                ///nokia-conf/configure/router/bgp/group/enforce-first-as
                leaf enforce-first-as {
                    type boolean;
                    description "Enforce the configured peer AS value in received routes";
                }

                ///nokia-conf/configure/router/bgp/group/initial-send-delay-zero
                leaf initial-send-delay-zero {
                    type boolean;
                    description "Send BGP updates as soon as the session comes up";
                }

                ///nokia-conf/configure/router/bgp/group/local-address
                leaf local-address {
                    type types-bgp:local-address;
                    description "Local IP address used when communicating with BGP peers";
                }

                ///nokia-conf/configure/router/bgp/group/ttl-security
                leaf ttl-security {
                    type uint32 {
                        range "1..255";
                    }
                    description "Minimum TTL value for an incoming BGP packet";
                }

                ///nokia-conf/configure/router/bgp/group/default-route-target
                leaf default-route-target {
                    type boolean;
                    default "false";
                    description "Send default RTC route (zero prefix length) to peers";
                }

                ///nokia-conf/configure/router/bgp/group/aigp
                leaf aigp {
                    type boolean;
                    default "false";
                    description "Add AIGP attribute to advertised routes";
                }

                ///nokia-conf/configure/router/bgp/group/advertise-inactive
                leaf advertise-inactive {
                    type boolean;
                    description "Advertise an inactive BGP route to peers";
                }

                ///nokia-conf/configure/router/bgp/group/authentication-keychain
                leaf authentication-keychain {
                    type leafref {
                        path "../../../../system/security/keychains/keychain/keychain-name";
                    }
                    description "TCP authentication keychain for the session";
                }

                ///nokia-conf/configure/router/bgp/group/bfd-liveness
                leaf bfd-liveness {
                    type boolean;
                    description "Enable BFD";
                }

                ///nokia-conf/configure/router/bgp/group/fast-external-failover
                leaf fast-external-failover {
                    type boolean;
                    description "Drop external BGP session immediately when link fails";
                }

                ///nokia-conf/configure/router/bgp/group/peer-ip-tracking
                leaf peer-ip-tracking {
                    type boolean;
                    description "Enable BGP peer tracking";
                }

                ///nokia-conf/configure/router/bgp/group/dynamic-neighbor-limit
                leaf dynamic-neighbor-limit {
                    type uint32 {
                        range "1..8192";
                    }
                    description "Maximum dynamic BGP sessions to accept from remote peer";
                }

                ///nokia-conf/configure/router/bgp/group/split-horizon
                leaf split-horizon {
                    type boolean;
                    description "Prevent routes being reflected back to best-route peer";
                }

                ///nokia-conf/configure/router/bgp/group/third-party-nexthop
                leaf third-party-nexthop {
                    type boolean;
                    description "Apply third-party next-hop processing to EBGP peers";
                }

                ///nokia-conf/configure/router/bgp/group/label-preference
                leaf label-preference {
                    type uint32 {
                        range "1..255";
                    }
                    description "Route preference for routes from labeled-unicast peers";
                }

                ///nokia-conf/configure/router/bgp/group/def-recv-evpn-encap
                leaf def-recv-evpn-encap {
                    type types-bgp:encap;
                    description "Default EVPN encapsulation type";
                }

                ///nokia-conf/configure/router/bgp/group/multipath-eligible
                leaf multipath-eligible {
                    type boolean;
                    default "false";
                    description "Allow routes from group peers in multipath eligibility";
                }

                ///nokia-conf/configure/router/bgp/group/egress-peer-engineering-label-unicast
                leaf egress-peer-engineering-label-unicast {
                    type boolean;
                    default "false";
                    description "Generate EPE label-unicast routes for group";
                }

                ///nokia-conf/configure/router/bgp/group/apply-groups
                leaf-list apply-groups {
                    type leafref {
                        path "../../../../groups/group/name";
                    }
                    max-elements 8;
                    ordered-by user;
                    description "Apply a configuration group at this level";
                }

                ///nokia-conf/configure/router/bgp/group/apply-groups-exclude
                leaf-list apply-groups-exclude {
                    type leafref {
                        path "../../../../groups/group/name";
                    }
                    max-elements 8;
                    ordered-by user;
                    description "Exclude a configuration group at this level";
                }

                ///nokia-conf/configure/router/bgp/group/hold-time
                container hold-time {
                    description "Enter the hold-time context";

                    ///nokia-conf/configure/router/bgp/group/hold-time/seconds
                    leaf seconds {
                        type int32 {
                            range "0|3..65535";
                        }
                        description "Maximum time BGP waits between successive messages";
                    }

                    ///nokia-conf/configure/router/bgp/group/hold-time/minimum-hold-time
                    leaf minimum-hold-time {
                        type int32 {
                            range "0|3..65536";
                        }
                        default "0";
                        description "Minimum hold time between successive messages";
                    }

                } // container hold-time

                ///nokia-conf/configure/router/bgp/group/family
                container family {
                    presence "Enable the family context";
                    description "Enable the family context";

                    ///nokia-conf/configure/router/bgp/group/family/ipv4
                    leaf ipv4 {
                        type boolean;
                        default "false";
                        description "Add support for the IPv4 address family";
                    }

                    ///nokia-conf/configure/router/bgp/group/family/vpn-ipv4
                    leaf vpn-ipv4 {
                        type boolean;
                        default "false";
                        description "Advertise MP-BGP support for IPv4 VPN address family";
                    }

                    ///nokia-conf/configure/router/bgp/group/family/ipv6
                    leaf ipv6 {
                        type boolean;
                        default "false";
                        description "Advertise MP-BGP support for the IPv6 address family";
                    }

                    ///nokia-conf/configure/router/bgp/group/family/mcast-ipv4
                    leaf mcast-ipv4 {
                        type boolean;
                        default "false";
                        description "Advertise support for the MCAST-IPv4 address family";
                    }

                    ///nokia-conf/configure/router/bgp/group/family/vpn-ipv6
                    leaf vpn-ipv6 {
                        type boolean;
                        default "false";
                        description "Advertise MP-BGP support for IPv6 VPN address family";
                    }

                    ///nokia-conf/configure/router/bgp/group/family/l2-vpn
                    leaf l2-vpn {
                        type boolean;
                        default "false";
                        description "Advertise MP-BGP support for the L2-VPN address family";
                    }

                    ///nokia-conf/configure/router/bgp/group/family/mvpn-ipv4
                    leaf mvpn-ipv4 {
                        type boolean;
                        default "false";
                        description "Advertise support for the IPv4 MCAST VPN address family";
                    }

                    ///nokia-conf/configure/router/bgp/group/family/mdt-safi
                    leaf mdt-safi {
                        type boolean;
                        default "false";
                        description "Advertise MP-BGP support for MDT-SAFI address family";
                    }

                    ///nokia-conf/configure/router/bgp/group/family/ms-pw
                    leaf ms-pw {
                        type boolean;
                        default "false";
                        description "Advertise support for multi-segment PW address family";
                    }

                    ///nokia-conf/configure/router/bgp/group/family/flow-ipv4
                    leaf flow-ipv4 {
                        type boolean;
                        default "false";
                        description "Advertise support for the flowspec-IPv4 address family";
                    }

                    ///nokia-conf/configure/router/bgp/group/family/route-target
                    leaf route-target {
                        type boolean;
                        default "false";
                        description "Advertise MP-BGP support for RT constraint routes";
                    }

                    ///nokia-conf/configure/router/bgp/group/family/mcast-vpn-ipv4
                    leaf mcast-vpn-ipv4 {
                        type boolean;
                        default "false";
                        description "Advertise support for the IPv4 VPN MCAST address family";
                    }

                    ///nokia-conf/configure/router/bgp/group/family/mvpn-ipv6
                    leaf mvpn-ipv6 {
                        type boolean;
                        default "false";
                        description "Advertise support for the IPv6 MCAST VPN address family";
                    }

                    ///nokia-conf/configure/router/bgp/group/family/flow-ipv6
                    leaf flow-ipv6 {
                        type boolean;
                        default "false";
                        description "Advertise support for the flowspec-IPv6 address family";
                    }

                    ///nokia-conf/configure/router/bgp/group/family/evpn
                    leaf evpn {
                        type boolean;
                        default "false";
                        description "Advertise MP-BGP support for the EVPN address family";
                    }

                    ///nokia-conf/configure/router/bgp/group/family/mcast-ipv6
                    leaf mcast-ipv6 {
                        type boolean;
                        default "false";
                        description "Advertise support for the MCAST-IPv6 address family";
                    }

                    ///nokia-conf/configure/router/bgp/group/family/label-ipv4
                    leaf label-ipv4 {
                        type boolean;
                        default "false";
                        description "Advertise support for the label-IPv4 address family";
                    }

                    ///nokia-conf/configure/router/bgp/group/family/label-ipv6
                    leaf label-ipv6 {
                        type boolean;
                        default "false";
                        description "Advertise support for the label-IPv6 address family";
                    }

                    ///nokia-conf/configure/router/bgp/group/family/bgp-ls
                    leaf bgp-ls {
                        type boolean;
                        default "false";
                        description "Advertise MP-BGP support for the BGP-LS address family";
                    }

                    ///nokia-conf/configure/router/bgp/group/family/mcast-vpn-ipv6
                    leaf mcast-vpn-ipv6 {
                        type boolean;
                        default "false";
                        description "Advertise support for the IPv6 VPN MCAST address family";
                    }

                    ///nokia-conf/configure/router/bgp/group/family/sr-policy-ipv4
                    leaf sr-policy-ipv4 {
                        type boolean;
                        default "false";
                        description "Advertise MP-BGP support for the SR-policy-IPv4 family";
                    }

                    ///nokia-conf/configure/router/bgp/group/family/sr-policy-ipv6
                    leaf sr-policy-ipv6 {
                        type boolean;
                        default "false";
                        description "Advertise MP-BGP support for the SR-policy-IPv6 family";
                    }

                    ///nokia-conf/configure/router/bgp/group/family/flow-vpn-ipv4
                    leaf flow-vpn-ipv4 {
                        type boolean;
                        default "false";
                        description "Advertise support for FlowSpec-VPN IPv4 address family";
                    }

                    ///nokia-conf/configure/router/bgp/group/family/flow-vpn-ipv6
                    leaf flow-vpn-ipv6 {
                        type boolean;
                        default "false";
                        description "Advertise support for FlowSpec-VPN IPv6 address family";
                    }

                } // container family

                ///nokia-conf/configure/router/bgp/group/send-default
                container send-default {
                    presence "Enable the send-default context";
                    description "Enable the send-default context";

                    ///nokia-conf/configure/router/bgp/group/send-default/ipv4
                    leaf ipv4 {
                        type boolean;
                        default "false";
                        description "Generate and advertise an IPv4 default route (0/0)";
                    }

                    ///nokia-conf/configure/router/bgp/group/send-default/ipv6
                    leaf ipv6 {
                        type boolean;
                        default "false";
                        description "Generate and advertise an IPv6 default route (::/0)";
                    }

                    ///nokia-conf/configure/router/bgp/group/send-default/export-policy
                    leaf export-policy {
                        type leafref {
                            path "../../../../../policy-options/policy-statement/name";
                        }
                        description "Export policy name";
                    }

                } // container send-default

                ///nokia-conf/configure/router/bgp/group/default-preference
                container default-preference {
                    description "Enter the default-preference context";

                    ///nokia-conf/configure/router/bgp/group/default-preference/ebgp
                    leaf ebgp {
                        type uint32 {
                            range "0..255";
                        }
                        description "Default preference for EBGP";
                    }

                    ///nokia-conf/configure/router/bgp/group/default-preference/ibgp
                    leaf ibgp {
                        type uint32 {
                            range "0..255";
                        }
                        description "Default preference for IBGP";
                    }

                } // container default-preference

                ///nokia-conf/configure/router/bgp/group/default-label-preference
                container default-label-preference {
                    description "Enter the default-label-preference context";

                    ///nokia-conf/configure/router/bgp/group/default-label-preference/ebgp
                    leaf ebgp {
                        type uint32 {
                            range "0..255";
                        }
                        description "Default preference for EBGP";
                    }

                    ///nokia-conf/configure/router/bgp/group/default-label-preference/ibgp
                    leaf ibgp {
                        type uint32 {
                            range "0..255";
                        }
                        description "Default preference for IBGP";
                    }

                } // container default-label-preference

                ///nokia-conf/configure/router/bgp/group/remove-private
                container remove-private {
                    presence "Enable the remove-private context";
                    description "Enable the remove-private context";

                    ///nokia-conf/configure/router/bgp/group/remove-private/limited
                    leaf limited {
                        type boolean;
                        default "false";
                        description "Remove private ASNs up to first public ASN encountered";
                    }

                    ///nokia-conf/configure/router/bgp/group/remove-private/skip-peer-as
                    leaf skip-peer-as {
                        type boolean;
                        default "false";
                        description "Keep private ASN if it is the same as the BGP peer ASN";
                    }

                    ///nokia-conf/configure/router/bgp/group/remove-private/replace
                    leaf replace {
                        type boolean;
                        default "false";
                        description "Replace private ASN with global ASN before advertising";
                    }

                } // container remove-private

                ///nokia-conf/configure/router/bgp/group/cluster
                container cluster {
                    description "Enter the cluster context";

                    ///nokia-conf/configure/router/bgp/group/cluster/cluster-id
                    leaf cluster-id {
                        type types-sros:ipv4-address;
                        description "Route reflector cluster ID";
                    }

                    ///nokia-conf/configure/router/bgp/group/cluster/orr-location
                    leaf orr-location {
                        type uint32 {
                            range "1..255";
                        }
                        description "Optimal route reflection location for the cluster";
                    }

                    ///nokia-conf/configure/router/bgp/group/cluster/allow-local-fallback
                    leaf allow-local-fallback {
                        type boolean;
                        default "false";
                        description "Allow fallback to RR topology location";
                    }

                } // container cluster

                ///nokia-conf/configure/router/bgp/group/ebgp-default-reject-policy
                container ebgp-default-reject-policy {
                    presence "Enable the ebgp-default-reject-policy context";
                    description "Enable the ebgp-default-reject-policy context";

                    ///nokia-conf/configure/router/bgp/group/ebgp-default-reject-policy/import
                    leaf import {
                        type boolean;
                        default "true";
                        description "Enable default reject import policy for external peers";
                    }

                    ///nokia-conf/configure/router/bgp/group/ebgp-default-reject-policy/export
                    leaf export {
                        type boolean;
                        default "true";
                        description "Enable default reject export policy for external peers";
                    }

                } // container ebgp-default-reject-policy

                ///nokia-conf/configure/router/bgp/group/local-as
                container local-as {
                    description "Enter the local-as context";

                    ///nokia-conf/configure/router/bgp/group/local-as/as-number
                    leaf as-number {
                        type uint32 {
                            range "1..4294967295";
                        }
                        description "Local (or virtual) BGP AS number";
                    }

                    ///nokia-conf/configure/router/bgp/group/local-as/private
                    leaf private {
                        type boolean;
                        default "false";
                        description "Hide the local ASN in sent paths learned from peering";
                    }

                    ///nokia-conf/configure/router/bgp/group/local-as/prepend-global-as
                    leaf prepend-global-as {
                        type boolean;
                        default "true";
                        description "Prepend global ASN when advertising routes to BGP peer";
                    }

                } // container local-as

                ///nokia-conf/configure/router/bgp/group/next-hop-unchanged
                container next-hop-unchanged {
                    description "Enter the next-hop-unchanged context";

                    ///nokia-conf/configure/router/bgp/group/next-hop-unchanged/label-ipv4
                    leaf label-ipv4 {
                        type boolean;
                        default "false";
                        description "Advertise label-IPv4 routes with unchanged BGP next hop";
                    }

                    ///nokia-conf/configure/router/bgp/group/next-hop-unchanged/label-ipv6
                    leaf label-ipv6 {
                        type boolean;
                        default "false";
                        description "Advertise label-IPv6 routes with unchanged BGP next hop";
                    }

                    ///nokia-conf/configure/router/bgp/group/next-hop-unchanged/vpn-ipv4
                    leaf vpn-ipv4 {
                        type boolean;
                        default "false";
                        description "Advertise VPN IPv4 routes with unchanged BGP next hop";
                    }

                    ///nokia-conf/configure/router/bgp/group/next-hop-unchanged/vpn-ipv6
                    leaf vpn-ipv6 {
                        type boolean;
                        default "false";
                        description "Advertise VPN IPv6 routes with unchanged BGP next hop";
                    }

                    ///nokia-conf/configure/router/bgp/group/next-hop-unchanged/evpn
                    leaf evpn {
                        type boolean;
                        default "false";
                        description "Advertise EVPN routes with unchanged BGP next hop";
                    }

                } // container next-hop-unchanged

                ///nokia-conf/configure/router/bgp/group/origin-validation
                container origin-validation {
                    description "Enter the origin-validation context";

                    ///nokia-conf/configure/router/bgp/group/origin-validation/ipv4
                    leaf ipv4 {
                        type boolean;
                        default "false";
                        description "Enable support for unlabeled unicast IPv4 routes";
                    }

                    ///nokia-conf/configure/router/bgp/group/origin-validation/ipv6
                    leaf ipv6 {
                        type boolean;
                        default "false";
                        description "Enable support for unlabeled unicast IPv6 routes";
                    }

                    ///nokia-conf/configure/router/bgp/group/origin-validation/label-ipv4
                    leaf label-ipv4 {
                        type boolean;
                        default "false";
                        description "Enable support for labeled-unicast IPv4 routes";
                    }

                    ///nokia-conf/configure/router/bgp/group/origin-validation/label-ipv6
                    leaf label-ipv6 {
                        type boolean;
                        default "false";
                        description "Enable support for labeled-unicast IPv6 routes";
                    }

                } // container origin-validation

                ///nokia-conf/configure/router/bgp/group/link-bandwidth
                container link-bandwidth {
                    description "Enter the link-bandwidth context";

                    ///nokia-conf/configure/router/bgp/group/link-bandwidth/accept-from-ebgp
                    container accept-from-ebgp {
                        description "Enter the accept-from-ebgp context";

                        ///nokia-conf/configure/router/bgp/group/link-bandwidth/accept-from-ebgp/ipv4
                        leaf ipv4 {
                            type boolean;
                            default "false";
                            description "Support Link Bandwidth EC in IPv4 routes";
                        }

                        ///nokia-conf/configure/router/bgp/group/link-bandwidth/accept-from-ebgp/ipv6
                        leaf ipv6 {
                            type boolean;
                            default "false";
                            description "Support Link Bandwidth EC in IPv6 routes";
                        }

                        ///nokia-conf/configure/router/bgp/group/link-bandwidth/accept-from-ebgp/vpn-ipv4
                        leaf vpn-ipv4 {
                            type boolean;
                            default "false";
                            description "Support Link Bandwidth EC in VPN-IPv4 routes";
                        }

                        ///nokia-conf/configure/router/bgp/group/link-bandwidth/accept-from-ebgp/vpn-ipv6
                        leaf vpn-ipv6 {
                            type boolean;
                            default "false";
                            description "Support Link Bandwidth EC in VPN-IPv6 routes";
                        }

                        ///nokia-conf/configure/router/bgp/group/link-bandwidth/accept-from-ebgp/label-ipv4
                        leaf label-ipv4 {
                            type boolean;
                            default "false";
                            description "Support Link Bandwidth EC in label-IPv4 routes";
                        }

                        ///nokia-conf/configure/router/bgp/group/link-bandwidth/accept-from-ebgp/label-ipv6
                        leaf label-ipv6 {
                            type boolean;
                            default "false";
                            description "Support Link Bandwidth EC in label-IPv6 routes";
                        }

                    } // container accept-from-ebgp

                    ///nokia-conf/configure/router/bgp/group/link-bandwidth/add-to-received-ebgp
                    container add-to-received-ebgp {
                        description "Enter the add-to-received-ebgp context";

                        ///nokia-conf/configure/router/bgp/group/link-bandwidth/add-to-received-ebgp/ipv4
                        leaf ipv4 {
                            type boolean;
                            default "false";
                            description "Support Link Bandwidth EC in IPv4 routes";
                        }

                        ///nokia-conf/configure/router/bgp/group/link-bandwidth/add-to-received-ebgp/ipv6
                        leaf ipv6 {
                            type boolean;
                            default "false";
                            description "Support Link Bandwidth EC in IPv6 routes";
                        }

                        ///nokia-conf/configure/router/bgp/group/link-bandwidth/add-to-received-ebgp/vpn-ipv4
                        leaf vpn-ipv4 {
                            type boolean;
                            default "false";
                            description "Support Link Bandwidth EC in VPN-IPv4 routes";
                        }

                        ///nokia-conf/configure/router/bgp/group/link-bandwidth/add-to-received-ebgp/vpn-ipv6
                        leaf vpn-ipv6 {
                            type boolean;
                            default "false";
                            description "Support Link Bandwidth EC in VPN-IPv6 routes";
                        }

                        ///nokia-conf/configure/router/bgp/group/link-bandwidth/add-to-received-ebgp/label-ipv4
                        leaf label-ipv4 {
                            type boolean;
                            default "false";
                            description "Support Link Bandwidth EC in label-IPv4 routes";
                        }

                        ///nokia-conf/configure/router/bgp/group/link-bandwidth/add-to-received-ebgp/label-ipv6
                        leaf label-ipv6 {
                            type boolean;
                            default "false";
                            description "Support Link Bandwidth EC in label-IPv6 routes";
                        }

                    } // container add-to-received-ebgp

                    ///nokia-conf/configure/router/bgp/group/link-bandwidth/aggregate-used-paths
                    container aggregate-used-paths {
                        description "Enter the aggregate-used-paths context";

                        ///nokia-conf/configure/router/bgp/group/link-bandwidth/aggregate-used-paths/ipv4
                        leaf ipv4 {
                            type boolean;
                            default "false";
                            description "Support Link Bandwidth EC in IPv4 routes";
                        }

                        ///nokia-conf/configure/router/bgp/group/link-bandwidth/aggregate-used-paths/ipv6
                        leaf ipv6 {
                            type boolean;
                            default "false";
                            description "Support Link Bandwidth EC in IPv6 routes";
                        }

                        ///nokia-conf/configure/router/bgp/group/link-bandwidth/aggregate-used-paths/vpn-ipv4
                        leaf vpn-ipv4 {
                            type boolean;
                            default "false";
                            description "Support Link Bandwidth EC in VPN-IPv4 routes";
                        }

                        ///nokia-conf/configure/router/bgp/group/link-bandwidth/aggregate-used-paths/vpn-ipv6
                        leaf vpn-ipv6 {
                            type boolean;
                            default "false";
                            description "Support Link Bandwidth EC in VPN-IPv6 routes";
                        }

                        ///nokia-conf/configure/router/bgp/group/link-bandwidth/aggregate-used-paths/label-ipv4
                        leaf label-ipv4 {
                            type boolean;
                            default "false";
                            description "Support Link Bandwidth EC in label-IPv4 routes";
                        }

                        ///nokia-conf/configure/router/bgp/group/link-bandwidth/aggregate-used-paths/label-ipv6
                        leaf label-ipv6 {
                            type boolean;
                            default "false";
                            description "Support Link Bandwidth EC in label-IPv6 routes";
                        }

                    } // container aggregate-used-paths

                    ///nokia-conf/configure/router/bgp/group/link-bandwidth/send-to-ebgp
                    container send-to-ebgp {
                        description "Enter the send-to-ebgp context";

                        ///nokia-conf/configure/router/bgp/group/link-bandwidth/send-to-ebgp/ipv4
                        leaf ipv4 {
                            type boolean;
                            default "false";
                            description "Support Link Bandwidth EC in IPv4 routes";
                        }

                        ///nokia-conf/configure/router/bgp/group/link-bandwidth/send-to-ebgp/ipv6
                        leaf ipv6 {
                            type boolean;
                            default "false";
                            description "Support Link Bandwidth EC in IPv6 routes";
                        }

                        ///nokia-conf/configure/router/bgp/group/link-bandwidth/send-to-ebgp/vpn-ipv4
                        leaf vpn-ipv4 {
                            type boolean;
                            default "false";
                            description "Support Link Bandwidth EC in VPN-IPv4 routes";
                        }

                        ///nokia-conf/configure/router/bgp/group/link-bandwidth/send-to-ebgp/vpn-ipv6
                        leaf vpn-ipv6 {
                            type boolean;
                            default "false";
                            description "Support Link Bandwidth EC in VPN-IPv6 routes";
                        }

                        ///nokia-conf/configure/router/bgp/group/link-bandwidth/send-to-ebgp/label-ipv4
                        leaf label-ipv4 {
                            type boolean;
                            default "false";
                            description "Support Link Bandwidth EC in label-IPv4 routes";
                        }

                        ///nokia-conf/configure/router/bgp/group/link-bandwidth/send-to-ebgp/label-ipv6
                        leaf label-ipv6 {
                            type boolean;
                            default "false";
                            description "Support Link Bandwidth EC in label-IPv6 routes";
                        }

                    } // container send-to-ebgp

                } // container link-bandwidth

                ///nokia-conf/configure/router/bgp/group/send-communities
                container send-communities {
                    description "Enter the send-communities context";

                    ///nokia-conf/configure/router/bgp/group/send-communities/standard
                    leaf standard {
                        type boolean;
                        description "Advertise the Communities attribute to peers";
                    }

                    ///nokia-conf/configure/router/bgp/group/send-communities/extended
                    leaf extended {
                        type boolean;
                        description "Advertise the Extended Communities attribute to peers";
                    }

                    ///nokia-conf/configure/router/bgp/group/send-communities/large
                    leaf large {
                        type boolean;
                        description "Advertise the Large Communities attribute to peers";
                    }

                } // container send-communities

                ///nokia-conf/configure/router/bgp/group/error-handling
                container error-handling {
                    description "Enter the error-handling context";

                    ///nokia-conf/configure/router/bgp/group/error-handling/update-fault-tolerance
                    leaf update-fault-tolerance {
                        type boolean;
                        description "Tolerate non-critical errors in UPDATE messages";
                    }

                } // container error-handling

                ///nokia-conf/configure/router/bgp/group/damp-peer-oscillations
                container damp-peer-oscillations {
                    presence "Enable the damp-peer-oscillations context";
                    description "Enable the damp-peer-oscillations context";

                    ///nokia-conf/configure/router/bgp/group/damp-peer-oscillations/error-interval
                    leaf error-interval {
                        type uint32 {
                            range "0..2048";
                        }
                        default "30";
                        description "Time after a reset that the session must be error-free";
                    }

                    ///nokia-conf/configure/router/bgp/group/damp-peer-oscillations/idle-hold-time
                    container idle-hold-time {
                        description "Enter the idle-hold-time context";

                        ///nokia-conf/configure/router/bgp/group/damp-peer-oscillations/idle-hold-time/initial-wait
                        leaf initial-wait {
                            type uint32 {
                                range "0..2048";
                            }
                            default "0";
                            description "Time session remains in idle state after stabilization";
                        }

                        ///nokia-conf/configure/router/bgp/group/damp-peer-oscillations/idle-hold-time/second-wait
                        leaf second-wait {
                            type uint32 {
                                range "1..2048";
                            }
                            default "5";
                            description "Time that doubles after each repeated session failure";
                        }

                        ///nokia-conf/configure/router/bgp/group/damp-peer-oscillations/idle-hold-time/max-wait
                        leaf max-wait {
                            type uint32 {
                                range "1..2048";
                            }
                            default "60";
                            description "Maximum session idle time after repeated instability";
                        }

                    } // container idle-hold-time

                } // container damp-peer-oscillations

                ///nokia-conf/configure/router/bgp/group/bfd-strict-mode
                container bfd-strict-mode {
                    description "Enter the bfd-strict-mode context";

                    ///nokia-conf/configure/router/bgp/group/bfd-strict-mode/next-hop-reachability
                    leaf next-hop-reachability {
                        type boolean;
                        description "Consider next hop unreachable if BFD session is down";
                    }

                    ///nokia-conf/configure/router/bgp/group/bfd-strict-mode/advertise
                    container advertise {
                        presence "Enable the advertise context";
                        description "Enable the advertise context";

                        ///nokia-conf/configure/router/bgp/group/bfd-strict-mode/advertise/holdtime
                        leaf holdtime {
                            type uint16 {
                                range "1..65535";
                            }
                            units "seconds";
                            default "30";
                            description "Maximum time BGP waits for the BFD session to come up";
                        }

                    } // container advertise

                } // container bfd-strict-mode

                ///nokia-conf/configure/router/bgp/group/add-paths
                container add-paths {
                    presence "Enable the add-paths context";
                    description "Enable the add-paths context";

                    ///nokia-conf/configure/router/bgp/group/add-paths/ipv4
                    container ipv4 {
                        description "Enter the ipv4 context";

                        ///nokia-conf/configure/router/bgp/group/add-paths/ipv4/send
                        leaf send {
                            type types-bgp:add-paths-send-limit;
                            description "Maximum paths per unlabeled IPv4 unicast prefix";
                        }

                        ///nokia-conf/configure/router/bgp/group/add-paths/ipv4/receive
                        leaf receive {
                            type boolean;
                            default "false";
                            description "Receive multiple labeled-unicast routes per IPv4 prefix";
                        }

                    } // container ipv4

                    ///nokia-conf/configure/router/bgp/group/add-paths/ipv6
                    container ipv6 {
                        description "Enter the ipv6 context";

                        ///nokia-conf/configure/router/bgp/group/add-paths/ipv6/send
                        leaf send {
                            type types-bgp:add-paths-send-limit;
                            description "Maximum paths per unlabeled IPv6 unicast prefix";
                        }

                        ///nokia-conf/configure/router/bgp/group/add-paths/ipv6/receive
                        leaf receive {
                            type boolean;
                            default "false";
                            description "Receive multiple routes per IPv6 prefix";
                        }

                    } // container ipv6

                    ///nokia-conf/configure/router/bgp/group/add-paths/label-ipv4
                    container label-ipv4 {
                        description "Enter the label-ipv4 context";

                        ///nokia-conf/configure/router/bgp/group/add-paths/label-ipv4/send
                        leaf send {
                            type types-bgp:add-paths-send-limit;
                            description "Maximum paths per labeled IPv4 unicast prefix";
                        }

                        ///nokia-conf/configure/router/bgp/group/add-paths/label-ipv4/receive
                        leaf receive {
                            type boolean;
                            default "false";
                            description "Receive multiple labeled-unicast routes per IPv4 prefix";
                        }

                    } // container label-ipv4

                    ///nokia-conf/configure/router/bgp/group/add-paths/label-ipv6
                    container label-ipv6 {
                        description "Enter the label-ipv6 context";

                        ///nokia-conf/configure/router/bgp/group/add-paths/label-ipv6/send
                        leaf send {
                            type types-bgp:add-paths-send-limit;
                            description "Maximum paths per labeled IPv6 unicast prefix";
                        }

                        ///nokia-conf/configure/router/bgp/group/add-paths/label-ipv6/receive
                        leaf receive {
                            type boolean;
                            default "false";
                            description "Receive multiple labeled-unicast routes per IPv6 prefix";
                        }

                    } // container label-ipv6

                    ///nokia-conf/configure/router/bgp/group/add-paths/vpn-ipv4
                    container vpn-ipv4 {
                        description "Enter the vpn-ipv4 context";

                        ///nokia-conf/configure/router/bgp/group/add-paths/vpn-ipv4/send
                        leaf send {
                            type types-bgp:add-paths-send-limit;
                            description "Maximum paths per VPN-IPv4 prefix";
                        }

                        ///nokia-conf/configure/router/bgp/group/add-paths/vpn-ipv4/receive
                        leaf receive {
                            type boolean;
                            default "false";
                            description "Receive multiple routes per VPN-IPv4 prefix";
                        }

                    } // container vpn-ipv4

                    ///nokia-conf/configure/router/bgp/group/add-paths/vpn-ipv6
                    container vpn-ipv6 {
                        description "Enter the vpn-ipv6 context";

                        ///nokia-conf/configure/router/bgp/group/add-paths/vpn-ipv6/send
                        leaf send {
                            type types-bgp:add-paths-send-limit;
                            description "Maximum paths per VPN-IPv6 prefix";
                        }

                        ///nokia-conf/configure/router/bgp/group/add-paths/vpn-ipv6/receive
                        leaf receive {
                            type boolean;
                            default "false";
                            description "Receive multiple routes per VPN-IPv6 prefix";
                        }

                    } // container vpn-ipv6

                    ///nokia-conf/configure/router/bgp/group/add-paths/mvpn-ipv4
                    container mvpn-ipv4 {
                        description "Enter the mvpn-ipv4 context";

                        ///nokia-conf/configure/router/bgp/group/add-paths/mvpn-ipv4/send
                        leaf send {
                            type int32 {
                                range "1..16";
                            }
                            description "Maximum paths per multicast VPN IPv4 prefix";
                        }

                        ///nokia-conf/configure/router/bgp/group/add-paths/mvpn-ipv4/receive
                        leaf receive {
                            type boolean;
                            default "false";
                            description "Receive multiple multicast VPN routes per IPv4 prefix";
                        }

                    } // container mvpn-ipv4

                    ///nokia-conf/configure/router/bgp/group/add-paths/mvpn-ipv6
                    container mvpn-ipv6 {
                        description "Enter the mvpn-ipv6 context";

                        ///nokia-conf/configure/router/bgp/group/add-paths/mvpn-ipv6/send
                        leaf send {
                            type int32 {
                                range "1..16";
                            }
                            description "Maximum paths per multicast VPN IPv6 prefix";
                        }

                        ///nokia-conf/configure/router/bgp/group/add-paths/mvpn-ipv6/receive
                        leaf receive {
                            type boolean;
                            default "false";
                            description "Receive multiple multicast VPN routes per IPv6 prefix";
                        }

                    } // container mvpn-ipv6

                    ///nokia-conf/configure/router/bgp/group/add-paths/mcast-vpn-ipv4
                    container mcast-vpn-ipv4 {
                        description "Enter the mcast-vpn-ipv4 context";

                        ///nokia-conf/configure/router/bgp/group/add-paths/mcast-vpn-ipv4/send
                        leaf send {
                            type int32 {
                                range "1..16";
                            }
                            description "Maximum paths per multicast IPv4 VPN prefix";
                        }

                        ///nokia-conf/configure/router/bgp/group/add-paths/mcast-vpn-ipv4/receive
                        leaf receive {
                            type boolean;
                            default "false";
                            description "Receive multiple multicast routes per IPv4 VPN prefix";
                        }

                    } // container mcast-vpn-ipv4

                    ///nokia-conf/configure/router/bgp/group/add-paths/mcast-vpn-ipv6
                    container mcast-vpn-ipv6 {
                        description "Enter the mcast-vpn-ipv6 context";

                        ///nokia-conf/configure/router/bgp/group/add-paths/mcast-vpn-ipv6/send
                        leaf send {
                            type int32 {
                                range "1..16";
                            }
                            description "Maximum paths per multicast IPv6 VPN prefix";
                        }

                        ///nokia-conf/configure/router/bgp/group/add-paths/mcast-vpn-ipv6/receive
                        leaf receive {
                            type boolean;
                            default "false";
                            description "Receive multiple multicast routes per IPv6 VPN prefix";
                        }

                    } // container mcast-vpn-ipv6

                    ///nokia-conf/configure/router/bgp/group/add-paths/evpn
                    container evpn {
                        description "Enter the evpn context";

                        ///nokia-conf/configure/router/bgp/group/add-paths/evpn/send
                        leaf send {
                            type types-bgp:add-paths-send-limit;
                            description "Maximum paths per EVPN prefix to Add-Path peers";
                        }

                        ///nokia-conf/configure/router/bgp/group/add-paths/evpn/receive
                        leaf receive {
                            type boolean;
                            default "false";
                            description "Receive multiple EVPN paths per prefix from a peer";
                        }

                    } // container evpn

                } // container add-paths

                ///nokia-conf/configure/router/bgp/group/import
                container import {
                    presence "Enable the import context";
                    description "Enable the import context";

                    ///nokia-conf/configure/router/bgp/group/import/policy
                    leaf-list policy {
                        type union {
                            type types-sros:policy-expr-string;
                            type string;
                        }
                        min-elements 1;
                        max-elements 15;
                        ordered-by user;
                        description "BGP import policy name";
                    }

                    ///nokia-conf/configure/router/bgp/group/import/apply-groups
                    leaf-list apply-groups {
                        type leafref {
                            path "../../../../../groups/group/name";
                        }
                        max-elements 8;
                        ordered-by user;
                        description "Apply a configuration group at this level";
                    }

                    ///nokia-conf/configure/router/bgp/group/import/apply-groups-exclude
                    leaf-list apply-groups-exclude {
                        type leafref {
                            path "../../../../../groups/group/name";
                        }
                        max-elements 8;
                        ordered-by user;
                        description "Exclude a configuration group at this level";
                    }

                } // container import

                ///nokia-conf/configure/router/bgp/group/export
                container export {
                    presence "Enable the export context";
                    description "Enable the export context";

                    ///nokia-conf/configure/router/bgp/group/export/policy
                    leaf-list policy {
                        type union {
                            type types-sros:policy-expr-string;
                            type string;
                        }
                        min-elements 1;
                        max-elements 15;
                        ordered-by user;
                        description "BGP export policy name";
                    }

                    ///nokia-conf/configure/router/bgp/group/export/apply-groups
                    leaf-list apply-groups {
                        type leafref {
                            path "../../../../../groups/group/name";
                        }
                        max-elements 8;
                        ordered-by user;
                        description "Apply a configuration group at this level";
                    }

                    ///nokia-conf/configure/router/bgp/group/export/apply-groups-exclude
                    leaf-list apply-groups-exclude {
                        type leafref {
                            path "../../../../../groups/group/name";
                        }
                        max-elements 8;
                        ordered-by user;
                        description "Exclude a configuration group at this level";
                    }

                } // container export

                ///nokia-conf/configure/router/bgp/group/extended-nh-encoding
                container extended-nh-encoding {
                    presence "Enable the extended-nh-encoding context";
                    description "Enable the extended-nh-encoding context";

                    ///nokia-conf/configure/router/bgp/group/extended-nh-encoding/vpn-ipv4
                    leaf vpn-ipv4 {
                        type boolean;
                        default "false";
                        description "Advertise encoding capability for VPN-IPv4 routes";
                    }

                    ///nokia-conf/configure/router/bgp/group/extended-nh-encoding/label-ipv4
                    leaf label-ipv4 {
                        type boolean;
                        default "false";
                        description "Advertise encoding capability for label-IPv4 routes";
                    }

                    ///nokia-conf/configure/router/bgp/group/extended-nh-encoding/ipv4
                    leaf ipv4 {
                        type boolean;
                        default "false";
                        description "Advertise encoding capability for IPv4 routes";
                    }

                } // container extended-nh-encoding

                ///nokia-conf/configure/router/bgp/group/advertise-ipv6-next-hops
                container advertise-ipv6-next-hops {
                    presence "Enable the advertise-ipv6-next-hops context";
                    description "Enable the advertise-ipv6-next-hops context";

                    ///nokia-conf/configure/router/bgp/group/advertise-ipv6-next-hops/vpn-ipv6
                    leaf vpn-ipv6 {
                        type boolean;
                        default "false";
                        description "Advertise VPN IPv6 route with IPv6 next-hop address";
                    }

                    ///nokia-conf/configure/router/bgp/group/advertise-ipv6-next-hops/label-ipv6
                    leaf label-ipv6 {
                        type boolean;
                        default "false";
                        description "Advertise label IPv6 route with IPv6 next-hop address";
                    }

                    ///nokia-conf/configure/router/bgp/group/advertise-ipv6-next-hops/evpn
                    leaf evpn {
                        type boolean;
                        default "false";
                        description "Advertise EVPN route with IPv6 next-hop address";
                    }

                    ///nokia-conf/configure/router/bgp/group/advertise-ipv6-next-hops/vpn-ipv4
                    leaf vpn-ipv4 {
                        type boolean;
                        default "false";
                        description "Advertise VPN IPv4 route with IPv6 next-hop address";
                    }

                    ///nokia-conf/configure/router/bgp/group/advertise-ipv6-next-hops/label-ipv4
                    leaf label-ipv4 {
                        type boolean;
                        default "false";
                        description "Advertise label IPv4 route with IPv6 next-hop address";
                    }

                    ///nokia-conf/configure/router/bgp/group/advertise-ipv6-next-hops/ipv4
                    leaf ipv4 {
                        type boolean;
                        default "false";
                        description "Advertise IPv4 route with IPv6 next-hop address";
                    }

                } // container advertise-ipv6-next-hops

                ///nokia-conf/configure/router/bgp/group/graceful-restart
                container graceful-restart {
                    presence "Enable the graceful-restart context";
                    description "Enable the graceful-restart context";

                    ///nokia-conf/configure/router/bgp/group/graceful-restart/restart-time
                    leaf restart-time {
                        type uint32 {
                            range "0..4095";
                        }
                        default "300";
                        description "Restart time advertised by GR capability";
                    }

                    ///nokia-conf/configure/router/bgp/group/graceful-restart/stale-routes-time
                    leaf stale-routes-time {
                        type uint32 {
                            range "1..3600";
                        }
                        default "360";
                        description "Maximum time to maintain routes after graceful restart";
                    }

                    ///nokia-conf/configure/router/bgp/group/graceful-restart/gr-notification
                    leaf gr-notification {
                        type boolean;
                        default "false";
                        description "Perform graceful restart procedures after NOTIFICATION";
                    }

                    ///nokia-conf/configure/router/bgp/group/graceful-restart/long-lived
                    container long-lived {
                        presence "Enable the long-lived context";
                        description "Enable the long-lived context";

                        ///nokia-conf/configure/router/bgp/group/graceful-restart/long-lived/advertised-stale-time
                        leaf advertised-stale-time {
                            type uint32 {
                                range "0..16777215";
                            }
                            default "86400";
                            description "Advertised long-lived stale time for LLGR routes";
                        }

                        ///nokia-conf/configure/router/bgp/group/graceful-restart/long-lived/helper-override-stale-time
                        leaf helper-override-stale-time {
                            type uint32 {
                                range "0..16777215";
                            }
                            description "Locally-configured stale routes override time";
                        }

                        ///nokia-conf/configure/router/bgp/group/graceful-restart/long-lived/helper-override-restart-time
                        leaf helper-override-restart-time {
                            type uint32 {
                                range "0..4095";
                            }
                            description "Locally-configured override for restart time";
                        }

                        ///nokia-conf/configure/router/bgp/group/graceful-restart/long-lived/forwarding-bits-set
                        leaf forwarding-bits-set {
                            type enumeration {
                                enum none                           { value 0; }
                                enum all                            { value 1; }
                                enum non-fwd                        { value 2; }
                            }
                            default "none";
                            description "BGP LLGR forwarding-bit behavior for address family";
                        }

                        ///nokia-conf/configure/router/bgp/group/graceful-restart/long-lived/advertise-stale-to-all-neighbors
                        leaf advertise-stale-to-all-neighbors {
                            type boolean;
                            default "false";
                            description "Advertise stale routes to all BGP peers";
                        }

                        ///nokia-conf/configure/router/bgp/group/graceful-restart/long-lived/without-no-export
                        leaf without-no-export {
                            type boolean;
                            default "false";
                            description "Advertise LLGR stale routes to non-LLGR peers";
                        }

                        ///nokia-conf/configure/router/bgp/group/graceful-restart/long-lived/family
                        list family {
                            key "family-type";
                            description "Enter the family list instance";

                            ///nokia-conf/configure/router/bgp/group/graceful-restart/long-lived/family/family-type
                            leaf family-type {
                                type types-bgp:llgr-family-identifiers;
                                description "Family type for family-specific LLGR configuration";
                            }

                            ///nokia-conf/configure/router/bgp/group/graceful-restart/long-lived/family/advertised-stale-time
                            leaf advertised-stale-time {
                                type uint32 {
                                    range "0..16777215";
                                }
                                default "86400";
                                description "LLGR stale routes time for family override";
                            }

                            ///nokia-conf/configure/router/bgp/group/graceful-restart/long-lived/family/helper-override-stale-time
                            leaf helper-override-stale-time {
                                type uint32 {
                                    range "0..16777216";
                                }
                                default "16777216";
                                description "Locally-configured stale routes override time";
                            }

                            ///nokia-conf/configure/router/bgp/group/graceful-restart/long-lived/family/apply-groups
                            leaf-list apply-groups {
                                type leafref {
                                    path "../../../../../../../groups/group/name";
                                }
                                max-elements 8;
                                ordered-by user;
                                description "Apply a configuration group at this level";
                            }

                            ///nokia-conf/configure/router/bgp/group/graceful-restart/long-lived/family/apply-groups-exclude
                            leaf-list apply-groups-exclude {
                                type leafref {
                                    path "../../../../../../../groups/group/name";
                                }
                                max-elements 8;
                                ordered-by user;
                                description "Exclude a configuration group at this level";
                            }

                        } // list family

                    } // container long-lived

                } // container graceful-restart

                ///nokia-conf/configure/router/bgp/group/outbound-route-filtering
                container outbound-route-filtering {
                    presence "Enable the outbound-route-filtering context";
                    description "Enable the outbound-route-filtering context";

                    ///nokia-conf/configure/router/bgp/group/outbound-route-filtering/extended-community
                    container extended-community {
                        presence "Enable the extended-community context";
                        description "Enable the extended-community context";

                        ///nokia-conf/configure/router/bgp/group/outbound-route-filtering/extended-community/accept-orf
                        leaf accept-orf {
                            type boolean;
                            description "Negotiate with peer to accept BGP ORF filters";
                        }

                        ///nokia-conf/configure/router/bgp/group/outbound-route-filtering/extended-community/send-orf
                        container send-orf {
                            presence "Enable the send-orf context";
                            description "Enable the send-orf context";

                            ///nokia-conf/configure/router/bgp/group/outbound-route-filtering/extended-community/send-orf/route-target
                            list route-target {
                                key "community-name";
                                description "Add a list entry for route-target";

                                ///nokia-conf/configure/router/bgp/group/outbound-route-filtering/extended-community/send-orf/route-target/community-name
                                leaf community-name {
                                    type types-sros:named-item;
                                    description "Route target community name";
                                }

                            } // list route-target

                        } // container send-orf

                    } // container extended-community

                } // container outbound-route-filtering

                ///nokia-conf/configure/router/bgp/group/prefix-limit
                list prefix-limit {
                    key "family";
                    description "Enter the prefix-limit list instance";

                    ///nokia-conf/configure/router/bgp/group/prefix-limit/family
                    leaf family {
                        type types-bgp:ip-family-identifier;
                        description "Address family to which the limit applies";
                    }

                    ///nokia-conf/configure/router/bgp/group/prefix-limit/maximum
                    leaf maximum {
                        type uint32 {
                            range "1..4294967295";
                        }
                        mandatory true;
                        description "Maximum number of routes to be learned from a peer";
                    }

                    ///nokia-conf/configure/router/bgp/group/prefix-limit/log-only
                    leaf log-only {
                        type boolean;
                        default "false";
                        description "Send warning message at threshold instead of take-down";
                    }

                    ///nokia-conf/configure/router/bgp/group/prefix-limit/threshold
                    leaf threshold {
                        type uint32 {
                            range "1..100";
                        }
                        default "90";
                        description "Percentage threshold that triggers a warning message";
                    }

                    ///nokia-conf/configure/router/bgp/group/prefix-limit/idle-timeout
                    leaf idle-timeout {
                        type int32 {
                            range "1..1024";
                        }
                        description "Time BGP peering remains idle before reconnecting";
                    }

                    ///nokia-conf/configure/router/bgp/group/prefix-limit/post-import
                    leaf post-import {
                        type boolean;
                        default "false";
                        description "Apply limit only to routes accepted by import policies";
                    }

                    ///nokia-conf/configure/router/bgp/group/prefix-limit/hold-excess
                    leaf hold-excess {
                        type int32 {
                            range "1..100";
                        }
                        description "Percentage of maximum routes to install in route table";
                    }

                    ///nokia-conf/configure/router/bgp/group/prefix-limit/apply-groups
                    leaf-list apply-groups {
                        type leafref {
                            path "../../../../../groups/group/name";
                        }
                        max-elements 8;
                        ordered-by user;
                        description "Apply a configuration group at this level";
                    }

                    ///nokia-conf/configure/router/bgp/group/prefix-limit/apply-groups-exclude
                    leaf-list apply-groups-exclude {
                        type leafref {
                            path "../../../../../groups/group/name";
                        }
                        max-elements 8;
                        ordered-by user;
                        description "Exclude a configuration group at this level";
                    }

                } // list prefix-limit

                ///nokia-conf/configure/router/bgp/group/dynamic-neighbor
                container dynamic-neighbor {
                    description "Enter the dynamic-neighbor context";

                    ///nokia-conf/configure/router/bgp/group/dynamic-neighbor/match
                    container match {
                        description "Enter the match context";

                        ///nokia-conf/configure/router/bgp/group/dynamic-neighbor/match/prefix
                        list prefix {
                            key "ip-prefix";
                            description "Enter the prefix list instance";

                            ///nokia-conf/configure/router/bgp/group/dynamic-neighbor/match/prefix/ip-prefix
                            leaf ip-prefix {
                                type types-sros:ip-prefix;
                                description "Dynamic peer prefix for the group";
                            }

                            ///nokia-conf/configure/router/bgp/group/dynamic-neighbor/match/prefix/allowed-peer-as
                            leaf-list allowed-peer-as {
                                type string {
                                    pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                                }
                                max-elements 32;
                                ordered-by user;
                                description "Allowed peer AS value or range of acceptable values";
                            }

                            ///nokia-conf/configure/router/bgp/group/dynamic-neighbor/match/prefix/apply-groups
                            leaf-list apply-groups {
                                type leafref {
                                    path "../../../../../../../groups/group/name";
                                }
                                max-elements 8;
                                ordered-by user;
                                description "Apply a configuration group at this level";
                            }

                            ///nokia-conf/configure/router/bgp/group/dynamic-neighbor/match/prefix/apply-groups-exclude
                            leaf-list apply-groups-exclude {
                                type leafref {
                                    path "../../../../../../../groups/group/name";
                                }
                                max-elements 8;
                                ordered-by user;
                                description "Exclude a configuration group at this level";
                            }

                        } // list prefix

                    } // container match



                    ///nokia-conf/configure/router/bgp/group/dynamic-neighbor/interface
                    list interface {
                        key "interface-name";
                        description "Enter the interface list instance";

                        ///nokia-conf/configure/router/bgp/group/dynamic-neighbor/interface/interface-name
                        leaf interface-name {
                            type types-sros:interface-name;
                            description "Name of the dynamic neighbor interface";
                        }

                        ///nokia-conf/configure/router/bgp/group/dynamic-neighbor/interface/allowed-peer-as
                        leaf-list allowed-peer-as {
                            type string {
                                pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                            }
                            max-elements 32;
                            ordered-by user;
                            description "Allowed peer AS value or range of acceptable values";
                        }

                        ///nokia-conf/configure/router/bgp/group/dynamic-neighbor/interface/max-sessions
                        leaf max-sessions {
                            type uint32 {
                                range "1..255";
                            }
                            default "1";
                            description "Maximum number of dynamic sessions allowed";
                        }

                        ///nokia-conf/configure/router/bgp/group/dynamic-neighbor/interface/apply-groups
                        leaf-list apply-groups {
                            type leafref {
                                path "../../../../../../groups/group/name";
                            }
                            max-elements 8;
                            ordered-by user;
                            description "Apply a configuration group at this level";
                        }

                        ///nokia-conf/configure/router/bgp/group/dynamic-neighbor/interface/apply-groups-exclude
                        leaf-list apply-groups-exclude {
                            type leafref {
                                path "../../../../../../groups/group/name";
                            }
                            max-elements 8;
                            ordered-by user;
                            description "Exclude a configuration group at this level";
                        }

                    } // list interface

                } // container dynamic-neighbor

                ///nokia-conf/configure/router/bgp/group/monitor
                container monitor {
                    presence "Enable the monitor context";
                    description "Enable the monitor context";

                    ///nokia-conf/configure/router/bgp/group/monitor/all-stations
                    leaf all-stations {
                        type boolean;
                        default "false";
                        description "Send BMP messages to all configured stations";
                    }

                    ///nokia-conf/configure/router/bgp/group/monitor/admin-state
                    leaf admin-state {
                        type types-sros:admin-state;
                        default "disable";
                        description "Administrative state of BMP monitoring";
                    }

                    ///nokia-conf/configure/router/bgp/group/monitor/apply-groups
                    leaf-list apply-groups {
                        type leafref {
                            path "../../../../../groups/group/name";
                        }
                        max-elements 8;
                        ordered-by user;
                        description "Apply a configuration group at this level";
                    }

                    ///nokia-conf/configure/router/bgp/group/monitor/apply-groups-exclude
                    leaf-list apply-groups-exclude {
                        type leafref {
                            path "../../../../../groups/group/name";
                        }
                        max-elements 8;
                        ordered-by user;
                        description "Exclude a configuration group at this level";
                    }

                    ///nokia-conf/configure/router/bgp/group/monitor/route-monitoring
                    container route-monitoring {
                        description "Enter the route-monitoring context";

                        ///nokia-conf/configure/router/bgp/group/monitor/route-monitoring/pre-policy
                        leaf pre-policy {
                            type boolean;
                            default "false";
                            description "Allow pre-policy route-monitoring messages to be sent";
                        }

                        ///nokia-conf/configure/router/bgp/group/monitor/route-monitoring/post-policy
                        leaf post-policy {
                            type boolean;
                            default "false";
                            description "Allow post-policy route-monitoring messages to be sent";
                        }

                    } // container route-monitoring

                    ///nokia-conf/configure/router/bgp/group/monitor/station
                    list station {
                        key "station-name";
                        max-elements 8;
                        description "Add a list entry for station";

                        ///nokia-conf/configure/router/bgp/group/monitor/station/station-name
                        leaf station-name {
                            type leafref {
                                path "../../../../../../bmp/station/name";
                            }
                            description "BMP monitoring station";
                        }

                    } // list station

                } // container monitor

                ///nokia-conf/configure/router/bgp/group/egress-engineering
                container egress-engineering {
                    presence "Enable the egress-engineering context";
                    description "Enable the egress-engineering context";

                    ///nokia-conf/configure/router/bgp/group/egress-engineering/admin-state
                    leaf admin-state {
                        type types-sros:admin-state;
                        default "disable";
                        description "Administrative state of BGP egress engineering";
                    }

                    ///nokia-conf/configure/router/bgp/group/egress-engineering/apply-groups
                    leaf-list apply-groups {
                        type leafref {
                            path "../../../../../groups/group/name";
                        }
                        max-elements 8;
                        ordered-by user;
                        description "Apply a configuration group at this level";
                    }

                    ///nokia-conf/configure/router/bgp/group/egress-engineering/apply-groups-exclude
                    leaf-list apply-groups-exclude {
                        type leafref {
                            path "../../../../../groups/group/name";
                        }
                        max-elements 8;
                        ordered-by user;
                        description "Exclude a configuration group at this level";
                    }

                } // container egress-engineering

                ///nokia-conf/configure/router/bgp/group/segment-routing-v6
                container segment-routing-v6 {
                    presence "Enable the segment-routing-v6 context";
                    description "Enable the segment-routing-v6 context";

                    ///nokia-conf/configure/router/bgp/group/segment-routing-v6/route-advertisement
                    container route-advertisement {
                        presence "Enable the route-advertisement context";
                        description "Enable the route-advertisement context";

                        ///nokia-conf/configure/router/bgp/group/segment-routing-v6/route-advertisement/drop-routes-with-srv6-tlvs
                        leaf drop-routes-with-srv6-tlvs {
                            type boolean;
                            default "false";
                            description "Drop BGP routes with SRv6 TLVs";
                        }

                        ///nokia-conf/configure/router/bgp/group/segment-routing-v6/route-advertisement/family
                        list family {
                            key "family-type";
                            description "Enter the family list instance";

                            ///nokia-conf/configure/router/bgp/group/segment-routing-v6/route-advertisement/family/family-type
                            leaf family-type {
                                type enumeration {
                                    enum ipv4                           { value 1; }
                                    enum ipv6                           { value 3; }
                                }
                                description "IP address type that SRv6 route attributes apply to";
                            }

                            ///nokia-conf/configure/router/bgp/group/segment-routing-v6/route-advertisement/family/strip-srv6-tlvs
                            leaf strip-srv6-tlvs {
                                type boolean;
                                default "false";
                                description "Strip SRv6 TLVs from BGP routes advertised to peers";
                            }

                            ///nokia-conf/configure/router/bgp/group/segment-routing-v6/route-advertisement/family/apply-groups
                            leaf-list apply-groups {
                                type leafref {
                                    path "../../../../../../../groups/group/name";
                                }
                                max-elements 8;
                                ordered-by user;
                                description "Apply a configuration group at this level";
                            }

                            ///nokia-conf/configure/router/bgp/group/segment-routing-v6/route-advertisement/family/apply-groups-exclude
                            leaf-list apply-groups-exclude {
                                type leafref {
                                    path "../../../../../../../groups/group/name";
                                }
                                max-elements 8;
                                ordered-by user;
                                description "Exclude a configuration group at this level";
                            }

                        } // list family

                    } // container route-advertisement

                } // container segment-routing-v6

            } // list group

            ///nokia-conf/configure/router/bgp/neighbor
            list neighbor {
                key "ip-address";
                description "Enter the neighbor list instance";

                ///nokia-conf/configure/router/bgp/neighbor/ip-address
                leaf ip-address {
                    type types-sros:ip-address-with-zone;
                    description "IP address of the BGP peer router";
                }

                ///nokia-conf/configure/router/bgp/neighbor/advertise-ldp-prefix
                leaf advertise-ldp-prefix {
                    type boolean;
                    default "false";
                    description "Advertise active /32 LDP FEC prefixes to BGP peers";
                }

                ///nokia-conf/configure/router/bgp/neighbor/ttl-security
                leaf ttl-security {
                    type uint32 {
                        range "1..255";
                    }
                    description "Minimum TTL value for an incoming BGP packet";
                }

                ///nokia-conf/configure/router/bgp/neighbor/default-route-target
                leaf default-route-target {
                    type boolean;
                    description "Send default RTC route (zero prefix length) to peers";
                }

                ///nokia-conf/configure/router/bgp/neighbor/aigp
                leaf aigp {
                    type boolean;
                    description "Add AIGP attribute to advertised routes";
                }

                ///nokia-conf/configure/router/bgp/neighbor/advertise-inactive
                leaf advertise-inactive {
                    type boolean;
                    description "Advertise an inactive BGP route to peers";
                }

                ///nokia-conf/configure/router/bgp/neighbor/authentication-keychain
                leaf authentication-keychain {
                    type leafref {
                        path "../../../../system/security/keychains/keychain/keychain-name";
                    }
                    description "TCP authentication keychain for the session";
                }

                ///nokia-conf/configure/router/bgp/neighbor/bfd-liveness
                leaf bfd-liveness {
                    type boolean;
                    description "Enable BFD";
                }

                ///nokia-conf/configure/router/bgp/neighbor/fast-external-failover
                leaf fast-external-failover {
                    type boolean;
                    description "Drop external BGP session immediately when link fails";
                }

                ///nokia-conf/configure/router/bgp/neighbor/peer-ip-tracking
                leaf peer-ip-tracking {
                    type boolean;
                    description "Enable BGP peer tracking";
                }

                ///nokia-conf/configure/router/bgp/neighbor/split-horizon
                leaf split-horizon {
                    type boolean;
                    description "Prevent routes being reflected back to best-route peer";
                }

                ///nokia-conf/configure/router/bgp/neighbor/third-party-nexthop
                leaf third-party-nexthop {
                    type boolean;
                    description "Apply third-party next-hop processing to EBGP peers";
                }

                ///nokia-conf/configure/router/bgp/neighbor/label-preference
                leaf label-preference {
                    type uint32 {
                        range "1..255";
                    }
                    description "Route preference for routes from labeled-unicast peers";
                }

                ///nokia-conf/configure/router/bgp/neighbor/def-recv-evpn-encap
                leaf def-recv-evpn-encap {
                    type types-bgp:encap;
                    description "Default EVPN encapsulation type";
                }

                ///nokia-conf/configure/router/bgp/neighbor/multipath-eligible
                leaf multipath-eligible {
                    type boolean;
                    description "Allow routes from this peer in multipath eligibility";
                }

                ///nokia-conf/configure/router/bgp/neighbor/group
                leaf group {
                    type leafref {
                        path "../../group/group-name";
                    }
                    sros-ext:immutable;
                    mandatory true;
                    description "BGP peer group";
                }

                ///nokia-conf/configure/router/bgp/neighbor/peer-creation-type
                leaf peer-creation-type {
                    type types-bgp:peer-creation-type;
                    default "static";
                    description "Peer creation type";
                }

                ///nokia-conf/configure/router/bgp/neighbor/connect-retry
                leaf connect-retry {
                    type int32 {
                        range "1..65535";
                    }
                    description "BGP connect retry timer value";
                }

                ///nokia-conf/configure/router/bgp/neighbor/description
                leaf description {
                    type types-sros:description;
                    description "Text description";
                }

                ///nokia-conf/configure/router/bgp/neighbor/admin-state
                leaf admin-state {
                    type types-sros:admin-state;
                    default "enable";
                    description "Administrative state of the BGP neighbor";
                }

                ///nokia-conf/configure/router/bgp/neighbor/keepalive
                leaf keepalive {
                    type int32 {
                        range "0..21845";
                    }
                    description "Time after which the BGP KEEPALIVE message is sent";
                }

                ///nokia-conf/configure/router/bgp/neighbor/damping
                leaf damping {
                    type boolean;
                    description "Use BGP route damping to reduce route flap";
                }

                ///nokia-conf/configure/router/bgp/neighbor/local-preference
                leaf local-preference {
                    type int64 {
                        range "0..4294967295";
                    }
                    description "Default local preference if not in incoming routes";
                }

                ///nokia-conf/configure/router/bgp/neighbor/loop-detect
                leaf loop-detect {
                    type types-bgp:loop-detect;
                    description "Strategy for loop detection in the AS path";
                }

                ///nokia-conf/configure/router/bgp/neighbor/loop-detect-threshold
                leaf loop-detect-threshold {
                    type uint32 {
                        range "0..15";
                    }
                    description "Threshold for the global ASN in a received AS path";
                }

                ///nokia-conf/configure/router/bgp/neighbor/tcp-mss
                leaf tcp-mss {
                    type union {
                        type uint32 {
                            range "384..9746";
                        }
                        type enumeration {
                            enum ip-stack                       { value 0; }
                        }
                    }
                    description "TCP maximum segment size override";
                }

                ///nokia-conf/configure/router/bgp/neighbor/selective-label-ipv4-install
                leaf selective-label-ipv4-install {
                    type boolean;
                    description "Enable selective download for BGP label-ipv4 routes";
                }

                ///nokia-conf/configure/router/bgp/neighbor/min-route-advertisement
                leaf min-route-advertisement {
                    type int16 {
                        range "1..255";
                    }
                    description "Minimum interval between successive prefix updates";
                }

                ///nokia-conf/configure/router/bgp/neighbor/aggregator-id-zero
                leaf aggregator-id-zero {
                    type boolean;
                    description "Set router ID in the BGP AGGREGATOR attribute to zero";
                }

                ///nokia-conf/configure/router/bgp/neighbor/preference
                leaf preference {
                    type uint32 {
                        range "1..255";
                    }
                    description "Route preference for routes learned from all peers";
                }

                ///nokia-conf/configure/router/bgp/neighbor/block-prefix-sid
                leaf block-prefix-sid {
                    type boolean;
                    default "false";
                    description "Block the prefix SID attribute";
                }

                ///nokia-conf/configure/router/bgp/neighbor/multihop
                leaf multihop {
                    type int32 {
                        range "1..255";
                    }
                    description "TTL in IP packet headers for EBGP peers multi-hops away";
                }

                ///nokia-conf/configure/router/bgp/neighbor/med-out
                leaf med-out {
                    type union {
                        type uint32;
                        type enumeration {
                            enum igp-cost                       { value -1; }
                        }
                    }
                    description "Default MED attribute value to advertise to peers";
                }

                ///nokia-conf/configure/router/bgp/neighbor/authentication-key
                leaf authentication-key {
                    type types-sros:encrypted-leaf {
                        length "1..370";
                    }
                    description "BGP authentication key";
                }

                ///nokia-conf/configure/router/bgp/neighbor/client-reflect
                leaf client-reflect {
                    type boolean;
                    description "Allow cluster RR to advertise routes to its clients";
                }

                ///nokia-conf/configure/router/bgp/neighbor/vpn-apply-export
                leaf vpn-apply-export {
                    type boolean;
                    description "Apply base-instance BGP export policies to VPN routes";
                }

                ///nokia-conf/configure/router/bgp/neighbor/vpn-apply-import
                leaf vpn-apply-import {
                    type boolean;
                    description "Apply base-instance BGP import policies to VPN routes";
                }

                ///nokia-conf/configure/router/bgp/neighbor/as-override
                leaf as-override {
                    type boolean;
                    description "Replace the peer's ASN with the local ASN in AS Path";
                }

                ///nokia-conf/configure/router/bgp/neighbor/asn-4-byte
                leaf asn-4-byte {
                    type boolean;
                    description "Advertise the use of 4-byte ASNs";
                }

                ///nokia-conf/configure/router/bgp/neighbor/path-mtu-discovery
                leaf path-mtu-discovery {
                    type boolean;
                    description "Enable path MTU discovery";
                }

                ///nokia-conf/configure/router/bgp/neighbor/local-address
                leaf local-address {
                    type types-bgp:local-address;
                    description "Local IP address used when communicating with BGP peers";
                }

                ///nokia-conf/configure/router/bgp/neighbor/l2vpn-cisco-interop
                leaf l2vpn-cisco-interop {
                    type boolean;
                    default "false";
                    description "Allow translation from Cisco non-compliant NLRI format";
                }

                ///nokia-conf/configure/router/bgp/neighbor/next-hop-self
                leaf next-hop-self {
                    type boolean;
                    description "Advertise routes with local address as next-hop address";
                }

                ///nokia-conf/configure/router/bgp/neighbor/passive
                leaf passive {
                    type boolean;
                    description "Use passive mode for BGP communication";
                }

                ///nokia-conf/configure/router/bgp/neighbor/type
                leaf type {
                    type types-bgp:peer-type;
                    description "BGP peer type";
                }

                ///nokia-conf/configure/router/bgp/neighbor/peer-as
                leaf peer-as {
                    type uint32 {
                        range "1..4294967295";
                    }
                    description "Peer AS number";
                }

                ///nokia-conf/configure/router/bgp/neighbor/capability-negotiation
                leaf capability-negotiation {
                    type boolean;
                    description "Enable capability negotiation";
                }

                ///nokia-conf/configure/router/bgp/neighbor/enforce-first-as
                leaf enforce-first-as {
                    type boolean;
                    description "Enforce the configured peer AS value in received routes";
                }

                ///nokia-conf/configure/router/bgp/neighbor/initial-send-delay-zero
                leaf initial-send-delay-zero {
                    type boolean;
                    description "Send BGP updates as soon as the session comes up";
                }

                ///nokia-conf/configure/router/bgp/neighbor/egress-peer-engineering-label-unicast
                leaf egress-peer-engineering-label-unicast {
                    type boolean;
                    default "false";
                    description "Generate EPE label-unicast routes for neighbor";
                }

                ///nokia-conf/configure/router/bgp/neighbor/apply-groups
                leaf-list apply-groups {
                    type leafref {
                        path "../../../../groups/group/name";
                    }
                    max-elements 8;
                    ordered-by user;
                    description "Apply a configuration group at this level";
                }

                ///nokia-conf/configure/router/bgp/neighbor/apply-groups-exclude
                leaf-list apply-groups-exclude {
                    type leafref {
                        path "../../../../groups/group/name";
                    }
                    max-elements 8;
                    ordered-by user;
                    description "Exclude a configuration group at this level";
                }

                ///nokia-conf/configure/router/bgp/neighbor/next-hop-unchanged
                container next-hop-unchanged {
                    presence "Enable the next-hop-unchanged context";
                    description "Enable the next-hop-unchanged context";

                    ///nokia-conf/configure/router/bgp/neighbor/next-hop-unchanged/label-ipv4
                    leaf label-ipv4 {
                        type boolean;
                        default "false";
                        description "Advertise label-IPv4 routes with unchanged BGP next hop";
                    }

                    ///nokia-conf/configure/router/bgp/neighbor/next-hop-unchanged/label-ipv6
                    leaf label-ipv6 {
                        type boolean;
                        default "false";
                        description "Advertise label-IPv6 routes with unchanged BGP next hop";
                    }

                    ///nokia-conf/configure/router/bgp/neighbor/next-hop-unchanged/vpn-ipv4
                    leaf vpn-ipv4 {
                        type boolean;
                        default "false";
                        description "Advertise VPN IPv4 routes with unchanged BGP next hop";
                    }

                    ///nokia-conf/configure/router/bgp/neighbor/next-hop-unchanged/vpn-ipv6
                    leaf vpn-ipv6 {
                        type boolean;
                        default "false";
                        description "Advertise VPN IPv6 routes with unchanged BGP next hop";
                    }

                    ///nokia-conf/configure/router/bgp/neighbor/next-hop-unchanged/evpn
                    leaf evpn {
                        type boolean;
                        default "false";
                        description "Advertise EVPN routes with unchanged BGP next hop";
                    }

                } // container next-hop-unchanged

                ///nokia-conf/configure/router/bgp/neighbor/origin-validation
                container origin-validation {
                    presence "Enable the origin-validation context";
                    description "Enable the origin-validation context";

                    ///nokia-conf/configure/router/bgp/neighbor/origin-validation/ipv4
                    leaf ipv4 {
                        type boolean;
                        default "false";
                        description "Enable support for unlabeled unicast IPv4 routes";
                    }

                    ///nokia-conf/configure/router/bgp/neighbor/origin-validation/ipv6
                    leaf ipv6 {
                        type boolean;
                        default "false";
                        description "Enable support for unlabeled unicast IPv6 routes";
                    }

                    ///nokia-conf/configure/router/bgp/neighbor/origin-validation/label-ipv4
                    leaf label-ipv4 {
                        type boolean;
                        default "false";
                        description "Enable support for labeled-unicast IPv4 routes";
                    }

                    ///nokia-conf/configure/router/bgp/neighbor/origin-validation/label-ipv6
                    leaf label-ipv6 {
                        type boolean;
                        default "false";
                        description "Enable support for labeled-unicast IPv6 routes";
                    }

                } // container origin-validation

                ///nokia-conf/configure/router/bgp/neighbor/link-bandwidth
                container link-bandwidth {
                    description "Enter the link-bandwidth context";

                    ///nokia-conf/configure/router/bgp/neighbor/link-bandwidth/accept-from-ebgp
                    container accept-from-ebgp {
                        presence "Enable the accept-from-ebgp context";
                        description "Enable the accept-from-ebgp context";

                        ///nokia-conf/configure/router/bgp/neighbor/link-bandwidth/accept-from-ebgp/ipv4
                        leaf ipv4 {
                            type boolean;
                            default "false";
                            description "Support Link Bandwidth EC in IPv4 routes";
                        }

                        ///nokia-conf/configure/router/bgp/neighbor/link-bandwidth/accept-from-ebgp/ipv6
                        leaf ipv6 {
                            type boolean;
                            default "false";
                            description "Support Link Bandwidth EC in IPv6 routes";
                        }

                        ///nokia-conf/configure/router/bgp/neighbor/link-bandwidth/accept-from-ebgp/vpn-ipv4
                        leaf vpn-ipv4 {
                            type boolean;
                            default "false";
                            description "Support Link Bandwidth EC in VPN-IPv4 routes";
                        }

                        ///nokia-conf/configure/router/bgp/neighbor/link-bandwidth/accept-from-ebgp/vpn-ipv6
                        leaf vpn-ipv6 {
                            type boolean;
                            default "false";
                            description "Support Link Bandwidth EC in VPN-IPv6 routes";
                        }

                        ///nokia-conf/configure/router/bgp/neighbor/link-bandwidth/accept-from-ebgp/label-ipv4
                        leaf label-ipv4 {
                            type boolean;
                            default "false";
                            description "Support Link Bandwidth EC in label-IPv4 routes";
                        }

                        ///nokia-conf/configure/router/bgp/neighbor/link-bandwidth/accept-from-ebgp/label-ipv6
                        leaf label-ipv6 {
                            type boolean;
                            default "false";
                            description "Support Link Bandwidth EC in label-IPv6 routes";
                        }

                    } // container accept-from-ebgp

                    ///nokia-conf/configure/router/bgp/neighbor/link-bandwidth/add-to-received-ebgp
                    container add-to-received-ebgp {
                        presence "Enable the add-to-received-ebgp context";
                        description "Enable the add-to-received-ebgp context";

                        ///nokia-conf/configure/router/bgp/neighbor/link-bandwidth/add-to-received-ebgp/ipv4
                        leaf ipv4 {
                            type boolean;
                            default "false";
                            description "Support Link Bandwidth EC in IPv4 routes";
                        }

                        ///nokia-conf/configure/router/bgp/neighbor/link-bandwidth/add-to-received-ebgp/ipv6
                        leaf ipv6 {
                            type boolean;
                            default "false";
                            description "Support Link Bandwidth EC in IPv6 routes";
                        }

                        ///nokia-conf/configure/router/bgp/neighbor/link-bandwidth/add-to-received-ebgp/vpn-ipv4
                        leaf vpn-ipv4 {
                            type boolean;
                            default "false";
                            description "Support Link Bandwidth EC in VPN-IPv4 routes";
                        }

                        ///nokia-conf/configure/router/bgp/neighbor/link-bandwidth/add-to-received-ebgp/vpn-ipv6
                        leaf vpn-ipv6 {
                            type boolean;
                            default "false";
                            description "Support Link Bandwidth EC in VPN-IPv6 routes";
                        }

                        ///nokia-conf/configure/router/bgp/neighbor/link-bandwidth/add-to-received-ebgp/label-ipv4
                        leaf label-ipv4 {
                            type boolean;
                            default "false";
                            description "Support Link Bandwidth EC in label-IPv4 routes";
                        }

                        ///nokia-conf/configure/router/bgp/neighbor/link-bandwidth/add-to-received-ebgp/label-ipv6
                        leaf label-ipv6 {
                            type boolean;
                            default "false";
                            description "Support Link Bandwidth EC in label-IPv6 routes";
                        }

                    } // container add-to-received-ebgp

                    ///nokia-conf/configure/router/bgp/neighbor/link-bandwidth/aggregate-used-paths
                    container aggregate-used-paths {
                        presence "Enable the aggregate-used-paths context";
                        description "Enable the aggregate-used-paths context";

                        ///nokia-conf/configure/router/bgp/neighbor/link-bandwidth/aggregate-used-paths/ipv4
                        leaf ipv4 {
                            type boolean;
                            default "false";
                            description "Support Link Bandwidth EC in IPv4 routes";
                        }

                        ///nokia-conf/configure/router/bgp/neighbor/link-bandwidth/aggregate-used-paths/ipv6
                        leaf ipv6 {
                            type boolean;
                            default "false";
                            description "Support Link Bandwidth EC in IPv6 routes";
                        }

                        ///nokia-conf/configure/router/bgp/neighbor/link-bandwidth/aggregate-used-paths/vpn-ipv4
                        leaf vpn-ipv4 {
                            type boolean;
                            default "false";
                            description "Support Link Bandwidth EC in VPN-IPv4 routes";
                        }

                        ///nokia-conf/configure/router/bgp/neighbor/link-bandwidth/aggregate-used-paths/vpn-ipv6
                        leaf vpn-ipv6 {
                            type boolean;
                            default "false";
                            description "Support Link Bandwidth EC in VPN-IPv6 routes";
                        }

                        ///nokia-conf/configure/router/bgp/neighbor/link-bandwidth/aggregate-used-paths/label-ipv4
                        leaf label-ipv4 {
                            type boolean;
                            default "false";
                            description "Support Link Bandwidth EC in label-IPv4 routes";
                        }

                        ///nokia-conf/configure/router/bgp/neighbor/link-bandwidth/aggregate-used-paths/label-ipv6
                        leaf label-ipv6 {
                            type boolean;
                            default "false";
                            description "Support Link Bandwidth EC in label-IPv6 routes";
                        }

                    } // container aggregate-used-paths

                    ///nokia-conf/configure/router/bgp/neighbor/link-bandwidth/send-to-ebgp
                    container send-to-ebgp {
                        presence "Enable the send-to-ebgp context";
                        description "Enable the send-to-ebgp context";

                        ///nokia-conf/configure/router/bgp/neighbor/link-bandwidth/send-to-ebgp/ipv4
                        leaf ipv4 {
                            type boolean;
                            default "false";
                            description "Support Link Bandwidth EC in IPv4 routes";
                        }

                        ///nokia-conf/configure/router/bgp/neighbor/link-bandwidth/send-to-ebgp/ipv6
                        leaf ipv6 {
                            type boolean;
                            default "false";
                            description "Support Link Bandwidth EC in IPv6 routes";
                        }

                        ///nokia-conf/configure/router/bgp/neighbor/link-bandwidth/send-to-ebgp/vpn-ipv4
                        leaf vpn-ipv4 {
                            type boolean;
                            default "false";
                            description "Support Link Bandwidth EC in VPN-IPv4 routes";
                        }

                        ///nokia-conf/configure/router/bgp/neighbor/link-bandwidth/send-to-ebgp/vpn-ipv6
                        leaf vpn-ipv6 {
                            type boolean;
                            default "false";
                            description "Support Link Bandwidth EC in VPN-IPv6 routes";
                        }

                        ///nokia-conf/configure/router/bgp/neighbor/link-bandwidth/send-to-ebgp/label-ipv4
                        leaf label-ipv4 {
                            type boolean;
                            default "false";
                            description "Support Link Bandwidth EC in label-IPv4 routes";
                        }

                        ///nokia-conf/configure/router/bgp/neighbor/link-bandwidth/send-to-ebgp/label-ipv6
                        leaf label-ipv6 {
                            type boolean;
                            default "false";
                            description "Support Link Bandwidth EC in label-IPv6 routes";
                        }

                    } // container send-to-ebgp

                } // container link-bandwidth

                ///nokia-conf/configure/router/bgp/neighbor/send-communities
                container send-communities {
                    description "Enter the send-communities context";

                    ///nokia-conf/configure/router/bgp/neighbor/send-communities/standard
                    leaf standard {
                        type boolean;
                        description "Advertise the Communities attribute to peers";
                    }

                    ///nokia-conf/configure/router/bgp/neighbor/send-communities/extended
                    leaf extended {
                        type boolean;
                        description "Advertise the Extended Communities attribute to peers";
                    }

                    ///nokia-conf/configure/router/bgp/neighbor/send-communities/large
                    leaf large {
                        type boolean;
                        description "Advertise the Large Communities attribute to peers";
                    }

                } // container send-communities

                ///nokia-conf/configure/router/bgp/neighbor/error-handling
                container error-handling {
                    description "Enter the error-handling context";

                    ///nokia-conf/configure/router/bgp/neighbor/error-handling/update-fault-tolerance
                    leaf update-fault-tolerance {
                        type boolean;
                        description "Tolerate non-critical errors in UPDATE messages";
                    }

                } // container error-handling

                ///nokia-conf/configure/router/bgp/neighbor/damp-peer-oscillations
                container damp-peer-oscillations {
                    presence "Enable the damp-peer-oscillations context";
                    description "Enable the damp-peer-oscillations context";

                    ///nokia-conf/configure/router/bgp/neighbor/damp-peer-oscillations/error-interval
                    leaf error-interval {
                        type uint32 {
                            range "0..2048";
                        }
                        default "30";
                        description "Time after a reset that the session must be error-free";
                    }

                    ///nokia-conf/configure/router/bgp/neighbor/damp-peer-oscillations/idle-hold-time
                    container idle-hold-time {
                        description "Enter the idle-hold-time context";

                        ///nokia-conf/configure/router/bgp/neighbor/damp-peer-oscillations/idle-hold-time/initial-wait
                        leaf initial-wait {
                            type uint32 {
                                range "0..2048";
                            }
                            default "0";
                            description "Time session remains in idle state after stabilization";
                        }

                        ///nokia-conf/configure/router/bgp/neighbor/damp-peer-oscillations/idle-hold-time/second-wait
                        leaf second-wait {
                            type uint32 {
                                range "1..2048";
                            }
                            default "5";
                            description "Time that doubles after each repeated session failure";
                        }

                        ///nokia-conf/configure/router/bgp/neighbor/damp-peer-oscillations/idle-hold-time/max-wait
                        leaf max-wait {
                            type uint32 {
                                range "1..2048";
                            }
                            default "60";
                            description "Maximum session idle time after repeated instability";
                        }

                    } // container idle-hold-time

                } // container damp-peer-oscillations

                ///nokia-conf/configure/router/bgp/neighbor/bfd-strict-mode
                container bfd-strict-mode {
                    description "Enter the bfd-strict-mode context";

                    ///nokia-conf/configure/router/bgp/neighbor/bfd-strict-mode/next-hop-reachability
                    leaf next-hop-reachability {
                        type boolean;
                        description "Consider next hop unreachable if BFD session is down";
                    }

                    ///nokia-conf/configure/router/bgp/neighbor/bfd-strict-mode/advertise
                    container advertise {
                        presence "Enable the advertise context";
                        description "Enable the advertise context";

                        ///nokia-conf/configure/router/bgp/neighbor/bfd-strict-mode/advertise/holdtime
                        leaf holdtime {
                            type uint16 {
                                range "1..65535";
                            }
                            units "seconds";
                            default "30";
                            description "Maximum time BGP waits for the BFD session to come up";
                        }

                    } // container advertise

                } // container bfd-strict-mode

                ///nokia-conf/configure/router/bgp/neighbor/hold-time
                container hold-time {
                    description "Enter the hold-time context";

                    ///nokia-conf/configure/router/bgp/neighbor/hold-time/seconds
                    leaf seconds {
                        type int32 {
                            range "0|3..65535";
                        }
                        description "Maximum hold time between successive messages";
                    }

                    ///nokia-conf/configure/router/bgp/neighbor/hold-time/minimum-hold-time
                    leaf minimum-hold-time {
                        type int32 {
                            range "0|3..65536";
                        }
                        default "0";
                        description "Minimum time BGP waits between successive messages";
                    }

                } // container hold-time

                ///nokia-conf/configure/router/bgp/neighbor/family
                container family {
                    presence "Enable the family context";
                    description "Enable the family context";

                    ///nokia-conf/configure/router/bgp/neighbor/family/ipv4
                    leaf ipv4 {
                        type boolean;
                        default "false";
                        description "Add support for the IPv4 address family";
                    }

                    ///nokia-conf/configure/router/bgp/neighbor/family/vpn-ipv4
                    leaf vpn-ipv4 {
                        type boolean;
                        default "false";
                        description "Advertise MP-BGP support for IPv4 VPN address family";
                    }

                    ///nokia-conf/configure/router/bgp/neighbor/family/ipv6
                    leaf ipv6 {
                        type boolean;
                        default "false";
                        description "Advertise MP-BGP support for the IPv6 address family";
                    }

                    ///nokia-conf/configure/router/bgp/neighbor/family/mcast-ipv4
                    leaf mcast-ipv4 {
                        type boolean;
                        default "false";
                        description "Advertise support for the MCAST-IPv4 address family";
                    }

                    ///nokia-conf/configure/router/bgp/neighbor/family/vpn-ipv6
                    leaf vpn-ipv6 {
                        type boolean;
                        default "false";
                        description "Advertise MP-BGP support for IPv6 VPN address family";
                    }

                    ///nokia-conf/configure/router/bgp/neighbor/family/l2-vpn
                    leaf l2-vpn {
                        type boolean;
                        default "false";
                        description "Advertise MP-BGP support for the L2-VPN address family";
                    }

                    ///nokia-conf/configure/router/bgp/neighbor/family/mvpn-ipv4
                    leaf mvpn-ipv4 {
                        type boolean;
                        default "false";
                        description "Advertise support for the IPv4 MCAST VPN address family";
                    }

                    ///nokia-conf/configure/router/bgp/neighbor/family/mdt-safi
                    leaf mdt-safi {
                        type boolean;
                        default "false";
                        description "Advertise MP-BGP support for MDT-SAFI address family";
                    }

                    ///nokia-conf/configure/router/bgp/neighbor/family/ms-pw
                    leaf ms-pw {
                        type boolean;
                        default "false";
                        description "Advertise support for multi-segment PW address family";
                    }

                    ///nokia-conf/configure/router/bgp/neighbor/family/flow-ipv4
                    leaf flow-ipv4 {
                        type boolean;
                        default "false";
                        description "Advertise support for the flowspec-IPv4 address family";
                    }

                    ///nokia-conf/configure/router/bgp/neighbor/family/route-target
                    leaf route-target {
                        type boolean;
                        default "false";
                        description "Advertise MP-BGP support for RT constraint routes";
                    }

                    ///nokia-conf/configure/router/bgp/neighbor/family/mcast-vpn-ipv4
                    leaf mcast-vpn-ipv4 {
                        type boolean;
                        default "false";
                        description "Advertise support for the IPv4 VPN MCAST address family";
                    }

                    ///nokia-conf/configure/router/bgp/neighbor/family/mvpn-ipv6
                    leaf mvpn-ipv6 {
                        type boolean;
                        default "false";
                        description "Advertise support for the IPv6 MCAST VPN address family";
                    }

                    ///nokia-conf/configure/router/bgp/neighbor/family/flow-ipv6
                    leaf flow-ipv6 {
                        type boolean;
                        default "false";
                        description "Advertise support for the flowspec-IPv6 address family";
                    }

                    ///nokia-conf/configure/router/bgp/neighbor/family/evpn
                    leaf evpn {
                        type boolean;
                        default "false";
                        description "Advertise MP-BGP support for the EVPN address family";
                    }

                    ///nokia-conf/configure/router/bgp/neighbor/family/mcast-ipv6
                    leaf mcast-ipv6 {
                        type boolean;
                        default "false";
                        description "Advertise support for the MCAST-IPv6 address family";
                    }

                    ///nokia-conf/configure/router/bgp/neighbor/family/label-ipv4
                    leaf label-ipv4 {
                        type boolean;
                        default "false";
                        description "Advertise support for the label-IPv4 address family";
                    }

                    ///nokia-conf/configure/router/bgp/neighbor/family/label-ipv6
                    leaf label-ipv6 {
                        type boolean;
                        default "false";
                        description "Advertise support for the label-IPv6 address family";
                    }

                    ///nokia-conf/configure/router/bgp/neighbor/family/bgp-ls
                    leaf bgp-ls {
                        type boolean;
                        default "false";
                        description "Advertise MP-BGP support for the BGP-LS address family";
                    }

                    ///nokia-conf/configure/router/bgp/neighbor/family/mcast-vpn-ipv6
                    leaf mcast-vpn-ipv6 {
                        type boolean;
                        default "false";
                        description "Advertise support for the IPv6 VPN MCAST address family";
                    }

                    ///nokia-conf/configure/router/bgp/neighbor/family/sr-policy-ipv4
                    leaf sr-policy-ipv4 {
                        type boolean;
                        default "false";
                        description "Advertise MP-BGP support for the SR-policy-IPv4 family";
                    }

                    ///nokia-conf/configure/router/bgp/neighbor/family/sr-policy-ipv6
                    leaf sr-policy-ipv6 {
                        type boolean;
                        default "false";
                        description "Advertise MP-BGP support for the SR-policy-IPv6 family";
                    }

                    ///nokia-conf/configure/router/bgp/neighbor/family/flow-vpn-ipv4
                    leaf flow-vpn-ipv4 {
                        type boolean;
                        default "false";
                        description "Advertise support for FlowSpec-VPN IPv4 address family";
                    }

                    ///nokia-conf/configure/router/bgp/neighbor/family/flow-vpn-ipv6
                    leaf flow-vpn-ipv6 {
                        type boolean;
                        default "false";
                        description "Advertise support for FlowSpec-VPN IPv6 address family";
                    }

                } // container family

                ///nokia-conf/configure/router/bgp/neighbor/send-default
                container send-default {
                    presence "Enable the send-default context";
                    description "Enable the send-default context";

                    ///nokia-conf/configure/router/bgp/neighbor/send-default/ipv4
                    leaf ipv4 {
                        type boolean;
                        default "false";
                        description "Enable IPv4 family type";
                    }

                    ///nokia-conf/configure/router/bgp/neighbor/send-default/ipv6
                    leaf ipv6 {
                        type boolean;
                        default "false";
                        description "Enable IPv6 family type";
                    }

                    ///nokia-conf/configure/router/bgp/neighbor/send-default/export-policy
                    leaf export-policy {
                        type leafref {
                            path "../../../../../policy-options/policy-statement/name";
                        }
                        description "Export policy name";
                    }

                } // container send-default

                ///nokia-conf/configure/router/bgp/neighbor/default-preference
                container default-preference {
                    description "Enter the default-preference context";

                    ///nokia-conf/configure/router/bgp/neighbor/default-preference/ebgp
                    leaf ebgp {
                        type uint32 {
                            range "0..255";
                        }
                        description "Default preference for EBGP";
                    }

                    ///nokia-conf/configure/router/bgp/neighbor/default-preference/ibgp
                    leaf ibgp {
                        type uint32 {
                            range "0..255";
                        }
                        description "Default preference for IBGP";
                    }

                } // container default-preference

                ///nokia-conf/configure/router/bgp/neighbor/default-label-preference
                container default-label-preference {
                    description "Enter the default-label-preference context";

                    ///nokia-conf/configure/router/bgp/neighbor/default-label-preference/ebgp
                    leaf ebgp {
                        type uint32 {
                            range "0..255";
                        }
                        description "Default preference for EBGP";
                    }

                    ///nokia-conf/configure/router/bgp/neighbor/default-label-preference/ibgp
                    leaf ibgp {
                        type uint32 {
                            range "0..255";
                        }
                        description "Default preference for IBGP";
                    }

                } // container default-label-preference

                ///nokia-conf/configure/router/bgp/neighbor/remove-private
                container remove-private {
                    presence "Enable the remove-private context";
                    description "Enable the remove-private context";

                    ///nokia-conf/configure/router/bgp/neighbor/remove-private/limited
                    leaf limited {
                        type boolean;
                        default "false";
                        description "Remove private ASNs up to first public ASN encountered";
                    }

                    ///nokia-conf/configure/router/bgp/neighbor/remove-private/skip-peer-as
                    leaf skip-peer-as {
                        type boolean;
                        default "false";
                        description "Keep private ASN if it is the same as the BGP peer ASN";
                    }

                    ///nokia-conf/configure/router/bgp/neighbor/remove-private/replace
                    leaf replace {
                        type boolean;
                        default "false";
                        description "Replace private ASN with global ASN before advertising";
                    }

                } // container remove-private

                ///nokia-conf/configure/router/bgp/neighbor/cluster
                container cluster {
                    description "Enter the cluster context";

                    ///nokia-conf/configure/router/bgp/neighbor/cluster/cluster-id
                    leaf cluster-id {
                        type types-sros:ipv4-address;
                        description "Route reflector cluster ID";
                    }

                    ///nokia-conf/configure/router/bgp/neighbor/cluster/orr-location
                    leaf orr-location {
                        type uint32 {
                            range "1..255";
                        }
                        description "Optimal route reflection location for the cluster";
                    }

                    ///nokia-conf/configure/router/bgp/neighbor/cluster/allow-local-fallback
                    leaf allow-local-fallback {
                        type boolean;
                        default "false";
                        description "Allow fallback to RR topology";
                    }

                } // container cluster

                ///nokia-conf/configure/router/bgp/neighbor/ebgp-default-reject-policy
                container ebgp-default-reject-policy {
                    presence "Enable the ebgp-default-reject-policy context";
                    description "Enable the ebgp-default-reject-policy context";

                    ///nokia-conf/configure/router/bgp/neighbor/ebgp-default-reject-policy/import
                    leaf import {
                        type boolean;
                        default "true";
                        description "Enable default reject import policy for external peers";
                    }

                    ///nokia-conf/configure/router/bgp/neighbor/ebgp-default-reject-policy/export
                    leaf export {
                        type boolean;
                        default "true";
                        description "Enable default reject export policy for external peers";
                    }

                } // container ebgp-default-reject-policy

                ///nokia-conf/configure/router/bgp/neighbor/local-as
                container local-as {
                    description "Enter the local-as context";

                    ///nokia-conf/configure/router/bgp/neighbor/local-as/as-number
                    leaf as-number {
                        type uint32 {
                            range "1..4294967295";
                        }
                        description "Local (or virtual) BGP AS number";
                    }

                    ///nokia-conf/configure/router/bgp/neighbor/local-as/private
                    leaf private {
                        type boolean;
                        default "false";
                        description "Hide the local ASN in sent paths learned from peering";
                    }

                    ///nokia-conf/configure/router/bgp/neighbor/local-as/prepend-global-as
                    leaf prepend-global-as {
                        type boolean;
                        default "true";
                        description "Prepend global ASN when advertising routes to BGP peer";
                    }

                } // container local-as

                ///nokia-conf/configure/router/bgp/neighbor/add-paths
                container add-paths {
                    presence "Enable the add-paths context";
                    description "Enable the add-paths context";

                    ///nokia-conf/configure/router/bgp/neighbor/add-paths/ipv4
                    container ipv4 {
                        description "Enter the ipv4 context";

                        ///nokia-conf/configure/router/bgp/neighbor/add-paths/ipv4/send
                        leaf send {
                            type types-bgp:add-paths-send-limit;
                            description "Maximum paths per unlabeled IPv4 unicast prefix";
                        }

                        ///nokia-conf/configure/router/bgp/neighbor/add-paths/ipv4/receive
                        leaf receive {
                            type boolean;
                            default "false";
                            description "Receive multiple labeled-unicast routes per IPv4 prefix";
                        }

                    } // container ipv4

                    ///nokia-conf/configure/router/bgp/neighbor/add-paths/ipv6
                    container ipv6 {
                        description "Enter the ipv6 context";

                        ///nokia-conf/configure/router/bgp/neighbor/add-paths/ipv6/send
                        leaf send {
                            type types-bgp:add-paths-send-limit;
                            description "Maximum paths per unlabeled IPv6 unicast prefix";
                        }

                        ///nokia-conf/configure/router/bgp/neighbor/add-paths/ipv6/receive
                        leaf receive {
                            type boolean;
                            default "false";
                            description "Receive multiple routes per IPv6 prefix";
                        }

                    } // container ipv6

                    ///nokia-conf/configure/router/bgp/neighbor/add-paths/label-ipv4
                    container label-ipv4 {
                        description "Enter the label-ipv4 context";

                        ///nokia-conf/configure/router/bgp/neighbor/add-paths/label-ipv4/send
                        leaf send {
                            type types-bgp:add-paths-send-limit;
                            description "Maximum paths per labeled IPv4 unicast prefix";
                        }

                        ///nokia-conf/configure/router/bgp/neighbor/add-paths/label-ipv4/receive
                        leaf receive {
                            type boolean;
                            default "false";
                            description "Receive multiple labeled-unicast routes per IPv4 prefix";
                        }

                    } // container label-ipv4

                    ///nokia-conf/configure/router/bgp/neighbor/add-paths/label-ipv6
                    container label-ipv6 {
                        description "Enter the label-ipv6 context";

                        ///nokia-conf/configure/router/bgp/neighbor/add-paths/label-ipv6/send
                        leaf send {
                            type types-bgp:add-paths-send-limit;
                            description "Maximum paths per labeled IPv6 unicast prefix";
                        }

                        ///nokia-conf/configure/router/bgp/neighbor/add-paths/label-ipv6/receive
                        leaf receive {
                            type boolean;
                            default "false";
                            description "Receive multiple labeled-unicast routes per IPv6 prefix";
                        }

                    } // container label-ipv6

                    ///nokia-conf/configure/router/bgp/neighbor/add-paths/vpn-ipv4
                    container vpn-ipv4 {
                        description "Enter the vpn-ipv4 context";

                        ///nokia-conf/configure/router/bgp/neighbor/add-paths/vpn-ipv4/send
                        leaf send {
                            type types-bgp:add-paths-send-limit;
                            description "Maximum paths per VPN-IPv4 prefix";
                        }

                        ///nokia-conf/configure/router/bgp/neighbor/add-paths/vpn-ipv4/receive
                        leaf receive {
                            type boolean;
                            default "false";
                            description "Receive multiple routes per VPN-IPv4 prefix";
                        }

                    } // container vpn-ipv4

                    ///nokia-conf/configure/router/bgp/neighbor/add-paths/vpn-ipv6
                    container vpn-ipv6 {
                        description "Enter the vpn-ipv6 context";

                        ///nokia-conf/configure/router/bgp/neighbor/add-paths/vpn-ipv6/send
                        leaf send {
                            type types-bgp:add-paths-send-limit;
                            description "Maximum paths per VPN-IPv6 prefix";
                        }

                        ///nokia-conf/configure/router/bgp/neighbor/add-paths/vpn-ipv6/receive
                        leaf receive {
                            type boolean;
                            default "false";
                            description "Receive multiple routes per VPN-IPv6 prefix";
                        }

                    } // container vpn-ipv6

                    ///nokia-conf/configure/router/bgp/neighbor/add-paths/mvpn-ipv4
                    container mvpn-ipv4 {
                        description "Enter the mvpn-ipv4 context";

                        ///nokia-conf/configure/router/bgp/neighbor/add-paths/mvpn-ipv4/send
                        leaf send {
                            type int32 {
                                range "1..16";
                            }
                            description "Maximum paths per multicast VPN IPv4 prefix";
                        }

                        ///nokia-conf/configure/router/bgp/neighbor/add-paths/mvpn-ipv4/receive
                        leaf receive {
                            type boolean;
                            default "false";
                            description "Receive multiple multicast VPN routes per IPv4 prefix";
                        }

                    } // container mvpn-ipv4

                    ///nokia-conf/configure/router/bgp/neighbor/add-paths/mvpn-ipv6
                    container mvpn-ipv6 {
                        description "Enter the mvpn-ipv6 context";

                        ///nokia-conf/configure/router/bgp/neighbor/add-paths/mvpn-ipv6/send
                        leaf send {
                            type int32 {
                                range "1..16";
                            }
                            description "Maximum paths per multicast VPN IPv6 prefix";
                        }

                        ///nokia-conf/configure/router/bgp/neighbor/add-paths/mvpn-ipv6/receive
                        leaf receive {
                            type boolean;
                            default "false";
                            description "Receive multiple multicast VPN routes per IPv6 prefix";
                        }

                    } // container mvpn-ipv6

                    ///nokia-conf/configure/router/bgp/neighbor/add-paths/mcast-vpn-ipv4
                    container mcast-vpn-ipv4 {
                        description "Enter the mcast-vpn-ipv4 context";

                        ///nokia-conf/configure/router/bgp/neighbor/add-paths/mcast-vpn-ipv4/send
                        leaf send {
                            type int32 {
                                range "1..16";
                            }
                            description "Maximum paths per multicast IPv4 VPN prefix";
                        }

                        ///nokia-conf/configure/router/bgp/neighbor/add-paths/mcast-vpn-ipv4/receive
                        leaf receive {
                            type boolean;
                            default "false";
                            description "Receive multiple multicast routes per IPv4 VPN prefix";
                        }

                    } // container mcast-vpn-ipv4

                    ///nokia-conf/configure/router/bgp/neighbor/add-paths/mcast-vpn-ipv6
                    container mcast-vpn-ipv6 {
                        description "Enter the mcast-vpn-ipv6 context";

                        ///nokia-conf/configure/router/bgp/neighbor/add-paths/mcast-vpn-ipv6/send
                        leaf send {
                            type int32 {
                                range "1..16";
                            }
                            description "Maximum paths per multicast IPv6 VPN prefix";
                        }

                        ///nokia-conf/configure/router/bgp/neighbor/add-paths/mcast-vpn-ipv6/receive
                        leaf receive {
                            type boolean;
                            default "false";
                            description "Receive multiple multicast routes per IPv6 VPN prefix";
                        }

                    } // container mcast-vpn-ipv6

                    ///nokia-conf/configure/router/bgp/neighbor/add-paths/evpn
                    container evpn {
                        description "Enter the evpn context";

                        ///nokia-conf/configure/router/bgp/neighbor/add-paths/evpn/send
                        leaf send {
                            type types-bgp:add-paths-send-limit;
                            description "Maximum paths per EVPN prefix to Add-Path peers";
                        }

                        ///nokia-conf/configure/router/bgp/neighbor/add-paths/evpn/receive
                        leaf receive {
                            type boolean;
                            default "false";
                            description "Receive multiple EVPN paths per prefix from a peer";
                        }

                    } // container evpn

                } // container add-paths

                ///nokia-conf/configure/router/bgp/neighbor/import
                container import {
                    presence "Enable the import context";
                    description "Enable the import context";

                    ///nokia-conf/configure/router/bgp/neighbor/import/policy
                    leaf-list policy {
                        type union {
                            type types-sros:policy-expr-string;
                            type string;
                        }
                        min-elements 1;
                        max-elements 15;
                        ordered-by user;
                        description "Names of the BGP import policies";
                    }

                    ///nokia-conf/configure/router/bgp/neighbor/import/apply-groups
                    leaf-list apply-groups {
                        type leafref {
                            path "../../../../../groups/group/name";
                        }
                        max-elements 8;
                        ordered-by user;
                        description "Apply a configuration group at this level";
                    }

                    ///nokia-conf/configure/router/bgp/neighbor/import/apply-groups-exclude
                    leaf-list apply-groups-exclude {
                        type leafref {
                            path "../../../../../groups/group/name";
                        }
                        max-elements 8;
                        ordered-by user;
                        description "Exclude a configuration group at this level";
                    }

                } // container import

                ///nokia-conf/configure/router/bgp/neighbor/export
                container export {
                    presence "Enable the export context";
                    description "Enable the export context";

                    ///nokia-conf/configure/router/bgp/neighbor/export/policy
                    leaf-list policy {
                        type union {
                            type types-sros:policy-expr-string;
                            type string;
                        }
                        min-elements 1;
                        max-elements 15;
                        ordered-by user;
                        description "BGP export policy name";
                    }

                    ///nokia-conf/configure/router/bgp/neighbor/export/apply-groups
                    leaf-list apply-groups {
                        type leafref {
                            path "../../../../../groups/group/name";
                        }
                        max-elements 8;
                        ordered-by user;
                        description "Apply a configuration group at this level";
                    }

                    ///nokia-conf/configure/router/bgp/neighbor/export/apply-groups-exclude
                    leaf-list apply-groups-exclude {
                        type leafref {
                            path "../../../../../groups/group/name";
                        }
                        max-elements 8;
                        ordered-by user;
                        description "Exclude a configuration group at this level";
                    }

                } // container export

                ///nokia-conf/configure/router/bgp/neighbor/extended-nh-encoding
                container extended-nh-encoding {
                    presence "Enable the extended-nh-encoding context";
                    description "Enable the extended-nh-encoding context";

                    ///nokia-conf/configure/router/bgp/neighbor/extended-nh-encoding/vpn-ipv4
                    leaf vpn-ipv4 {
                        type boolean;
                        default "false";
                        description "Advertise encoding capability for VPN-IPv4 routes";
                    }

                    ///nokia-conf/configure/router/bgp/neighbor/extended-nh-encoding/label-ipv4
                    leaf label-ipv4 {
                        type boolean;
                        default "false";
                        description "Advertise encoding capability for label-IPv4 routes";
                    }

                    ///nokia-conf/configure/router/bgp/neighbor/extended-nh-encoding/ipv4
                    leaf ipv4 {
                        type boolean;
                        default "false";
                        description "Advertise encoding capability for IPv4 routes";
                    }

                } // container extended-nh-encoding

                ///nokia-conf/configure/router/bgp/neighbor/advertise-ipv6-next-hops
                container advertise-ipv6-next-hops {
                    presence "Enable the advertise-ipv6-next-hops context";
                    description "Enable the advertise-ipv6-next-hops context";

                    ///nokia-conf/configure/router/bgp/neighbor/advertise-ipv6-next-hops/vpn-ipv6
                    leaf vpn-ipv6 {
                        type boolean;
                        default "false";
                        description "Advertise VPN IPv6 route with IPv6 next-hop address";
                    }

                    ///nokia-conf/configure/router/bgp/neighbor/advertise-ipv6-next-hops/label-ipv6
                    leaf label-ipv6 {
                        type boolean;
                        default "false";
                        description "Advertise label IPv6 route with IPv6 next-hop address";
                    }

                    ///nokia-conf/configure/router/bgp/neighbor/advertise-ipv6-next-hops/evpn
                    leaf evpn {
                        type boolean;
                        default "false";
                        description "Advertise EVPN route with IPv6 next-hop address";
                    }

                    ///nokia-conf/configure/router/bgp/neighbor/advertise-ipv6-next-hops/vpn-ipv4
                    leaf vpn-ipv4 {
                        type boolean;
                        default "false";
                        description "Advertise VPN IPv4 route with IPv6 next-hop address";
                    }

                    ///nokia-conf/configure/router/bgp/neighbor/advertise-ipv6-next-hops/label-ipv4
                    leaf label-ipv4 {
                        type boolean;
                        default "false";
                        description "Advertise label IPv4 route with IPv6 next-hop address";
                    }

                    ///nokia-conf/configure/router/bgp/neighbor/advertise-ipv6-next-hops/ipv4
                    leaf ipv4 {
                        type boolean;
                        default "false";
                        description "Advertise IPv4 route with IPv6 next-hop address";
                    }

                } // container advertise-ipv6-next-hops

                ///nokia-conf/configure/router/bgp/neighbor/graceful-restart
                container graceful-restart {
                    presence "Enable the graceful-restart context";
                    description "Enable the graceful-restart context";

                    ///nokia-conf/configure/router/bgp/neighbor/graceful-restart/restart-time
                    leaf restart-time {
                        type uint32 {
                            range "0..4095";
                        }
                        default "300";
                        description "Restart time advertised by GR capability";
                    }

                    ///nokia-conf/configure/router/bgp/neighbor/graceful-restart/stale-routes-time
                    leaf stale-routes-time {
                        type uint32 {
                            range "1..3600";
                        }
                        default "360";
                        description "Maximum time to maintain routes after graceful restart";
                    }

                    ///nokia-conf/configure/router/bgp/neighbor/graceful-restart/gr-notification
                    leaf gr-notification {
                        type boolean;
                        default "false";
                        description "Perform graceful restart procedures after NOTIFICATION";
                    }

                    ///nokia-conf/configure/router/bgp/neighbor/graceful-restart/long-lived
                    container long-lived {
                        presence "Enable the long-lived context";
                        description "Enable the long-lived context";

                        ///nokia-conf/configure/router/bgp/neighbor/graceful-restart/long-lived/advertised-stale-time
                        leaf advertised-stale-time {
                            type uint32 {
                                range "0..16777215";
                            }
                            default "86400";
                            description "Advertised long-lived stale time for LLGR routes";
                        }

                        ///nokia-conf/configure/router/bgp/neighbor/graceful-restart/long-lived/helper-override-stale-time
                        leaf helper-override-stale-time {
                            type uint32 {
                                range "0..16777215";
                            }
                            description "Locally-configured stale routes override time";
                        }

                        ///nokia-conf/configure/router/bgp/neighbor/graceful-restart/long-lived/helper-override-restart-time
                        leaf helper-override-restart-time {
                            type uint32 {
                                range "0..4095";
                            }
                            description "Locally-configured override for restart time";
                        }

                        ///nokia-conf/configure/router/bgp/neighbor/graceful-restart/long-lived/forwarding-bits-set
                        leaf forwarding-bits-set {
                            type enumeration {
                                enum none                           { value 0; }
                                enum all                            { value 1; }
                                enum non-fwd                        { value 2; }
                            }
                            default "none";
                            description "BGP LLGR forwarding-bit behavior for address family";
                        }

                        ///nokia-conf/configure/router/bgp/neighbor/graceful-restart/long-lived/advertise-stale-to-all-neighbors
                        leaf advertise-stale-to-all-neighbors {
                            type boolean;
                            default "false";
                            description "Advertise stale routes to all BGP peers";
                        }

                        ///nokia-conf/configure/router/bgp/neighbor/graceful-restart/long-lived/without-no-export
                        leaf without-no-export {
                            type boolean;
                            default "false";
                            description "Advertise LLGR stale routes to non-LLGR peers";
                        }

                        ///nokia-conf/configure/router/bgp/neighbor/graceful-restart/long-lived/family
                        list family {
                            key "family-type";
                            description "Enter the family list instance";

                            ///nokia-conf/configure/router/bgp/neighbor/graceful-restart/long-lived/family/family-type
                            leaf family-type {
                                type types-bgp:llgr-family-identifiers;
                                description "Family type for family-specific LLGR configuration";
                            }

                            ///nokia-conf/configure/router/bgp/neighbor/graceful-restart/long-lived/family/advertised-stale-time
                            leaf advertised-stale-time {
                                type uint32 {
                                    range "0..16777215";
                                }
                                default "86400";
                                description "LLGR stale routes time for family override";
                            }

                            ///nokia-conf/configure/router/bgp/neighbor/graceful-restart/long-lived/family/helper-override-stale-time
                            leaf helper-override-stale-time {
                                type uint32 {
                                    range "0..16777216";
                                }
                                default "16777216";
                                description "Locally-configured stale routes override time";
                            }

                            ///nokia-conf/configure/router/bgp/neighbor/graceful-restart/long-lived/family/apply-groups
                            leaf-list apply-groups {
                                type leafref {
                                    path "../../../../../../../groups/group/name";
                                }
                                max-elements 8;
                                ordered-by user;
                                description "Apply a configuration group at this level";
                            }

                            ///nokia-conf/configure/router/bgp/neighbor/graceful-restart/long-lived/family/apply-groups-exclude
                            leaf-list apply-groups-exclude {
                                type leafref {
                                    path "../../../../../../../groups/group/name";
                                }
                                max-elements 8;
                                ordered-by user;
                                description "Exclude a configuration group at this level";
                            }

                        } // list family

                    } // container long-lived

                } // container graceful-restart

                ///nokia-conf/configure/router/bgp/neighbor/outbound-route-filtering
                container outbound-route-filtering {
                    presence "Enable the outbound-route-filtering context";
                    description "Enable the outbound-route-filtering context";

                    ///nokia-conf/configure/router/bgp/neighbor/outbound-route-filtering/extended-community
                    container extended-community {
                        presence "Enable the extended-community context";
                        description "Enable the extended-community context";

                        ///nokia-conf/configure/router/bgp/neighbor/outbound-route-filtering/extended-community/accept-orf
                        leaf accept-orf {
                            type boolean;
                            description "Negotiate with peer to accept BGP ORF filters";
                        }

                        ///nokia-conf/configure/router/bgp/neighbor/outbound-route-filtering/extended-community/send-orf
                        container send-orf {
                            presence "Enable the send-orf context";
                            description "Enable the send-orf context";

                            ///nokia-conf/configure/router/bgp/neighbor/outbound-route-filtering/extended-community/send-orf/route-target
                            list route-target {
                                key "community-name";
                                description "Add a list entry for route-target";

                                ///nokia-conf/configure/router/bgp/neighbor/outbound-route-filtering/extended-community/send-orf/route-target/community-name
                                leaf community-name {
                                    type types-sros:named-item;
                                    description "Route target community name";
                                }

                            } // list route-target

                        } // container send-orf

                    } // container extended-community

                } // container outbound-route-filtering

                ///nokia-conf/configure/router/bgp/neighbor/monitor
                container monitor {
                    presence "Enable the monitor context";
                    description "Enable the monitor context";

                    ///nokia-conf/configure/router/bgp/neighbor/monitor/all-stations
                    leaf all-stations {
                        type boolean;
                        default "false";
                        description "Send BMP messages to all configured stations";
                    }

                    ///nokia-conf/configure/router/bgp/neighbor/monitor/admin-state
                    leaf admin-state {
                        type types-sros:admin-state;
                        default "disable";
                        description "Administrative state of BMP monitoring";
                    }

                    ///nokia-conf/configure/router/bgp/neighbor/monitor/apply-groups
                    leaf-list apply-groups {
                        type leafref {
                            path "../../../../../groups/group/name";
                        }
                        max-elements 8;
                        ordered-by user;
                        description "Apply a configuration group at this level";
                    }

                    ///nokia-conf/configure/router/bgp/neighbor/monitor/apply-groups-exclude
                    leaf-list apply-groups-exclude {
                        type leafref {
                            path "../../../../../groups/group/name";
                        }
                        max-elements 8;
                        ordered-by user;
                        description "Exclude a configuration group at this level";
                    }

                    ///nokia-conf/configure/router/bgp/neighbor/monitor/route-monitoring
                    container route-monitoring {
                        description "Enter the route-monitoring context";

                        ///nokia-conf/configure/router/bgp/neighbor/monitor/route-monitoring/pre-policy
                        leaf pre-policy {
                            type boolean;
                            default "false";
                            description "Allow pre-policy route-monitoring messages to be sent";
                        }

                        ///nokia-conf/configure/router/bgp/neighbor/monitor/route-monitoring/post-policy
                        leaf post-policy {
                            type boolean;
                            default "false";
                            description "Allow post-policy route-monitoring messages to be sent";
                        }

                    } // container route-monitoring

                    ///nokia-conf/configure/router/bgp/neighbor/monitor/station
                    list station {
                        key "station-name";
                        max-elements 8;
                        description "Add a list entry for station";

                        ///nokia-conf/configure/router/bgp/neighbor/monitor/station/station-name
                        leaf station-name {
                            type leafref {
                                path "../../../../../../bmp/station/name";
                            }
                            description "BMP monitoring station";
                        }

                    } // list station

                } // container monitor

                ///nokia-conf/configure/router/bgp/neighbor/prefix-limit
                list prefix-limit {
                    key "family";
                    description "Enter the prefix-limit list instance";

                    ///nokia-conf/configure/router/bgp/neighbor/prefix-limit/family
                    leaf family {
                        type types-bgp:ip-family-identifier;
                        description "Address family to which the limit applies";
                    }

                    ///nokia-conf/configure/router/bgp/neighbor/prefix-limit/maximum
                    leaf maximum {
                        type uint32 {
                            range "1..4294967295";
                        }
                        mandatory true;
                        description "Maximum number of routes to be learned from a peer";
                    }

                    ///nokia-conf/configure/router/bgp/neighbor/prefix-limit/log-only
                    leaf log-only {
                        type boolean;
                        default "false";
                        description "Send warning message at threshold instead of take-down";
                    }

                    ///nokia-conf/configure/router/bgp/neighbor/prefix-limit/threshold
                    leaf threshold {
                        type uint32 {
                            range "1..100";
                        }
                        default "90";
                        description "Percentage threshold that triggers a warning message";
                    }

                    ///nokia-conf/configure/router/bgp/neighbor/prefix-limit/idle-timeout
                    leaf idle-timeout {
                        type int32 {
                            range "1..1024";
                        }
                        description "Time which BGP peering remains idle before reconnecting";
                    }

                    ///nokia-conf/configure/router/bgp/neighbor/prefix-limit/post-import
                    leaf post-import {
                        type boolean;
                        default "false";
                        description "Apply limit only to routes accepted by import policies";
                    }

                    ///nokia-conf/configure/router/bgp/neighbor/prefix-limit/hold-excess
                    leaf hold-excess {
                        type int32 {
                            range "1..100";
                        }
                        description "Percentage of maximum routes to install in route table";
                    }

                    ///nokia-conf/configure/router/bgp/neighbor/prefix-limit/apply-groups
                    leaf-list apply-groups {
                        type leafref {
                            path "../../../../../groups/group/name";
                        }
                        max-elements 8;
                        ordered-by user;
                        description "Apply a configuration group at this level";
                    }

                    ///nokia-conf/configure/router/bgp/neighbor/prefix-limit/apply-groups-exclude
                    leaf-list apply-groups-exclude {
                        type leafref {
                            path "../../../../../groups/group/name";
                        }
                        max-elements 8;
                        ordered-by user;
                        description "Exclude a configuration group at this level";
                    }

                } // list prefix-limit

                ///nokia-conf/configure/router/bgp/neighbor/egress-engineering
                container egress-engineering {
                    presence "Enable the egress-engineering context";
                    description "Enable the egress-engineering context";

                    ///nokia-conf/configure/router/bgp/neighbor/egress-engineering/admin-state
                    leaf admin-state {
                        type types-sros:admin-state;
                        default "disable";
                        description "Administrative state of BGP egress engineering";
                    }

                    ///nokia-conf/configure/router/bgp/neighbor/egress-engineering/apply-groups
                    leaf-list apply-groups {
                        type leafref {
                            path "../../../../../groups/group/name";
                        }
                        max-elements 8;
                        ordered-by user;
                        description "Apply a configuration group at this level";
                    }

                    ///nokia-conf/configure/router/bgp/neighbor/egress-engineering/apply-groups-exclude
                    leaf-list apply-groups-exclude {
                        type leafref {
                            path "../../../../../groups/group/name";
                        }
                        max-elements 8;
                        ordered-by user;
                        description "Exclude a configuration group at this level";
                    }

                } // container egress-engineering

                ///nokia-conf/configure/router/bgp/neighbor/segment-routing-v6
                container segment-routing-v6 {
                    presence "Enable the segment-routing-v6 context";
                    description "Enable the segment-routing-v6 context";

                    ///nokia-conf/configure/router/bgp/neighbor/segment-routing-v6/route-advertisement
                    container route-advertisement {
                        presence "Enable the route-advertisement context";
                        description "Enable the route-advertisement context";

                        ///nokia-conf/configure/router/bgp/neighbor/segment-routing-v6/route-advertisement/drop-routes-with-srv6-tlvs
                        leaf drop-routes-with-srv6-tlvs {
                            type boolean;
                            default "false";
                            description "Drop BGP routes with SRv6 TLVs";
                        }

                        ///nokia-conf/configure/router/bgp/neighbor/segment-routing-v6/route-advertisement/family
                        list family {
                            key "family-type";
                            description "Enter the family list instance";

                            ///nokia-conf/configure/router/bgp/neighbor/segment-routing-v6/route-advertisement/family/family-type
                            leaf family-type {
                                type enumeration {
                                    enum ipv4                           { value 1; }
                                    enum ipv6                           { value 3; }
                                }
                                description "IP address type that SRv6 route attributes apply to";
                            }

                            ///nokia-conf/configure/router/bgp/neighbor/segment-routing-v6/route-advertisement/family/strip-srv6-tlvs
                            leaf strip-srv6-tlvs {
                                type boolean;
                                default "false";
                                description "Strip SRv6 TLVs from BGP routes advertised to peers";
                            }

                            ///nokia-conf/configure/router/bgp/neighbor/segment-routing-v6/route-advertisement/family/apply-groups
                            leaf-list apply-groups {
                                type leafref {
                                    path "../../../../../../../groups/group/name";
                                }
                                max-elements 8;
                                ordered-by user;
                                description "Apply a configuration group at this level";
                            }

                            ///nokia-conf/configure/router/bgp/neighbor/segment-routing-v6/route-advertisement/family/apply-groups-exclude
                            leaf-list apply-groups-exclude {
                                type leafref {
                                    path "../../../../../../../groups/group/name";
                                }
                                max-elements 8;
                                ordered-by user;
                                description "Exclude a configuration group at this level";
                            }

                        } // list family

                    } // container route-advertisement

                } // container segment-routing-v6

            } // list neighbor

            ///nokia-conf/configure/router/bgp/bgp-tunnel-metric
            container bgp-tunnel-metric {
                description "Enter the bgp-tunnel-metric context";

                ///nokia-conf/configure/router/bgp/bgp-tunnel-metric/value
                leaf value {
                    type uint32 {
                        range "0..4294967295";
                    }
                    default "1000";
                    description "BGP tunnel metric value";
                }

                ///nokia-conf/configure/router/bgp/bgp-tunnel-metric/prefer-aigp
                leaf prefer-aigp {
                    type boolean;
                    default "false";
                    description "Use the AIGP attribute as tunnel metric when present";
                }

                ///nokia-conf/configure/router/bgp/bgp-tunnel-metric/prefer-med
                leaf prefer-med {
                    type boolean;
                    default "false";
                    description "Use the MED attribute as tunnel metric when present";
                }

            } // container bgp-tunnel-metric

            ///nokia-conf/configure/router/bgp/segment-routing-v6
            container segment-routing-v6 {
                presence "Enable the segment-routing-v6 context";
                description "Enable the segment-routing-v6 context";

                ///nokia-conf/configure/router/bgp/segment-routing-v6/source-address
                leaf source-address {
                    type types-sros:ipv6-unicast-address;
                    description "Source address used in SRv6 packet";
                }

                ///nokia-conf/configure/router/bgp/segment-routing-v6/family
                list family {
                    key "family-type";
                    description "Enter the family list instance";

                    ///nokia-conf/configure/router/bgp/segment-routing-v6/family/family-type
                    leaf family-type {
                        type enumeration {
                            enum ipv4                           { value 1; }
                            enum ipv6                           { value 3; }
                        }
                        description "IP address type that SRv6 route attributes apply to";
                    }

                    ///nokia-conf/configure/router/bgp/segment-routing-v6/family/ignore-received-srv6-tlvs
                    leaf ignore-received-srv6-tlvs {
                        type boolean;
                        default "true";
                        description "Ignore SRv6 TLVs for received routes";
                    }

                    ///nokia-conf/configure/router/bgp/segment-routing-v6/family/resolution
                    leaf resolution {
                        type types-sros:srv6-route-resolution;
                        default "route-table";
                        description "Resolution options for routes";
                    }

                    ///nokia-conf/configure/router/bgp/segment-routing-v6/family/apply-groups
                    leaf-list apply-groups {
                        type leafref {
                            path "../../../../../groups/group/name";
                        }
                        max-elements 8;
                        ordered-by user;
                        description "Apply a configuration group at this level";
                    }

                    ///nokia-conf/configure/router/bgp/segment-routing-v6/family/apply-groups-exclude
                    leaf-list apply-groups-exclude {
                        type leafref {
                            path "../../../../../groups/group/name";
                        }
                        max-elements 8;
                        ordered-by user;
                        description "Exclude a configuration group at this level";
                    }

                    ///nokia-conf/configure/router/bgp/segment-routing-v6/family/add-srv6-tlvs
                    container add-srv6-tlvs {
                        presence "Enable the add-srv6-tlvs context";
                        description "Enable the add-srv6-tlvs context";

                        ///nokia-conf/configure/router/bgp/segment-routing-v6/family/add-srv6-tlvs/locator-name
                        leaf locator-name {
                            type leafref {
                                path "../../../../../segment-routing/segment-routing-v6/base-routing-instance/locator/locator-name";
                            }
                            description "SRv6 locator name";
                        }

                        ///nokia-conf/configure/router/bgp/segment-routing-v6/family/add-srv6-tlvs/micro-segment-locator-name
                        leaf micro-segment-locator-name {
                            type leafref {
                                path "../../../../../../router/segment-routing/segment-routing-v6/base-routing-instance/micro-segment-locator/locator-name";
                            }
                            description "Micro-segment SRv6 locator name";
                        }

                    } // container add-srv6-tlvs

                } // list family

            } // container segment-routing-v6

        } // container bgp

    } // grouping conf-router-bgp

}
