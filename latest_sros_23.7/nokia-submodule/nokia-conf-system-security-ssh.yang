submodule nokia-conf-system-security-ssh {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure system security parameters. on SR OS based routers.

         Copyright 2016 Nokia. All rights reserved. Reproduction of this document
         is authorized on the condition that the foregoing copyright notice is included.

         This nokia-conf-system-security-ssh YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-04-17";

    grouping conf-system-security-ssh {
        container ssh {
            description "Enter the ssh context";

            leaf preserve-key {
                type boolean;
                default "false";
                description "Preserve keys and restore on system or server restart";
            }

            leaf server-admin-state {
                type types-sros:admin-state;
                default "enable";
                description "Administrative state of the SSH server";
            }

            leaf version {
                status obsolete;
                type enumeration {
                    enum 1                              { value 1; }
                    enum 2                              { value 2; }
                    enum 1-2                            { value 3; }
                }
                default "2";
                description "SSH protocol version supported by the SSH server";
            }

            leaf permit-empty-passwords {
                type boolean;
                default "true";
                description "Permit users with empty password strings to log in";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container server-cipher-list-v1 {
                status obsolete;
                description "Enter the server-cipher-list-v1 context";

                leaf-list apply-groups {
                    status obsolete;
                    type leafref {
                        path "../../../../../groups/group/name";
                    }
                    max-elements 8;
                    ordered-by user;
                    description "Apply a configuration group at this level";
                }

                leaf-list apply-groups-exclude {
                    status obsolete;
                    type leafref {
                        path "../../../../../groups/group/name";
                    }
                    max-elements 8;
                    ordered-by user;
                    description "Exclude a configuration group at this level";
                }

                list cipher {
                    status obsolete;
                    key "index";
                    description "Enter the cipher list instance";

                    leaf index {
                        status obsolete;
                        type int32 {
                            range "1..255";
                        }
                        description "Cipher index in the list";
                    }

                    leaf name {
                        status obsolete;
                        type enumeration {
                            enum des                            { value 2; }
                            enum 3des                           { value 3; }
                            enum blowfish                       { value 6; }
                        }
                        mandatory true;
                        description "Algorithm for performing encryption or decryption";
                    }

                    leaf-list apply-groups {
                        status obsolete;
                        type leafref {
                            path "../../../../../../groups/group/name";
                        }
                        max-elements 8;
                        ordered-by user;
                        description "Apply a configuration group at this level";
                    }

                    leaf-list apply-groups-exclude {
                        status obsolete;
                        type leafref {
                            path "../../../../../../groups/group/name";
                        }
                        max-elements 8;
                        ordered-by user;
                        description "Exclude a configuration group at this level";
                    }

                } // list cipher

            } // container server-cipher-list-v1

            container server-cipher-list-v2 {
                description "Enter the server-cipher-list-v2 context";

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list cipher {
                    key "index";
                    description "Enter the cipher list instance";

                    leaf index {
                        type int32 {
                            range "1..255";
                        }
                        description "Cipher index in the list";
                    }

                    leaf name {
                        type enumeration {
                            enum 3des-cbc                       { value 32; }
                            enum aes128-cbc                     { value 36; }
                            enum aes192-cbc                     { value 37; }
                            enum aes256-cbc                     { value 38; }
                            enum aes128-ctr                     { value 40; }
                            enum aes192-ctr                     { value 41; }
                            enum aes256-ctr                     { value 42; }
                            enum blowfish-cbc                   { status obsolete; }
                            enum cast128-cbc                    { status obsolete; }
                            enum arcfour                        { status obsolete; }
                            enum rijndael-cbc                   { status obsolete; }
                        }
                        mandatory true;
                        description "Algorithm for performing encryption or decryption";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list cipher

            } // container server-cipher-list-v2

            container client-cipher-list-v1 {
                status obsolete;
                description "Enter the client-cipher-list-v1 context";

                leaf-list apply-groups {
                    status obsolete;
                    type leafref {
                        path "../../../../../groups/group/name";
                    }
                    max-elements 8;
                    ordered-by user;
                    description "Apply a configuration group at this level";
                }

                leaf-list apply-groups-exclude {
                    status obsolete;
                    type leafref {
                        path "../../../../../groups/group/name";
                    }
                    max-elements 8;
                    ordered-by user;
                    description "Exclude a configuration group at this level";
                }

                list cipher {
                    status obsolete;
                    key "index";
                    description "Enter the cipher list instance";

                    leaf index {
                        status obsolete;
                        type int32 {
                            range "1..255";
                        }
                        description "Cipher index in the list";
                    }

                    leaf name {
                        status obsolete;
                        type enumeration {
                            enum des                            { value 2; }
                            enum 3des                           { value 3; }
                            enum blowfish                       { value 6; }
                        }
                        mandatory true;
                        description "Algorithm for performing encryption or decryption";
                    }

                    leaf-list apply-groups {
                        status obsolete;
                        type leafref {
                            path "../../../../../../groups/group/name";
                        }
                        max-elements 8;
                        ordered-by user;
                        description "Apply a configuration group at this level";
                    }

                    leaf-list apply-groups-exclude {
                        status obsolete;
                        type leafref {
                            path "../../../../../../groups/group/name";
                        }
                        max-elements 8;
                        ordered-by user;
                        description "Exclude a configuration group at this level";
                    }

                } // list cipher

            } // container client-cipher-list-v1

            container client-cipher-list-v2 {
                description "Enter the client-cipher-list-v2 context";

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list cipher {
                    key "index";
                    description "Enter the cipher list instance";

                    leaf index {
                        type int32 {
                            range "1..255";
                        }
                        description "Cipher index in the list";
                    }

                    leaf name {
                        type enumeration {
                            enum 3des-cbc                       { value 32; }
                            enum aes128-cbc                     { value 36; }
                            enum aes192-cbc                     { value 37; }
                            enum aes256-cbc                     { value 38; }
                            enum aes128-ctr                     { value 40; }
                            enum aes192-ctr                     { value 41; }
                            enum aes256-ctr                     { value 42; }
                            enum blowfish-cbc                   { status obsolete; }
                            enum cast128-cbc                    { status obsolete; }
                            enum arcfour                        { status obsolete; }
                            enum rijndael-cbc                   { status obsolete; }
                        }
                        mandatory true;
                        description "Algorithm for performing encryption or decryption";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list cipher

            } // container client-cipher-list-v2

            container server-mac-list-v2 {
                description "Enter the server-mac-list-v2 context";

                list mac {
                    key "index";
                    description "Enter the mac list instance";

                    leaf index {
                        type uint32 {
                            range "1..255";
                        }
                        description "MAC algorithm index";
                    }

                    leaf name {
                        type enumeration {
                            enum hmac-sha2-512                  { value 1; }
                            enum hmac-sha2-256                  { value 2; }
                            enum hmac-sha1                      { value 3; }
                            enum hmac-sha1-96                   { value 4; }
                            enum hmac-md5                       { value 5; }
                            enum hmac-md5-96                    { value 8; }
                            enum hmac-ripemd160                 { status obsolete; }
                            enum hmac-ripemd160-openssh-com     { status obsolete; }
                        }
                        mandatory true;
                        description "Algorithm for calculating message authentication code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list mac

            } // container server-mac-list-v2

            container client-mac-list-v2 {
                description "Enter the client-mac-list-v2 context";

                list mac {
                    key "index";
                    description "Enter the mac list instance";

                    leaf index {
                        type uint32 {
                            range "1..255";
                        }
                        description "MAC algorithm index";
                    }

                    leaf name {
                        type enumeration {
                            enum hmac-sha2-512                  { value 1; }
                            enum hmac-sha2-256                  { value 2; }
                            enum hmac-sha1                      { value 3; }
                            enum hmac-sha1-96                   { value 4; }
                            enum hmac-md5                       { value 5; }
                            enum hmac-md5-96                    { value 8; }
                            enum hmac-ripemd160                 { status obsolete; }
                            enum hmac-ripemd160-openssh-com     { status obsolete; }
                        }
                        mandatory true;
                        description "Algorithm for calculating message authentication code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list mac

            } // container client-mac-list-v2

            container key-re-exchange {
                description "Enter the key-re-exchange context";

                container server {
                    description "Enter the server context";

                    leaf minutes {
                        type union {
                            type uint32 {
                                range "1..1440";
                            }
                            type enumeration {
                                enum infinite                       { value 0; }
                            }
                        }
                        units "minutes";
                        default "60";
                        description "Maximum time before key re-exchange is initiated";
                    }

                    leaf mbytes {
                        type union {
                            type uint32 {
                                range "1..64000";
                            }
                            type enumeration {
                                enum infinite                       { value 0; }
                            }
                        }
                        units "megabytes";
                        default "1024";
                        description "Maximum bytes transmitted before key re-exchange begins";
                    }

                    leaf admin-state {
                        type types-sros:admin-state;
                        default "enable";
                        description "Administrative state of the key re-exchange";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // container server

                container client {
                    description "Enter the client context";

                    leaf minutes {
                        type union {
                            type uint32 {
                                range "1..1440";
                            }
                            type enumeration {
                                enum infinite                       { value 0; }
                            }
                        }
                        units "minutes";
                        default "60";
                        description "Maximum time before key re-exchange is initiated";
                    }

                    leaf mbytes {
                        type union {
                            type uint32 {
                                range "1..64000";
                            }
                            type enumeration {
                                enum infinite                       { value 0; }
                            }
                        }
                        units "megabytes";
                        default "1024";
                        description "Maximum bytes transmitted before key re-exchange begins";
                    }

                    leaf admin-state {
                        type types-sros:admin-state;
                        default "enable";
                        description "Administrative state of the key re-exchange";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // container client

            } // container key-re-exchange

            container server-kex-list-v2 {
                description "Enter the server-kex-list-v2 context";

                list kex {
                    key "index";
                    description "Enter the kex list instance";

                    leaf index {
                        type uint32 {
                            range "1..255";
                        }
                        description "SSHv2 KEX algorithm index";
                    }

                    leaf name {
                        type enumeration {
                            enum diffie-hellman-group1-sha1     { value 1; }
                            enum diffie-hellman-group14-sha1    { value 2; }
                            enum diffie-hellman-group-exchange-sha1 { value 3; }
                            enum diffie-hellman-group14-sha256  { value 4; }
                            enum diffie-hellman-group16-sha512  { value 5; }
                        }
                        mandatory true;
                        description "KEX algorithm for computing a shared secret key";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list kex

            } // container server-kex-list-v2

            container client-kex-list-v2 {
                description "Enter the client-kex-list-v2 context";

                list kex {
                    key "index";
                    description "Enter the kex list instance";

                    leaf index {
                        type uint32 {
                            range "1..255";
                        }
                        description "SSHv2 KEX algorithm index";
                    }

                    leaf name {
                        type enumeration {
                            enum diffie-hellman-group1-sha1     { value 1; }
                            enum diffie-hellman-group14-sha1    { value 2; }
                            enum diffie-hellman-group-exchange-sha1 { value 3; }
                            enum diffie-hellman-group14-sha256  { value 4; }
                            enum diffie-hellman-group16-sha512  { value 5; }
                        }
                        mandatory true;
                        description "KEX algorithm for computing a shared secret key";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list kex

            } // container client-kex-list-v2

            container authentication-method {
                description "Enter the authentication-method context";


                container server {
                    description "Enter the server context";

                    leaf public-key-only {
                        type boolean;
                        default "false";
                        description "Accept only public-key authentication for SSH session";
                    }

                } // container server

            } // container authentication-method

        } // container ssh

    } // grouping conf-system-security-ssh

}
