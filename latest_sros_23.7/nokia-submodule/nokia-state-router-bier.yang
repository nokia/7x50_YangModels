submodule nokia-state-router-bier {

    yang-version "1.1";

    belongs-to nokia-state { prefix "state"; }

    import ietf-inet-types                { prefix "inet"; }
    import nokia-sros-yang-extensions     { prefix "sros-ext"; }
    import nokia-types-sros               { prefix "types-sros"; }

    sros-ext:sros-major-release "rel23";
    organization "Nokia";
    contact
        "Nokia SR OS Support
         Web: <http://www.nokia.com>";
    description
        "Nokia YANG Data model with operational state for Base router BIER protocol on SR OS based routers.

         Copyright 2016 Nokia. All rights reserved. Reproduction of this document
         is authorized on the condition that the foregoing copyright notice is included.

         This nokia-state-router-bier YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-06-27";

    grouping state-router-bier {
        ///nokia-state/state/router/bier
        container bier {
            description "Enable the bier context";

            ///nokia-state/state/router/bier/oper-state
            leaf oper-state {
                type types-sros:oper-state;
                description "BIER operational state.";
            }

            ///nokia-state/state/router/bier/template
            list template {
                key "template-name";
                description "Enter the template list instance";

                ///nokia-state/state/router/bier/template/template-name
                leaf template-name {
                    type types-sros:named-item;
                    description "BIER template name";
                }

                ///nokia-state/state/router/bier/template/oper-state
                leaf oper-state {
                    type types-sros:oper-state;
                    description "BIER template operational state.";
                }

            } // list template

            ///nokia-state/state/router/bier/database
            list database {
                key "template-name sub-domain-id";
                description "Enter the database list instance";

                ///nokia-state/state/router/bier/database/template-name
                leaf template-name {
                    type types-sros:named-item;
                    description "BIER template name";
                }

                ///nokia-state/state/router/bier/database/sub-domain-id
                leaf sub-domain-id {
                    type inet:as-number {
                        range "0..255";
                    }
                    description "bier sub-domain start value.";
                }

                ///nokia-state/state/router/bier/database/bit-string-length
                leaf bit-string-length {
                    type uint32;
                    description "The current supported bit string length.";
                }

                ///nokia-state/state/router/bier/database/bfr-prefix
                leaf bfr-prefix {
                    type types-sros:ip-address;
                    description "The address to be advertised in this sub-domain.";
                }

                ///nokia-state/state/router/bier/database/multi-topology
                leaf multi-topology {
                    type enumeration {
                        enum ipv4-unicast                   { value 0; }
                        enum ipv6-unicast                   { value 2; }
                        enum ipv4-multicast                 { value 3; }
                        enum ipv6-multicast                 { value 4; }
                    }
                    description "The ISIS Multi-topolog ID where the BIER template should be applied.";
                }

                ///nokia-state/state/router/bier/database/mpls-start-label
                leaf mpls-start-label {
                    type uint32;
                    description "The mpls start label.";
                }

                ///nokia-state/state/router/bier/database/mpls-end-label
                leaf mpls-end-label {
                    type uint32;
                    description "The mpls end label.";
                }

                ///nokia-state/state/router/bier/database/mpls-total-label
                leaf mpls-total-label {
                    type uint32;
                    description "Total number of mpls labels.";
                }

                ///nokia-state/state/router/bier/database/bfr-id
                leaf bfr-id {
                    type uint32;
                    description "A BFR ID uniquely identifies a BFIR/BFER within the sub-domain.";
                }

            } // list database

            ///nokia-state/state/router/bier/forwarding
            list forwarding {
                key "sub-domain-id bit-string-length next-hop-prefix next-hop-interface-name set-id";
                description "Enter the forwarding list instance";

                ///nokia-state/state/router/bier/forwarding/sub-domain-id
                leaf sub-domain-id {
                    type inet:as-number {
                        range "0..255";
                    }
                    description "bier sub-domain start value.";
                }

                ///nokia-state/state/router/bier/forwarding/bit-string-length
                leaf bit-string-length {
                    type uint32;
                    description "The current supported bit string length.";
                }

                ///nokia-state/state/router/bier/forwarding/next-hop-prefix
                leaf next-hop-prefix {
                    type types-sros:ipv4-address;
                    description "Address of the destination prefix.";
                }

                ///nokia-state/state/router/bier/forwarding/next-hop-interface-name
                leaf next-hop-interface-name {
                    type types-sros:interface-name;
                    description "Next hop interface name.";
                }

                ///nokia-state/state/router/bier/forwarding/set-id
                leaf set-id {
                    type uint32;
                    description "The set identifier.";
                }

                ///nokia-state/state/router/bier/forwarding/neighbor-prefix
                leaf neighbor-prefix {
                    type types-sros:ip-address;
                    description "Address of the BFR prefix to be advertised in this sub-domain.";
                }

                ///nokia-state/state/router/bier/forwarding/bit-string
                leaf bit-string {
                    type types-sros:display-string-or-empty;
                    description "The bit string value.";
                }

                ///nokia-state/state/router/bier/forwarding/mpls-label
                leaf mpls-label {
                    type uint32;
                    description "The service BIER label for the sender tunnel.";
                }

                ///nokia-state/state/router/bier/forwarding/destination
                list destination {
                    key "destination-prefix";
                    description "Enter the destination list instance";

                    ///nokia-state/state/router/bier/forwarding/destination/destination-prefix
                    leaf destination-prefix {
                        type types-sros:ip-address;
                        description "Address of the destination prefix.";
                    }

                    ///nokia-state/state/router/bier/forwarding/destination/bfr-id
                    leaf bfr-id {
                        type uint32;
                        description "A BFR ID uniquely identifies a BFIR/BFER within the sub-domain.";
                    }

                } // list destination

                ///nokia-state/state/router/bier/forwarding/backup
                container backup {
                    description "Enter the backup context";

                    ///nokia-state/state/router/bier/forwarding/backup/neighbor-prefix
                    leaf neighbor-prefix {
                        type types-sros:ip-address;
                        description "Address of the backup BFR prefix to be advertised in this sub-domain.";
                    }

                    ///nokia-state/state/router/bier/forwarding/backup/next-hop-prefix
                    leaf next-hop-prefix {
                        type types-sros:ipv4-address;
                        description "Address of the backup destination prefix.";
                    }

                    ///nokia-state/state/router/bier/forwarding/backup/next-hop-interface-name
                    leaf next-hop-interface-name {
                        type types-sros:interface-name;
                        description "Backup next hop interface name.";
                    }

                    ///nokia-state/state/router/bier/forwarding/backup/bit-string
                    leaf bit-string {
                        type types-sros:display-string-or-empty;
                        description "The backup bit string value.";
                    }

                    ///nokia-state/state/router/bier/forwarding/backup/mpls-label
                    leaf mpls-label {
                        type uint32;
                        description "The backup service BIER label for the sender tunnel.";
                    }

                    ///nokia-state/state/router/bier/forwarding/backup/destination
                    list destination {
                        key "destination-prefix";
                        description "Enter the destination list instance";

                        ///nokia-state/state/router/bier/forwarding/backup/destination/destination-prefix
                        leaf destination-prefix {
                            type types-sros:ip-address;
                            description "Address of the destination prefix.";
                        }

                        ///nokia-state/state/router/bier/forwarding/backup/destination/bfr-id
                        leaf bfr-id {
                            type uint32;
                            description "A BFR ID uniquely identifies a BFIR/BFER within the sub-domain for backup part.";
                        }

                    } // list destination

                } // container backup

            } // list forwarding

            ///nokia-state/state/router/bier/routing
            list routing {
                key "sub-domain-id bit-string-length next-hop-prefix next-hop-interface-name destination-prefix";
                description "Enter the routing list instance";

                ///nokia-state/state/router/bier/routing/sub-domain-id
                leaf sub-domain-id {
                    type inet:as-number {
                        range "0..255";
                    }
                    description "bier sub-domain start value.";
                }

                ///nokia-state/state/router/bier/routing/bit-string-length
                leaf bit-string-length {
                    type uint32;
                    description "The current supported bit string length.";
                }

                ///nokia-state/state/router/bier/routing/next-hop-prefix
                leaf next-hop-prefix {
                    type types-sros:ipv4-address;
                    description "Address of the destination prefix.";
                }

                ///nokia-state/state/router/bier/routing/next-hop-interface-name
                leaf next-hop-interface-name {
                    type types-sros:interface-name;
                    description "Next hop interface name.";
                }

                ///nokia-state/state/router/bier/routing/destination-prefix
                leaf destination-prefix {
                    type types-sros:ip-address;
                    description "Address of the destination prefix.";
                }

                ///nokia-state/state/router/bier/routing/neighbor-prefix
                leaf neighbor-prefix {
                    type types-sros:ip-address;
                    description "Address of the BFR prefix to be advertised in this sub-domain.";
                }

                ///nokia-state/state/router/bier/routing/bfr-id
                leaf bfr-id {
                    type uint32;
                    description "A BFR ID uniquely identifies a BFIR/BFER within the sub-domain.";
                }

                ///nokia-state/state/router/bier/routing/backup
                container backup {
                    description "Enter the backup context";

                    ///nokia-state/state/router/bier/routing/backup/neighbor-prefix
                    leaf neighbor-prefix {
                        type types-sros:ip-address;
                        description "Address of the backup BFR prefix to be advertised in this sub-domain.";
                    }

                    ///nokia-state/state/router/bier/routing/backup/next-hop-prefix
                    leaf next-hop-prefix {
                        type types-sros:ipv4-address;
                        description "Address of the backup destination prefix.";
                    }

                    ///nokia-state/state/router/bier/routing/backup/next-hop-interface-name
                    leaf next-hop-interface-name {
                        type types-sros:interface-name;
                        description "Backup next hop interface name.";
                    }

                } // container backup

            } // list routing

            ///nokia-state/state/router/bier/tunnel
            list tunnel {
                key "tunnel-index";
                description "Enter the tunnel list instance";

                ///nokia-state/state/router/bier/tunnel/tunnel-index
                leaf tunnel-index {
                    type uint32;
                    description "Tunnel index for the bier tunnel, internally maintained.";
                }

                ///nokia-state/state/router/bier/tunnel/tunnel-type
                leaf tunnel-type {
                    type enumeration {
                        enum tx                             { value 0; }
                        enum rx                             { value 1; }
                    }
                    description "The tunnel type identifies whether tunnel is transmitter or receiver.";
                }

                ///nokia-state/state/router/bier/tunnel/bfr-prefix
                leaf bfr-prefix {
                    type types-sros:ip-address;
                    description "Address of the tunnel originator, advertised in PTA.";
                }

                ///nokia-state/state/router/bier/tunnel/sub-domain-id
                leaf sub-domain-id {
                    type inet:as-number {
                        range "0..255";
                    }
                    description "BIER sub-domain value, where the tunnel is resolved, advertised in PTA.";
                }

                ///nokia-state/state/router/bier/tunnel/mpls-svc-label
                leaf mpls-svc-label {
                    type uint32;
                    description "The mpls service label to be used for this tunnel, advertised in PTA.";
                }

                ///nokia-state/state/router/bier/tunnel/bfr-id
                leaf bfr-id {
                    type uint32;
                    description "BFR ID of the tunnel in the sub-domain, advertised in PTA.";
                }

                ///nokia-state/state/router/bier/tunnel/oper-state
                leaf oper-state {
                    type types-sros:oper-state;
                    description "Indicates the operational state of the bier tunnel.";
                }

                ///nokia-state/state/router/bier/tunnel/number-of-leaves
                leaf number-of-leaves {
                    type uint32;
                    description "Indicates number of leaves for each transmitting tunnels.";
                }

                ///nokia-state/state/router/bier/tunnel/last-oper-down-reason
                leaf last-oper-down-reason {
                    type uint32;
                    description "Indicates the reason for last time tunnel was flapped.";
                }

                ///nokia-state/state/router/bier/tunnel/tunnel-leaf
                list tunnel-leaf {
                    key "tunnel-leaf-prefix";
                    description "Enter the tunnel-leaf list instance";

                    ///nokia-state/state/router/bier/tunnel/tunnel-leaf/tunnel-leaf-prefix
                    leaf tunnel-leaf-prefix {
                        type types-sros:ip-address;
                        description "Tunnel leaf router address";
                    }

                    ///nokia-state/state/router/bier/tunnel/tunnel-leaf/mvpn-id
                    leaf mvpn-id {
                        type uint32;
                        description "The MVPN ID indicates the service instance id, internaly used";
                    }

                    ///nokia-state/state/router/bier/tunnel/tunnel-leaf/oper-state
                    leaf oper-state {
                        type types-sros:oper-state;
                        description
                            "This indecates the operational state of the transmitting
                             tunnel";
                    }

                    ///nokia-state/state/router/bier/tunnel/tunnel-leaf/bfr-prefix
                    leaf bfr-prefix {
                        type types-sros:ip-address;
                        description
                            "This indicates the address of the BFR prefix to be advertised
                             via the PMSI attribute";
                    }

                    ///nokia-state/state/router/bier/tunnel/tunnel-leaf/bfr-id
                    leaf bfr-id {
                        type uint32;
                        description
                            "This indicates the BFR-ID of the BFR prefix in the sub-domain
                             to be advertised via the PMSI attribute";
                    }

                    ///nokia-state/state/router/bier/tunnel/tunnel-leaf/sub-domain
                    leaf sub-domain {
                        type uint32;
                        description
                            "This indicates the sub-domain id to be advertised via the PMSI
                             attribute";
                    }

                    ///nokia-state/state/router/bier/tunnel/tunnel-leaf/mpls-label
                    leaf mpls-label {
                        type uint32;
                        description
                            "This indicates the MPLS label to be advertised via the PMSI
                             attribute";
                    }

                    ///nokia-state/state/router/bier/tunnel/tunnel-leaf/leaf-bfr-id
                    leaf leaf-bfr-id {
                        type uint32;
                        description
                            "The leaf BFR-ID field indicates each leaf BFR IDs, joined to
                             this tunnel";
                    }

                } // list tunnel-leaf

            } // list tunnel

            ///nokia-state/state/router/bier/statistics
            container statistics {
                description "Enter the statistics context";

                ///nokia-state/state/router/bier/statistics/total-learnt-routes
                leaf total-learnt-routes {
                    type uint32;
                    description "The value indicates the total number of learnt BFR prefixes.";
                }

                ///nokia-state/state/router/bier/statistics/total-valid-routes
                leaf total-valid-routes {
                    type uint32;
                    description
                        "The value indicates the total number of BFR prefixes with
                         valid BFR info.";
                }

                ///nokia-state/state/router/bier/statistics/valid-neighbor-nexthop
                leaf valid-neighbor-nexthop {
                    type uint32;
                    description
                        "The value indicates the total number of neighbors or
                         next-hops with valid BFR info.";
                }

                ///nokia-state/state/router/bier/statistics/received-invalid-bier-info
                leaf received-invalid-bier-info {
                    type uint32;
                    description
                        "The value indicates the number of learnt BFR prefixes with
                         invalid BIER info.";
                }

                ///nokia-state/state/router/bier/statistics/received-invalid-bfr-info
                leaf received-invalid-bfr-info {
                    type uint32;
                    description
                        "The value indecates the number of learnt BFR prefixes with
                         invalid BFR info.";
                }

                ///nokia-state/state/router/bier/statistics/received-invalid-encap-info
                leaf received-invalid-encap-info {
                    type uint32;
                    description
                        "The value indicates the number of learnt BFR prefixes with
                         invalid encapsulation info.";
                }

                ///nokia-state/state/router/bier/statistics/received-invalid-mpls-info
                leaf received-invalid-mpls-info {
                    type uint32;
                    description
                        "The value indicates the number of learnt BFR prefixes with
                         invalid MPLS info.";
                }

                ///nokia-state/state/router/bier/statistics/discard-tunneled-nexthop
                leaf discard-tunneled-nexthop {
                    type uint32;
                    description "The value indicates the number of tunneled next-hops discarded.";
                }

                ///nokia-state/state/router/bier/statistics/discard-non-network-nexthop
                leaf discard-non-network-nexthop {
                    type uint32;
                    description
                        "The value indicates the number of non network nexthops
                         discarded.";
                }

                ///nokia-state/state/router/bier/statistics/discard-non-fp4-nexthop
                leaf discard-non-fp4-nexthop {
                    type uint32;
                    description "The value indicates the number of non FP4 nexthops discarded.";
                }

                ///nokia-state/state/router/bier/statistics/sub-domain-bit-string-length-mismatch
                leaf sub-domain-bit-string-length-mismatch {
                    type uint32;
                    description
                        "The value indicates the number of BFR prefixes received with
                         sub-domain and BSL value different from configured values.";
                }

                ///nokia-state/state/router/bier/statistics/multi-topology-mismatch
                leaf multi-topology-mismatch {
                    type uint32;
                    description
                        "The value indicates the number of BFR prefixes received with
                         multi-topology value different from the configured value.";
                }

                ///nokia-state/state/router/bier/statistics/unsupported-ipv6-routes
                leaf unsupported-ipv6-routes {
                    type uint32;
                    description
                        "The value indicates the number of BFR prefixes learnt with
                         IPv6 addresses.";
                }

                ///nokia-state/state/router/bier/statistics/bfr-id-duplicate
                leaf bfr-id-duplicate {
                    type uint32;
                    description
                        "The value indicates the number of duplicate BFR id received in
                         multiple BFR prefixes.";
                }

            } // container statistics

        } // container bier

    } // grouping state-router-bier

}
