submodule nokia-conf-port-ethernet {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-port               { prefix "types-port"; }
    import nokia-types-qos                { prefix "types-qos"; }
    import nokia-types-sros               { prefix "types-sros"; }

    include nokia-conf-eth-cfm;
    include nokia-conf-groups;
    include nokia-conf-log;
    include nokia-conf-port-eth-access;
    include nokia-conf-port-eth-dot1x;
    include nokia-conf-port-eth-efm-oam;
    include nokia-conf-port-eth-egress;
    include nokia-conf-port-eth-lldp;
    include nokia-conf-port-eth-network;

    sros-ext:sros-major-release "rel23";
    organization "Nokia";
    contact
        "Nokia SR OS Support
         Web: <http://www.nokia.com>";
    description
        "Nokia YANG Data model to configure ethernet ports on SR OS based routers.

         Copyright 2016 Nokia. All rights reserved. Reproduction of this document
         is authorized on the condition that the foregoing copyright notice is included.

         This nokia-conf-port-ethernet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-19";

    grouping conf-port-ethernet {
        container ethernet {
            description "Enter the ethernet context";

            leaf accounting-policy {
                type leafref {
                    path "../../../log/accounting-policy/policy-id";
                }
                description "Accounting policy for the Ethernet port";
            }

            leaf autonegotiate {
                type enumeration {
                    enum true                           { value 1; }
                    enum false                          { value 2; }
                    enum limited                        { value 3; }
                }
                description "Speed and duplex autonegotiation on the Ethernet port";
            }

            leaf collect-stats {
                type boolean;
                default "false";
                description "Collect accounting and statistical data";
            }

            leaf dot1q-etype {
                type types-port:etype;
                default "33024";
                description "Ethertype expected if port encapsulation type is dot1q";
            }

            leaf duplex {
                type types-port:duplex-mode;
                description "Duplex type for the fast Ethernet port";
            }

            leaf lacp-tunnel {
                type boolean;
                default "false";
                description "Enable LACP packet tunneling for the Ethernet port";
            }

            leaf load-balancing-algorithm {
                type types-port:load-balancing-algorithm;
                description "Load balancing algorithm for the Ethernet port";
            }

            leaf mac-address {
                type yang:mac-address;
                default "00:00:00:00:00:00";
                description "MAC address of the Ethernet port";
            }

            leaf min-frame-length {
                type uint32 {
                    range "64|68|72";
                }
                units "bytes";
                default "64";
                description "Minimum transmitted frame length";
            }

            leaf mode {
                type types-port:mode;
                description "Operation mode for the Ethernet port";
            }

            leaf encap-type {
                type types-port:ethernet-encap-type;
                description "Encapsulation method for the Ethernet port";
            }

            leaf mtu {
                type uint32 {
                    range "512..9800";
                }
                units "bytes";
                description "Maximum payload MTU size for the Ethernet port";
            }

            leaf pbb-etype {
                type types-port:etype;
                default "35047";
                description "Ethertype for PBB encapsulation";
            }

            leaf ptp-asymmetry {
                type int32;
                units "nanoseconds";
                description "PTP asymmetry delay on the Ethernet port";
            }

            leaf qinq-etype {
                type types-port:etype;
                default "33024";
                description "Ethertype for QinQ encapsulation";
            }

            leaf rs-fec-mode {
                type enumeration {
                    enum cl91-514-528                   { value 1; }
                    enum cl74                           { value 2; }
                    enum cl108                          { value 3; }
                }
                description "RS-FEC mode on the Ethernet port";
            }

            leaf single-fiber {
                type boolean;
                default "false";
                description "Enable packet gathering from a single fiber port";
            }

            leaf speed {
                type uint32 {
                    range "10|100|1000|10000|25000|40000|50000|100000";
                }
                units "megabps";
                description "Ethernet port speed";
            }

            leaf util-stats-interval {
                type uint32 {
                    range "30..600";
                }
                units "seconds";
                default "300";
                description "Interval to calculate utilization statistics";
            }

            leaf xgig {
                type enumeration {
                    enum lan                            { value 1; }
                    enum wan                            { value 2; }
                }
                description "Ethernet port mode";
            }

            leaf discard-rx-pause-frames {
                type boolean;
                default "false";
                description "Discard received pause frames";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container down-on-internal-error {
                presence "Enable the down-on-internal-error context";
                description "Enable the down-on-internal-error context";

                leaf tx-laser {
                    type enumeration {
                        enum off                            { value 1; }
                        enum on                             { value 2; }
                    }
                    default "on";
                    description "Remote laser state on internal MAC transmit error";
                }

            } // container down-on-internal-error

            container hold-time {
                description "Enter the hold-time context";

                leaf units {
                    type enumeration {
                        enum seconds                        { value 0; }
                        enum centiseconds                   { value 1; }
                    }
                    default "seconds";
                    description "Hold time units";
                }

                leaf up {
                    type uint32 {
                        range "1..3600000";
                    }
                    description "Delay after interface goes from down state to up state";
                }

                leaf down {
                    type uint32 {
                        range "1..3600000";
                    }
                    description "Delay after interface goes from up state to down state";
                }

            } // container hold-time

            container loopback {
                description "Enter the loopback context";

                leaf direction {
                    type enumeration {
                        enum line                           { value 1; }
                        enum internal                       { value 2; }
                    }
                    description "Direction of loopback for received frames";
                }

                leaf swap-src-dst-mac {
                    type boolean;
                    default "false";
                    description "Enable swapping source and destination MAC addresses";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container loopback

            container report-alarm {
                description "Enter the report-alarm context";

                leaf signal-fail {
                    type boolean;
                    description "Report Ethernet signal lost alarm";
                }

                leaf remote {
                    type boolean;
                    description "Report remote faults";
                }

                leaf local {
                    type boolean;
                    description "Report local faults";
                }

                leaf frame-not-locked {
                    type boolean;
                    description "Report \"not locked on the Ethernet framing sequence\"";
                }

                leaf high-ber {
                    type boolean;
                    description "Report High Bit Error Rate";
                }

                leaf block-not-locked {
                    type boolean;
                    description "Report 40G/100G PCS Lanes Not Block Locked";
                }

                leaf alignment-marker-not-locked {
                    type boolean;
                    description "Report 40G/100G PCS Alignment Marker Loss of Lock";
                }

                leaf duplicate-lane {
                    type boolean;
                    description "Report 40G/100G PCS Duplicate Lane Marker alarm";
                }

            } // container report-alarm

            container crc-monitor {
                description "Enter the crc-monitor context";

                leaf window-size {
                    type uint32 {
                        range "5..60";
                    }
                    units "seconds";
                    default "10";
                    description "Sliding window size over which errors are measured";
                }

                container signal-degrade {
                    description "Enter the signal-degrade context";

                    leaf threshold {
                        type uint32 {
                            range "1..9";
                        }
                        description "SD threshold";
                    }

                    leaf multiplier {
                        type uint32 {
                            range "1..9";
                        }
                        default "1";
                        description "SD multiplier";
                    }

                } // container signal-degrade

                container signal-failure {
                    description "Enter the signal-failure context";

                    leaf threshold {
                        type uint32 {
                            range "1..9";
                        }
                        description "SF threshold";
                    }

                    leaf multiplier {
                        type uint32 {
                            range "1..9";
                        }
                        default "1";
                        description "SF multiplier";
                    }

                } // container signal-failure

            } // container crc-monitor

            container dampening {
                description "Enter the dampening context";

                leaf admin-state {
                    type types-sros:admin-state;
                    default "disable";
                    description "Administrative state of exponential port dampening";
                }

                leaf half-life {
                    type uint32 {
                        range "1..2000";
                    }
                    units "seconds";
                    default "5";
                    description "Half-life decay time";
                }

                leaf max-suppress-time {
                    type uint32 {
                        range "1..43200";
                    }
                    units "seconds";
                    default "20";
                    description "Maximum suppression time";
                }

                leaf reuse-threshold {
                    type uint32 {
                        range "1..20000";
                    }
                    units "penalties";
                    default "1000";
                    description "Threshold which port-up state is no longer suppressed";
                }

                leaf suppress-threshold {
                    type uint32 {
                        range "1..20000";
                    }
                    units "penalties";
                    default "2000";
                    description "Threshold at which the port-up state is suppressed";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container dampening

            container down-when-looped {
                description "Enter the down-when-looped context";

                leaf admin-state {
                    type types-sros:admin-state;
                    default "disable";
                    description "Administrative state of Ethernet loop detection";
                }

                leaf keep-alive {
                    type uint32 {
                        range "1..120";
                    }
                    units "seconds";
                    default "10";
                    description "Time interval between keep-alive PDUs";
                }

                leaf retry-timeout {
                    type uint32 {
                        range "0|10..160";
                    }
                    units "seconds";
                    default "120";
                    description "Wait time before re-enabling port after loop detection";
                }

                leaf use-broadcast-address {
                    type boolean;
                    default "false";
                    description "Use broadcast MAC address for destination MAC address";
                }

            } // container down-when-looped

            container eth-cfm {
                description "Enter the eth-cfm context";

                list mep {
                    key "md-admin-name ma-admin-name mep-id";
                    description "Enter the mep list instance";

                    leaf md-admin-name {
                        type leafref {
                            path "../../../../../eth-cfm/domain/md-admin-name";
                        }
                        description "Maintenance Domain (MD) name";
                    }

                    leaf ma-admin-name {
                        type leafref {
                            path "../../../../../eth-cfm/domain[md-admin-name=current()/../md-admin-name]/association/ma-admin-name";
                        }
                        description "Maintenance Association (MA) name";
                    }

                    leaf mep-id {
                        type types-eth-cfm:mep-id-type;
                        description "Maintenance Endpoint (MEP) ID";
                    }

                    leaf vlan {
                        type types-eth-cfm:vlan-id-or-none;
                        sros-ext:immutable;
                        default "none";
                        description "Outer VLAN ID of the tunnel";
                    }

                    leaf admin-state {
                        type types-sros:admin-state;
                        default "disable";
                        description "Administrative state of the MEP";
                    }

                    leaf description {
                        type types-sros:description;
                        description "Text description";
                    }

                    leaf mac-address {
                        type types-sros:mac-unicast-address-no-zero;
                        description "MAC address of the MEP";
                    }

                    leaf install-mep {
                        type boolean;
                        default "false";
                        description "Install MEP in the forwarding plane";
                    }

                    leaf low-priority-defect {
                        type types-eth-cfm:lowest-alarm-priority;
                        default "mac-rem-err-xcon";
                        description "Lowest priority defect allowed to generate fault alarm";
                    }

                    leaf ccm {
                        type boolean;
                        default "false";
                        description "Generate CCM messages";
                    }

                    leaf ccm-ltm-priority {
                        type types-eth-cfm:frame-priority;
                        default "7";
                        description "Priority of CCM and LTM messages transmitted by the MEP";
                    }

                    leaf ccm-padding-size {
                        type uint32 {
                            range "3..1500";
                        }
                        description "Number of octets of padding to insert in CCM packets";
                    }

                    leaf one-way-delay-threshold {
                        type uint32 {
                            range "0..600";
                        }
                        units "seconds";
                        default "3";
                        description "Threshold time limit for the one-way delay test";
                    }

                    leaf collect-lmm-stats {
                        type boolean;
                        default "false";
                        description "Collect statistics for loss measurement message tests";
                    }

                    leaf facility-fault {
                        type boolean;
                        default "false";
                        description "Allow the facility MEP to generate a network action";
                    }

                    leaf-list ccm-tlv-ignore {
                        type types-eth-cfm:ccm-tlv-ignore-type;
                        max-elements 2;
                        description "TLV to ignore on reception";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container alarm-notification {
                        description "Enter the alarm-notification context";

                        leaf fng-alarm-time {
                            type int32 {
                                range "250|500|1000";
                            }
                            units "centiseconds";
                            description "Time that must expire before an FNG alarm is raised";
                        }

                        leaf fng-reset-time {
                            type int32 {
                                range "250|500|1000";
                            }
                            units "centiseconds";
                            description "Time that must expire before an FNG alarm is reset";
                        }

                    } // container alarm-notification

                    container ais {
                        presence "Enable the ais context";
                        description "Enable the ais context";

                        leaf-list client-meg-level {
                            type uint32 {
                                range "1..7";
                            }
                            max-elements 7;
                            description "Client MEG level for AIS message generation";
                        }

                        leaf interface-support {
                            type boolean;
                            default "false";
                            description "Enable generation of AIS PDUs based on endpoint state";
                        }

                        leaf interval {
                            type uint32 {
                                range "1|60";
                            }
                            units "seconds";
                            default "1";
                            description "Transmission interval for AIS messages";
                        }

                        leaf low-priority-defect {
                            type enumeration {
                                enum all-def                        { value 1; }
                                enum mac-rem-err-xcon               { value 2; }
                            }
                            default "all-def";
                            description "Lowest priority defect allowed to generate fault alarm";
                        }

                        leaf priority {
                            type types-eth-cfm:frame-priority;
                            default "7";
                            description "Priority of the AIS messages generated by the node";
                        }

                    } // container ais

                    container csf {
                        presence "Enable the csf context";
                        description "Enable the csf context";

                        leaf multiplier {
                            type decimal64 {
                                range "0.0|2.0..30.0";
                                fraction-digits 1;
                            }
                            default "3.5";
                            description "Multiplication factor used to clear the CSF condition";
                        }

                    } // container csf

                    container eth-test {
                        presence "Enable the eth-test context";
                        description "Enable the eth-test context";

                        leaf bit-error-threshold {
                            type uint32 {
                                range "0..11840";
                            }
                            units "bit errors";
                            default "1";
                            description "Lowest priority defect allowed to generate fault alarm";
                        }

                        container test-pattern {
                            description "Enter the test-pattern context";

                            leaf pattern {
                                type enumeration {
                                    enum all-zeros                      { value 0; }
                                    enum all-ones                       { value 1; }
                                }
                                default "all-zeros";
                                description "Test pattern for Ethernet Test frames";
                            }

                            leaf crc-tlv {
                                type boolean;
                                default "false";
                                description "Generate a CRC checksum";
                            }

                        } // container test-pattern

                    } // container eth-test

                    container grace {
                        description "Enter the grace context";

                        container eth-ed {
                            description "Enter the eth-ed context";

                            leaf max-rx-defect-window {
                                type uint32 {
                                    range "1..86400";
                                }
                                units "seconds";
                                description "Maximum received ETH-ED expected defect window duration";
                            }

                            leaf priority {
                                type int32 {
                                    range "0..7";
                                }
                                description "Transmission priority for ETH-ED PDUs";
                            }

                            leaf rx-eth-ed {
                                type boolean;
                                default "true";
                                description "Receive and process ETH-ED ITU-T Y.1731 PDUs on the MEP";
                            }

                            leaf tx-eth-ed {
                                type boolean;
                                default "false";
                                description "Transmit ETH-ED PDUs from the MEP";
                            }

                        } // container eth-ed

                        container eth-vsm-grace {
                            description "Enter the eth-vsm-grace context";

                            leaf rx-eth-vsm-grace {
                                type boolean;
                                default "true";
                                description "Receive and process Nokia ETH-CFM Grace PDU on the MEP";
                            }

                            leaf tx-eth-vsm-grace {
                                type boolean;
                                default "true";
                                description "Transmit ETH-ED PDUs from the MEP";
                            }

                        } // container eth-vsm-grace

                    } // container grace

                    container eth-bn {
                        description "Enter the eth-bn context";

                        leaf receive {
                            type boolean;
                            default "false";
                            description "Enable the reception and processing of ETH-BN messages";
                        }

                        leaf rx-update-pacing {
                            type uint32 {
                                range "1..600";
                            }
                            default "5";
                            description "Pace of messages to and from ETH-CFM to QoS subsystems";
                        }

                    } // container eth-bn

                } // list mep

            } // container eth-cfm

            container ingress {
                description "Enter the ingress context";

                leaf rate {
                    type int32;
                    units "megabps";
                    description "Maximum ingress bandwidth";
                }

            } // container ingress

            container elmi {
                description "Enter the elmi context";

                leaf mode {
                    type enumeration {
                        enum uni-n                          { value 1; }
                    }
                    description "Ethernet LMI mode";
                }

                leaf n393 {
                    type uint32 {
                        range "2..10";
                    }
                    default "4";
                    description "Monitored count of consecutive errors";
                }

                leaf t391 {
                    type uint32 {
                        range "5..30";
                    }
                    units "seconds";
                    default "10";
                    description "Polling timer for UNI-C";
                }

                leaf t392 {
                    type uint32 {
                        range "5..30";
                    }
                    units "seconds";
                    default "15";
                    description "Polling verification timer for UNI-N";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container elmi

            container ssm {
                description "Enter the ssm context";

                leaf admin-state {
                    type types-sros:admin-state;
                    default "disable";
                    description "Administrative state of the ESMC for the Ethernet port";
                }

                leaf code-type {
                    type enumeration {
                        enum sonet                          { value 2; }
                        enum sdh                            { value 3; }
                    }
                    default "sdh";
                    description "Encoding of synchronization status messages";
                }

                leaf esmc-tunnel {
                    type boolean;
                    default "false";
                    description "Tunnel ESMC frames in Epipe or VPLS services";
                }

                leaf tx-dus {
                    type boolean;
                    description "Force QL value transmitted be set to QL-DNU or QL-DUS";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container ssm

            container symbol-monitor {
                description "Enter the symbol-monitor context";

                leaf admin-state {
                    type types-sros:admin-state;
                    default "disable";
                    description "Administrative state of symbol monitoring on the port";
                }

                leaf window-size {
                    type uint32 {
                        range "5..60";
                    }
                    units "seconds";
                    default "10";
                    description "Sliding window size over which errors are measured";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container signal-degrade {
                    description "Enter the signal-degrade context";

                    leaf threshold {
                        type uint32 {
                            range "1..9";
                        }
                        description "SD threshold for symbol errors";
                    }

                    leaf multiplier {
                        type uint32 {
                            range "1..9";
                        }
                        default "1";
                        description "SD multiplier used to scale the symbol error ratio";
                    }

                } // container signal-degrade

                container signal-failure {
                    description "Enter the signal-failure context";

                    leaf threshold {
                        type uint32 {
                            range "1..9";
                        }
                        description "SF threshold for symbol errors";
                    }

                    leaf multiplier {
                        type uint32 {
                            range "1..9";
                        }
                        default "1";
                        description "SF multiplier used to scale the symbol error ratio";
                    }

                } // container signal-failure

            } // container symbol-monitor

            container storm-control {
                description "Enter the storm-control context";

                list traffic-type {
                    key "storm-traffic-type";
                    description "Enter the traffic-type list instance";

                    leaf storm-traffic-type {
                        type types-sros:strm-ctrl-traffic-type;
                        description "Storm-control traffic type";
                    }

                    leaf rate {
                        type types-qos:storm-control-rate;
                        description "Traffic rate limit";
                    }

                    leaf burst {
                        type types-qos:storm-control-burst;
                        description "Traffic burst size limit";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list traffic-type

            } // container storm-control

            uses conf-port-eth-access;
            uses conf-port-eth-dot1x;
            uses conf-port-eth-efm-oam;
            uses conf-port-eth-egress;
            uses conf-port-eth-lldp;
            uses conf-port-eth-network;
        } // container ethernet

    } // grouping conf-port-ethernet

}
