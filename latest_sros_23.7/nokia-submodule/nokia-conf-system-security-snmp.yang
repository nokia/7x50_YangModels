submodule nokia-conf-system-security-snmp {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure system security snmp parameters. on SR OS based routers.

         Copyright 2016 Nokia. All rights reserved. Reproduction of this document
         is authorized on the condition that the foregoing copyright notice is included.

         This nokia-conf-system-security-snmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2017-10-24";

    grouping conf-system-security-snmp {
        ///nokia-conf/configure/system/security/snmp
        container snmp {
            description "Enable the snmp context";

            ///nokia-conf/configure/system/security/snmp/apply-groups
            leaf-list apply-groups {
                type leafref {
                    path "../../../../groups/group/name";
                }
                max-elements 8;
                ordered-by user;
                description "Apply a configuration group at this level";
            }

            ///nokia-conf/configure/system/security/snmp/apply-groups-exclude
            leaf-list apply-groups-exclude {
                type leafref {
                    path "../../../../groups/group/name";
                }
                max-elements 8;
                ordered-by user;
                description "Exclude a configuration group at this level";
            }

            ///nokia-conf/configure/system/security/snmp/access
            list access {
                key "group context security-model security-level";
                description "Enter the access list instance";

                ///nokia-conf/configure/system/security/snmp/access/group
                leaf group {
                    type types-sros:named-item;
                    description "Group name";
                }

                ///nokia-conf/configure/system/security/snmp/access/context
                leaf context {
                    type types-sros:named-item-or-empty;
                    description "String to match context name for access rights";
                }

                ///nokia-conf/configure/system/security/snmp/access/security-model
                leaf security-model {
                    type enumeration {
                        enum snmpv1                         { value 1; }
                        enum snmpv2c                        { value 2; }
                        enum usm                            { value 3; }
                    }
                    description "Security model";
                }

                ///nokia-conf/configure/system/security/snmp/access/security-level
                leaf security-level {
                    type enumeration {
                        enum no-auth-no-privacy             { value 1; }
                        enum auth-no-privacy                { value 2; }
                        enum privacy                        { value 3; }
                    }
                    description "Minimum security level required to gain access rights";
                }

                ///nokia-conf/configure/system/security/snmp/access/prefix-match
                leaf prefix-match {
                    type enumeration {
                        enum exact                          { value 1; }
                        enum prefix                         { value 2; }
                    }
                    description "Match type for the context";
                }

                ///nokia-conf/configure/system/security/snmp/access/read
                leaf read {
                    type types-sros:named-item;
                    description "SNMP view for read access";
                }

                ///nokia-conf/configure/system/security/snmp/access/write
                leaf write {
                    type types-sros:named-item;
                    description "SNMP view for write access";
                }

                ///nokia-conf/configure/system/security/snmp/access/notify
                leaf notify {
                    type types-sros:named-item;
                    description "SNMP view for notification access";
                }

                ///nokia-conf/configure/system/security/snmp/access/apply-groups
                leaf-list apply-groups {
                    type leafref {
                        path "../../../../../groups/group/name";
                    }
                    max-elements 8;
                    ordered-by user;
                    description "Apply a configuration group at this level";
                }

                ///nokia-conf/configure/system/security/snmp/access/apply-groups-exclude
                leaf-list apply-groups-exclude {
                    type leafref {
                        path "../../../../../groups/group/name";
                    }
                    max-elements 8;
                    ordered-by user;
                    description "Exclude a configuration group at this level";
                }

            } // list access

            ///nokia-conf/configure/system/security/snmp/community
            list community {
                key "community-string";
                description "Enter the community list instance";

                ///nokia-conf/configure/system/security/snmp/community/community-string
                leaf community-string {
                    type types-sros:encrypted-leaf {
                        length "1..114";
                    }
                    description "SNMPv1 or SNMPv2c community string";
                }

                ///nokia-conf/configure/system/security/snmp/community/access-permissions
                leaf access-permissions {
                    type enumeration {
                        enum r                              { value 1; }
                        enum rw                             { value 2; }
                        enum rwa                            { value 3; }
                        enum mgmt                           { value 4; }
                        enum vpls-mgmt                      { value 5; }
                    }
                    mandatory true;
                    description "Access permissions for objects in the MIB";
                }

                ///nokia-conf/configure/system/security/snmp/community/version
                leaf version {
                    type enumeration {
                        enum v1                             { value 1; }
                        enum v2c                            { value 2; }
                        enum both                           { value 3; }
                    }
                    default "both";
                    description "SNMP version";
                }

                ///nokia-conf/configure/system/security/snmp/community/source-access-list
                leaf source-access-list {
                    type leafref {
                        path "../../source-access-list/list-name";
                    }
                    description "Source access list to validate received SNMP requests";
                }

                ///nokia-conf/configure/system/security/snmp/community/apply-groups
                leaf-list apply-groups {
                    type leafref {
                        path "../../../../../groups/group/name";
                    }
                    max-elements 8;
                    ordered-by user;
                    description "Apply a configuration group at this level";
                }

                ///nokia-conf/configure/system/security/snmp/community/apply-groups-exclude
                leaf-list apply-groups-exclude {
                    type leafref {
                        path "../../../../../groups/group/name";
                    }
                    max-elements 8;
                    ordered-by user;
                    description "Exclude a configuration group at this level";
                }

            } // list community

            ///nokia-conf/configure/system/security/snmp/usm-community
            list usm-community {
                key "community-string";
                description "Enter the usm-community list instance";

                ///nokia-conf/configure/system/security/snmp/usm-community/community-string
                leaf community-string {
                    type types-sros:encrypted-leaf {
                        length "1..114";
                    }
                    description "Community string associated with SNMPv3 access group";
                }

                ///nokia-conf/configure/system/security/snmp/usm-community/group
                leaf group {
                    type types-sros:named-item;
                    description "Group to manage access rights of the community string";
                }

                ///nokia-conf/configure/system/security/snmp/usm-community/source-access-list
                leaf source-access-list {
                    type leafref {
                        path "../../source-access-list/list-name";
                    }
                    description "Source access list to validate received SNMP requests";
                }

                ///nokia-conf/configure/system/security/snmp/usm-community/apply-groups
                leaf-list apply-groups {
                    type leafref {
                        path "../../../../../groups/group/name";
                    }
                    max-elements 8;
                    ordered-by user;
                    description "Apply a configuration group at this level";
                }

                ///nokia-conf/configure/system/security/snmp/usm-community/apply-groups-exclude
                leaf-list apply-groups-exclude {
                    type leafref {
                        path "../../../../../groups/group/name";
                    }
                    max-elements 8;
                    ordered-by user;
                    description "Exclude a configuration group at this level";
                }

            } // list usm-community

            ///nokia-conf/configure/system/security/snmp/attempts
            container attempts {
                description "Enter the attempts context";

                ///nokia-conf/configure/system/security/snmp/attempts/count
                leaf count {
                    type uint16 {
                        range "1..64";
                    }
                    default "20";
                    description "Unsuccessful attempts allowed within time period";
                }

                ///nokia-conf/configure/system/security/snmp/attempts/time
                leaf time {
                    type uint16 {
                        range "0..60";
                    }
                    units "minutes";
                    default "5";
                    description "Time before host lockout after unsuccessful attempts";
                }

                ///nokia-conf/configure/system/security/snmp/attempts/lockout
                leaf lockout {
                    type uint16 {
                        range "0..1440";
                    }
                    units "minutes";
                    default "10";
                    description "Lockout period during which the host cannot log in";
                }

                ///nokia-conf/configure/system/security/snmp/attempts/apply-groups
                leaf-list apply-groups {
                    type leafref {
                        path "../../../../../groups/group/name";
                    }
                    max-elements 8;
                    ordered-by user;
                    description "Apply a configuration group at this level";
                }

                ///nokia-conf/configure/system/security/snmp/attempts/apply-groups-exclude
                leaf-list apply-groups-exclude {
                    type leafref {
                        path "../../../../../groups/group/name";
                    }
                    max-elements 8;
                    ordered-by user;
                    description "Exclude a configuration group at this level";
                }

            } // container attempts

            ///nokia-conf/configure/system/security/snmp/source-access-list
            list source-access-list {
                key "list-name";
                max-elements 16;
                description "Enter the source-access-list list instance";

                ///nokia-conf/configure/system/security/snmp/source-access-list/list-name
                leaf list-name {
                    type types-sros:string-not-all-spaces {
                        length "1..32";
                        pattern "([A-Za-z].*[^ \\\\t]?$)|(^[^_].*[^ \\\\t]?)" {
                            error-message "List name must begin with a letter";
                        }
                    }
                    description "Source access list name";
                }

                ///nokia-conf/configure/system/security/snmp/source-access-list/apply-groups
                leaf-list apply-groups {
                    type leafref {
                        path "../../../../../groups/group/name";
                    }
                    max-elements 8;
                    ordered-by user;
                    description "Apply a configuration group at this level";
                }

                ///nokia-conf/configure/system/security/snmp/source-access-list/apply-groups-exclude
                leaf-list apply-groups-exclude {
                    type leafref {
                        path "../../../../../groups/group/name";
                    }
                    max-elements 8;
                    ordered-by user;
                    description "Exclude a configuration group at this level";
                }

                ///nokia-conf/configure/system/security/snmp/source-access-list/source-host
                list source-host {
                    key "host-name";
                    max-elements 16;
                    description "Enter the source-host list instance";

                    ///nokia-conf/configure/system/security/snmp/source-access-list/source-host/host-name
                    leaf host-name {
                        type types-sros:named-item;
                        description "Source host entry name";
                    }

                    ///nokia-conf/configure/system/security/snmp/source-access-list/source-host/address
                    leaf address {
                        type types-sros:ip-unicast-address;
                        mandatory true;
                        description "Source IP address entry used to validate SNMP requests";
                    }

                    ///nokia-conf/configure/system/security/snmp/source-access-list/source-host/apply-groups
                    leaf-list apply-groups {
                        type leafref {
                            path "../../../../../../groups/group/name";
                        }
                        max-elements 8;
                        ordered-by user;
                        description "Apply a configuration group at this level";
                    }

                    ///nokia-conf/configure/system/security/snmp/source-access-list/source-host/apply-groups-exclude
                    leaf-list apply-groups-exclude {
                        type leafref {
                            path "../../../../../../groups/group/name";
                        }
                        max-elements 8;
                        ordered-by user;
                        description "Exclude a configuration group at this level";
                    }

                } // list source-host

            } // list source-access-list

            ///nokia-conf/configure/system/security/snmp/view
            list view {
                key "view-name subtree";
                description "Enter the view list instance";

                ///nokia-conf/configure/system/security/snmp/view/view-name
                leaf view-name {
                    type types-sros:named-item;
                    description "View name";
                }

                ///nokia-conf/configure/system/security/snmp/view/subtree
                leaf subtree {
                    type string {
                        length "1..256";
                    }
                    description "Object Identifier (OID) value";
                }

                ///nokia-conf/configure/system/security/snmp/view/mask
                leaf mask {
                    type string {
                        length "1..16";
                        pattern "(0X|0x)?(([A-Fa-f0-9]){2})+" {
                            error-message "Hex value must be even number of characters.";
                        }
                    }
                    description "Mask value as binary value, or hex value";
                }

                ///nokia-conf/configure/system/security/snmp/view/type
                leaf type {
                    type enumeration {
                        enum included                       { value 1; }
                        enum excluded                       { value 2; }
                    }
                    description "Type of SNMP security view mask";
                }

                ///nokia-conf/configure/system/security/snmp/view/apply-groups
                leaf-list apply-groups {
                    type leafref {
                        path "../../../../../groups/group/name";
                    }
                    max-elements 8;
                    ordered-by user;
                    description "Apply a configuration group at this level";
                }

                ///nokia-conf/configure/system/security/snmp/view/apply-groups-exclude
                leaf-list apply-groups-exclude {
                    type leafref {
                        path "../../../../../groups/group/name";
                    }
                    max-elements 8;
                    ordered-by user;
                    description "Exclude a configuration group at this level";
                }

            } // list view

        } // container snmp

    } // grouping conf-system-security-snmp

}
