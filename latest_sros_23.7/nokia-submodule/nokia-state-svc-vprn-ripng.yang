submodule nokia-state-svc-vprn-ripng {

    yang-version "1.1";

    belongs-to nokia-state { prefix "state"; }

    import ietf-yang-types                { prefix "yang"; }
    import nokia-sros-yang-extensions     { prefix "sros-ext"; }
    import nokia-types-ripng              { prefix "types-ripng"; }
    import nokia-types-sros               { prefix "types-sros"; }

    include nokia-state-service;
    include nokia-state-svc-vprn;

    sros-ext:sros-major-release "rel23";
    organization "Nokia";
    contact
        "Nokia SR OS Support
         Web: <http://www.nokia.com>";
    description
        "Nokia YANG Data model with operational state for vprn ripng protocol attributes on SR OS based routers.

         Copyright 2016 Nokia. All rights reserved. Reproduction of this document
         is authorized on the condition that the foregoing copyright notice is included.

         This nokia-state-svc-vprn-ripng YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-svc-vprn-ripng {
        ///nokia-state/state/service/vprn/ripng
        container ripng {
            description "Enable the ripng context";

            ///nokia-state/state/service/vprn/ripng/oper-state
            leaf oper-state {
                type types-sros:oper-state;
                description "The operational state of this RIPng instance.";
            }

            ///nokia-state/state/service/vprn/ripng/peer
            list peer {
                key "interface-name address";
                description "Enter the peer list instance";

                ///nokia-state/state/service/vprn/ripng/peer/interface-name
                leaf interface-name {
                    type types-sros:interface-name;
                    description "The interface on which this peer was discovered.";
                }

                ///nokia-state/state/service/vprn/ripng/peer/address
                leaf address {
                    type types-sros:ipv6-address;
                    description "IP Address the peer is using as its source address.";
                }

                ///nokia-state/state/service/vprn/ripng/peer/version
                leaf version {
                    type types-ripng:peer-version;
                    description "The RIPng version in the header of the last packet received from this peer.";
                }

                ///nokia-state/state/service/vprn/ripng/peer/last-update
                leaf last-update {
                    type yang:date-and-time;
                    description "The time the most recent RIPng update was received from this peer.";
                }

            } // list peer

            ///nokia-state/state/service/vprn/ripng/advertised-routes
            list advertised-routes {
                key "destination interface-name interface-address";
                description "Enter the advertised-routes list instance";

                ///nokia-state/state/service/vprn/ripng/advertised-routes/destination
                leaf destination {
                    type types-sros:ipv6-prefix-with-host-bits;
                    description
                        "Destination IP prefix of the advertised route. If length of prefix is zero,
                         then this indicates a default route.";
                }

                ///nokia-state/state/service/vprn/ripng/advertised-routes/interface-name
                leaf interface-name {
                    type types-sros:interface-name;
                    description "The interface on which the route is advertised.";
                }

                ///nokia-state/state/service/vprn/ripng/advertised-routes/interface-address
                leaf interface-address {
                    type types-sros:ipv6-address;
                    description "The IP address of the subnet/prefix to which the route is advertised.";
                }

                ///nokia-state/state/service/vprn/ripng/advertised-routes/next-hop
                leaf next-hop {
                    type types-sros:ipv6-address;
                    description "The IP address which is advertised in the Next Hop field of the RIPng updates.";
                }

                ///nokia-state/state/service/vprn/ripng/advertised-routes/metric
                leaf metric {
                    type types-ripng:metric;
                    description "The metric with which the route is advertised.";
                }

                ///nokia-state/state/service/vprn/ripng/advertised-routes/tag
                leaf tag {
                    type uint16;
                    description "The value which is advertised in the Route Tag field for the route.";
                }

                ///nokia-state/state/service/vprn/ripng/advertised-routes/ttl
                leaf ttl {
                    type uint32;
                    units "seconds";
                    description
                        "The number of seconds till the flush timer expires.
                         The flush timer is active for only those routes which are no longer valid.
                         Such routes will be advertised with a metric of 16 till the flush timer expires
                         after which they will be removed from the database.";
                }

            } // list advertised-routes

            ///nokia-state/state/service/vprn/ripng/database
            list database {
                key "destination interface-name peer";
                description "Enter the database list instance";

                ///nokia-state/state/service/vprn/ripng/database/destination
                leaf destination {
                    type types-sros:ipv6-prefix-with-host-bits;
                    description
                        "Destination IP prefix of the RIP route. If length of prefix is zero,
                         then this indicates a default route.";
                }

                ///nokia-state/state/service/vprn/ripng/database/interface-name
                leaf interface-name {
                    type types-sros:interface-name;
                    description "The interface on which this route was received.";
                }

                ///nokia-state/state/service/vprn/ripng/database/peer
                leaf peer {
                    type types-sros:ipv6-address;
                    description "The IP address of the peer from whom this route was received.";
                }

                ///nokia-state/state/service/vprn/ripng/database/next-hop
                leaf next-hop {
                    type types-sros:ipv6-address;
                    description
                        "The IP address in the Next Hop field of the RIPng updatevreceived for this route.
                         The Next Hop field is the immediate next hop IP address to which packets sent to the destination
                         specified by this route entry should be forwarded. A value of 0::0 in this field indicates that packets should be
                         forwarded to the originator of the RIPng advertisement.";
                }

                ///nokia-state/state/service/vprn/ripng/database/metric
                leaf metric {
                    type types-ripng:metric;
                    description "The distance to the destination as advertised by the peer that sent this route.";
                }

                ///nokia-state/state/service/vprn/ripng/database/tag
                leaf tag {
                    type uint16;
                    description "The value in the Route Tag field of the update received for this route.";
                }

                ///nokia-state/state/service/vprn/ripng/database/ttl
                leaf ttl {
                    type uint32;
                    units "seconds";
                    description "The number of seconds till the timeout timer expires.";
                }

                ///nokia-state/state/service/vprn/ripng/database/fc
                leaf fc {
                    type types-sros:fc-name;
                    description "The forwarding class associated with the RIPng route.";
                }

                ///nokia-state/state/service/vprn/ripng/database/priority
                leaf priority {
                    type types-sros:priority;
                    description "Specifies the priority to be assigned to the RIPng route.";
                }

                ///nokia-state/state/service/vprn/ripng/database/active
                leaf active {
                    type boolean;
                    description
                        "Indicates whether or not the route entry is active in the system.
                         It will be true if the route entry has been added to the Route Table Manager(RTM).";
                }

            } // list database

            ///nokia-state/state/service/vprn/ripng/group
            list group {
                key "group-name";
                description "Enter the group list instance";

                ///nokia-state/state/service/vprn/ripng/group/group-name
                leaf group-name {
                    type types-sros:named-item;
                    description "RIP group name";
                }

                ///nokia-state/state/service/vprn/ripng/group/oper-state
                leaf oper-state {
                    type types-sros:oper-state;
                    description "The operational state of this RIPng group.";
                }

                ///nokia-state/state/service/vprn/ripng/group/neighbor
                list neighbor {
                    key "interface-name";
                    description "Enter the neighbor list instance";

                    ///nokia-state/state/service/vprn/ripng/group/neighbor/interface-name
                    leaf interface-name {
                        type leafref {
                            path "../../../../interface/interface-name";
                        }
                        description "IP interface name";
                    }

                    ///nokia-state/state/service/vprn/ripng/group/neighbor/oper-state
                    leaf oper-state {
                        type types-sros:oper-state;
                        description "The operational state of this RIPng neighbor.";
                    }

                    ///nokia-state/state/service/vprn/ripng/group/neighbor/statistics
                    container statistics {
                        description "Enter the statistics context";

                        ///nokia-state/state/service/vprn/ripng/group/neighbor/statistics/updates-sent
                        container updates-sent {
                            description "Enter the updates-sent context";

                            ///nokia-state/state/service/vprn/ripng/group/neighbor/statistics/updates-sent/total
                            leaf total {
                                type yang:counter32;
                                description
                                    "The number of all RIPng updates actually sent on this interface.
                                     This explicitly does include full updates sent containing new information.";
                            }

                            ///nokia-state/state/service/vprn/ripng/group/neighbor/statistics/updates-sent/last-5min
                            leaf last-5min {
                                type yang:counter32;
                                description
                                    "The number of all RIPng updates actually sent on this interface in the last 5 minutes.
                                     This explicitly does include full updates sent containing new information.";
                            }

                            ///nokia-state/state/service/vprn/ripng/group/neighbor/statistics/updates-sent/last-1min
                            leaf last-1min {
                                type yang:counter32;
                                description
                                    "The number of all RIPng updates actually sent on this interface in the last minute.
                                     This explicitly does include full updates sent containing new information.";
                            }

                        } // container updates-sent

                        ///nokia-state/state/service/vprn/ripng/group/neighbor/statistics/triggered-updates
                        container triggered-updates {
                            description "Enter the triggered-updates context";

                            ///nokia-state/state/service/vprn/ripng/group/neighbor/statistics/triggered-updates/total
                            leaf total {
                                type yang:counter32;
                                description
                                    "The number of triggered RIPng updates actually sent on this interface.
                                     This explicitly does include full updates sent containing new information.";
                            }

                            ///nokia-state/state/service/vprn/ripng/group/neighbor/statistics/triggered-updates/last-5min
                            leaf last-5min {
                                type yang:counter32;
                                description
                                    "The number of triggered RIPng updates actually sent on this interface in the last 5 minutes.
                                     This explicitly does include full updates sent containing new information.";
                            }

                            ///nokia-state/state/service/vprn/ripng/group/neighbor/statistics/triggered-updates/last-1min
                            leaf last-1min {
                                type yang:counter32;
                                description
                                    "The number of triggered RIPng updates actually sent on this interface in the last minute.
                                     This explicitly does include full updates sent containing new information.";
                            }

                        } // container triggered-updates

                        ///nokia-state/state/service/vprn/ripng/group/neighbor/statistics/bad-packets-received
                        container bad-packets-received {
                            description "Enter the bad-packets-received context";

                            ///nokia-state/state/service/vprn/ripng/group/neighbor/statistics/bad-packets-received/total
                            leaf total {
                                type yang:counter32;
                                description "The number of RIPng updates received on this interface that were discarded as invalid.";
                            }

                            ///nokia-state/state/service/vprn/ripng/group/neighbor/statistics/bad-packets-received/last-5min
                            leaf last-5min {
                                type yang:counter32;
                                description
                                    "The number of RIPng response packets discarded (for any reason e.g. a version 0 packet,
                                     or an unknown command type) in the last 5 minutes.";
                            }

                            ///nokia-state/state/service/vprn/ripng/group/neighbor/statistics/bad-packets-received/last-1min
                            leaf last-1min {
                                type yang:counter32;
                                description
                                    "The number of RIPng response packets discarded (for any reason e.g. a version 0 packet,
                                     or an unknown command type) in the last minute.";
                            }

                        } // container bad-packets-received

                        ///nokia-state/state/service/vprn/ripng/group/neighbor/statistics/updates-received
                        container updates-received {
                            description "Enter the updates-received context";

                            ///nokia-state/state/service/vprn/ripng/group/neighbor/statistics/updates-received/total
                            leaf total {
                                type yang:counter32;
                                description "The number of RIPng response packets received.";
                            }

                            ///nokia-state/state/service/vprn/ripng/group/neighbor/statistics/updates-received/last-5min
                            leaf last-5min {
                                type yang:counter32;
                                description "The number of RIPng response packets received in the last 5 minutes.";
                            }

                            ///nokia-state/state/service/vprn/ripng/group/neighbor/statistics/updates-received/last-1min
                            leaf last-1min {
                                type yang:counter32;
                                description "The number of RIPng response packets received in the last minute.";
                            }

                        } // container updates-received

                        ///nokia-state/state/service/vprn/ripng/group/neighbor/statistics/updates-ignored
                        container updates-ignored {
                            description "Enter the updates-ignored context";

                            ///nokia-state/state/service/vprn/ripng/group/neighbor/statistics/updates-ignored/total
                            leaf total {
                                type yang:counter32;
                                description "The number of RIPng response packets received which were subsequently discarded for any reason.";
                            }

                            ///nokia-state/state/service/vprn/ripng/group/neighbor/statistics/updates-ignored/last-5min
                            leaf last-5min {
                                type yang:counter32;
                                description "The number of RIPng response packets received in the last 5 minutes which were subsequently discarded for any reason.";
                            }

                            ///nokia-state/state/service/vprn/ripng/group/neighbor/statistics/updates-ignored/last-1min
                            leaf last-1min {
                                type yang:counter32;
                                description "The number of RIPng response packets received in the last minute which were subsequently discarded for any reason.";
                            }

                        } // container updates-ignored

                        ///nokia-state/state/service/vprn/ripng/group/neighbor/statistics/bad-routes
                        container bad-routes {
                            description "Enter the bad-routes context";

                            ///nokia-state/state/service/vprn/ripng/group/neighbor/statistics/bad-routes/total
                            leaf total {
                                type yang:counter32;
                                description
                                    "The number of routes, in valid RIPng packets, which were ignored for any reason
                                     (e.g. unknown address family, or invalid metric).";
                            }

                            ///nokia-state/state/service/vprn/ripng/group/neighbor/statistics/bad-routes/last-5min
                            leaf last-5min {
                                type yang:counter32;
                                description
                                    "The number of routes, in valid RIPng packets, which were ignored for any reason
                                     (e.g. unknown address family, or invalid metric) in the last 5 minutes.";
                            }

                            ///nokia-state/state/service/vprn/ripng/group/neighbor/statistics/bad-routes/last-1min
                            leaf last-1min {
                                type yang:counter32;
                                description
                                    "The number of routes, in valid RIPng packets, which were ignored for any reason
                                     (e.g. unknown address family, or invalid metric) in the last minute.";
                            }

                        } // container bad-routes

                        ///nokia-state/state/service/vprn/ripng/group/neighbor/statistics/requests-received
                        container requests-received {
                            description "Enter the requests-received context";

                            ///nokia-state/state/service/vprn/ripng/group/neighbor/statistics/requests-received/total
                            leaf total {
                                type yang:counter32;
                                description "The number of RIPng request packets received.";
                            }

                            ///nokia-state/state/service/vprn/ripng/group/neighbor/statistics/requests-received/last-5min
                            leaf last-5min {
                                type yang:counter32;
                                description "The number RIPng request packets received in the last 5 minutes.";
                            }

                            ///nokia-state/state/service/vprn/ripng/group/neighbor/statistics/requests-received/last-1min
                            leaf last-1min {
                                type yang:counter32;
                                description "The number RIPng request packets received in the last minute.";
                            }

                        } // container requests-received

                        ///nokia-state/state/service/vprn/ripng/group/neighbor/statistics/requests-ignored
                        container requests-ignored {
                            description "Enter the requests-ignored context";

                            ///nokia-state/state/service/vprn/ripng/group/neighbor/statistics/requests-ignored/total
                            leaf total {
                                type yang:counter32;
                                description "The number of RIPng request packets received that were subsequently discarded for any reason.";
                            }

                            ///nokia-state/state/service/vprn/ripng/group/neighbor/statistics/requests-ignored/last-5min
                            leaf last-5min {
                                type yang:counter32;
                                description "The number of RIPng request packets received in the last 5 minutes that were subsequently discarded for any reason.";
                            }

                            ///nokia-state/state/service/vprn/ripng/group/neighbor/statistics/requests-ignored/last-1min
                            leaf last-1min {
                                type yang:counter32;
                                description "The number of RIPng request packets received in the last minute that were subsequently discarded for any reason.";
                            }

                        } // container requests-ignored

                    } // container statistics

                } // list neighbor

            } // list group

        } // container ripng

    } // grouping state-svc-vprn-ripng

}
