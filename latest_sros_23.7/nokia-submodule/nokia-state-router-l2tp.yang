submodule nokia-state-router-l2tp {

    yang-version "1.1";

    belongs-to nokia-state { prefix "state"; }

    import ietf-inet-types                { prefix "inet"; }
    import ietf-yang-types                { prefix "yang"; }
    import nokia-sros-yang-extensions     { prefix "sros-ext"; }
    import nokia-types-l2tp               { prefix "types-l2tp"; }
    import nokia-types-ppp                { prefix "types-ppp"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for l2tp on SR OS based routers.

         Copyright 2016 Nokia. All rights reserved. Reproduction of this document
         is authorized on the condition that the foregoing copyright notice is included.

         This nokia-state-router-l2tp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-11-18";

    grouping state-router-l2tp {
        ///nokia-state/state/router/l2tp
        container l2tp {
            description "Enable the l2tp context";

            ///nokia-state/state/router/l2tp/statistics
            container statistics {
                description "Enter the statistics context";

                ///nokia-state/state/router/l2tp/statistics/last-cleared
                leaf last-cleared {
                    type yang:date-and-time;
                    description "Indicates when the statistics were cleared.";
                }

                ///nokia-state/state/router/l2tp/statistics/total-tunnels
                leaf total-tunnels {
                    type yang:counter32;
                    description
                        "The total number of tunnels set up attempts since the last
                         re-initialization of the local network management subsystem,
                         or the last time the system statistics were cleared.";
                }

                ///nokia-state/state/router/l2tp/statistics/failed-tunnels
                leaf failed-tunnels {
                    type yang:counter32;
                    description
                        "The total number of tunnels that failed to reach the established
                         state since the last re-initialization of the local network
                         management subsystem, or the last time the system statistics were
                         cleared.";
                }

                ///nokia-state/state/router/l2tp/statistics/failed-authentication
                leaf failed-authentication {
                    type yang:counter32;
                    description
                        "The total number of tunnels that failed authentication
                         since the last re-initialization of the local network
                         management subsystem, or the last time the system statistics were
                         cleared.";
                }

                ///nokia-state/state/router/l2tp/statistics/actual-tunnels
                leaf actual-tunnels {
                    type yang:counter32;
                    description "The actual number of tunnels.";
                }

                ///nokia-state/state/router/l2tp/statistics/active-tunnels
                leaf active-tunnels {
                    type yang:counter32;
                    description "The number of tunnels currently established.";
                }

                ///nokia-state/state/router/l2tp/statistics/total-sessions
                leaf total-sessions {
                    type yang:counter32;
                    description
                        "The total number of session set up attempts since the last
                         re-initialization of the local network management subsystem,
                         or the last time the system statistics were cleared.";
                }

                ///nokia-state/state/router/l2tp/statistics/failed-sessions
                leaf failed-sessions {
                    type yang:counter32;
                    description
                        "The total number of sessions that failed to reach the established
                         state since the last re-initialization of the local network
                         management subsystem, or the last time the system statistics were
                         cleared.";
                }

                ///nokia-state/state/router/l2tp/statistics/actual-sessions
                leaf actual-sessions {
                    type yang:counter32;
                    description "The actual number of sessions.";
                }

                ///nokia-state/state/router/l2tp/statistics/active-sessions
                leaf active-sessions {
                    type yang:counter32;
                    description "The number of sessions currently established.";
                }

                ///nokia-state/state/router/l2tp/statistics/blacklist-len
                leaf blacklist-len {
                    type yang:gauge32;
                    description
                        "The actual number of tunnels and peers in the tunnel
                         selection blacklist.";
                }

                ///nokia-state/state/router/l2tp/statistics/unavailable-tunnel-ids
                leaf unavailable-tunnel-ids {
                    type yang:gauge32;
                    description
                        "The number of tunnel identifiers that is unavailable for the
                         L2TP protocol because they are used by some other application.";
                }

            } // container statistics

            ///nokia-state/state/router/l2tp/oper-group
            list oper-group {
                key "tunnel-group-name";
                description "Enter the oper-group list instance";

                ///nokia-state/state/router/l2tp/oper-group/tunnel-group-name
                leaf tunnel-group-name {
                    type types-sros:named-item-64 {
                        length "1..63";
                    }
                    description "Tunnel group name";
                }

                ///nokia-state/state/router/l2tp/oper-group/oper-state
                leaf oper-state {
                    type types-l2tp:group-oper-state;
                    description "The operational state of the tunnel group.";
                }

                ///nokia-state/state/router/l2tp/oper-group/session-limit
                leaf session-limit {
                    type types-l2tp:base-session-limit;
                    description "The administrative session limit of this tunnel group.";
                }

                ///nokia-state/state/router/l2tp/oper-group/oper-session-limit
                leaf oper-session-limit {
                    type uint32;
                    description "The operational session limit of this tunnel group.";
                }

                ///nokia-state/state/router/l2tp/oper-group/session-assign-method
                leaf session-assign-method {
                    type types-l2tp:base-session-assign-method;
                    description
                        "The latest actual method use for the authentication
                         of the tunnels in this tunnel group.";
                }

                ///nokia-state/state/router/l2tp/oper-group/statistics
                container statistics {
                    description "Enter the statistics context";

                    ///nokia-state/state/router/l2tp/oper-group/statistics/last-cleared
                    leaf last-cleared {
                        type yang:date-and-time;
                        description "Indicates when the statistics were cleared.";
                    }

                    ///nokia-state/state/router/l2tp/oper-group/statistics/total-tunnels
                    leaf total-tunnels {
                        type yang:counter32;
                        description
                            "The total number of tunnel set up attempts
                             in this tunnel group since the last re-initialization
                             of the local network management subsystem, or the last
                             time the system statistics were cleared.";
                    }

                    ///nokia-state/state/router/l2tp/oper-group/statistics/failed-tunnels
                    leaf failed-tunnels {
                        type yang:counter32;
                        description
                            "The total number of tunnels in this tunnel group
                             that failed to reach the established state since the last
                             re-initialization of the local network management subsystem,
                             or the last time the system statistics were cleared.";
                    }

                    ///nokia-state/state/router/l2tp/oper-group/statistics/auth-failed-tunnels
                    leaf auth-failed-tunnels {
                        type yang:counter32;
                        description
                            "The total number of tunnels in this tunnel group
                             that failed authentication since the last re-initialization
                             of the local network management subsystem, or the last time
                             the system statistics were cleared.";
                    }

                    ///nokia-state/state/router/l2tp/oper-group/statistics/active-tunnels
                    leaf active-tunnels {
                        type yang:gauge32;
                        description
                            "The total number of tunnels currently established
                             in this tunnel group.";
                    }

                    ///nokia-state/state/router/l2tp/oper-group/statistics/tunnels
                    leaf tunnels {
                        type yang:gauge32;
                        description "The actual number of tunnels in this tunnel group.";
                    }

                    ///nokia-state/state/router/l2tp/oper-group/statistics/total-sessions
                    leaf total-sessions {
                        type yang:counter32;
                        description
                            "The total number of session creation attempts
                             in this tunnel group since the last re-initialization
                             of the local network management subsystem, or the last
                             time the system statistics were cleared.";
                    }

                    ///nokia-state/state/router/l2tp/oper-group/statistics/failed-sessions
                    leaf failed-sessions {
                        type yang:counter32;
                        description
                            "The total number of sessions in this tunnel group
                             that failed to reach the established state since the last
                             re-initialization of the local network management subsystem,
                             or the last time the system statistics were cleared.";
                    }

                    ///nokia-state/state/router/l2tp/oper-group/statistics/active-sessions
                    leaf active-sessions {
                        type yang:gauge32;
                        description
                            "The total number of sessions currently established
                             in this tunnel group.";
                    }

                    ///nokia-state/state/router/l2tp/oper-group/statistics/sessions
                    leaf sessions {
                        type yang:gauge32;
                        description "The actual number of sessions in this tunnel group.";
                    }

                    ///nokia-state/state/router/l2tp/oper-group/statistics/rx-control-octets
                    leaf rx-control-octets {
                        type yang:counter64;
                        units "octets";
                        description
                            "The number of control-channel octets received by the
                             current tunnels in this tunnel group.";
                    }

                    ///nokia-state/state/router/l2tp/oper-group/statistics/rx-control-packets
                    leaf rx-control-packets {
                        type yang:counter32;
                        units "packets";
                        description
                            "The number of control-channel packets received by the
                             current tunnels in this tunnel group.";
                    }

                    ///nokia-state/state/router/l2tp/oper-group/statistics/errored-packets
                    leaf errored-packets {
                        type yang:gauge32;
                        units "packets";
                        description
                            "The accumulated number of control packets that were
                             received by the current tunnel endpoints in this tunnel group.";
                    }

                    ///nokia-state/state/router/l2tp/oper-group/statistics/tx-control-octets
                    leaf tx-control-octets {
                        type yang:counter64;
                        units "octets";
                        description
                            "The number of control-channel octets transmitted by the
                             current tunnels in this tunnel group.";
                    }

                    ///nokia-state/state/router/l2tp/oper-group/statistics/tx-control-packets
                    leaf tx-control-packets {
                        type yang:counter32;
                        units "packets";
                        description
                            "The number of control-channel packets transmitted by the
                             current tunnels in this tunnel group.";
                    }

                    ///nokia-state/state/router/l2tp/oper-group/statistics/transmission-errors
                    leaf transmission-errors {
                        type yang:gauge32;
                        units "packets";
                        description
                            "The accumulated number of control packet transmission errors
                             on the current tunnels in this tunnel group.";
                    }

                } // container statistics

            } // list oper-group

            ///nokia-state/state/router/l2tp/tunnel
            list tunnel {
                key "tunnel-conn-id";
                description "Enter the tunnel list instance";

                ///nokia-state/state/router/l2tp/tunnel/tunnel-conn-id
                leaf tunnel-conn-id {
                    type types-l2tp:connection-id;
                    description "The local connection-id of the control channel of the tunnel.";
                }

                ///nokia-state/state/router/l2tp/tunnel/oper-state
                leaf oper-state {
                    type types-l2tp:tunnel-oper-state;
                    description "The operational state of the tunnel.";
                }

                ///nokia-state/state/router/l2tp/tunnel/start-time
                leaf start-time {
                    type yang:date-and-time;
                    description "The time when this tunnel reached the state wait-reply or wait-connected.";
                }

                ///nokia-state/state/router/l2tp/tunnel/established-time
                leaf established-time {
                    type yang:date-and-time;
                    description "The time when this tunnel reached an active state.";
                }

                ///nokia-state/state/router/l2tp/tunnel/idle-time
                leaf idle-time {
                    type yang:date-and-time;
                    description "The time when this tunnel entered the state idle.";
                }

                ///nokia-state/state/router/l2tp/tunnel/closed-time
                leaf closed-time {
                    type yang:date-and-time;
                    description "The time when this tunnel entered the state closed or closed-by-peer.";
                }

                ///nokia-state/state/router/l2tp/tunnel/stop-ccn-result
                leaf stop-ccn-result {
                    type types-l2tp:stop-ccn-result;
                    description "The result of a transmitted or received StopCCN message.";
                }

                ///nokia-state/state/router/l2tp/tunnel/general-error
                leaf general-error {
                    type types-l2tp:general-error;
                    description "The general error of a transmitted or received StopCCN message.";
                }

                ///nokia-state/state/router/l2tp/tunnel/error-message
                leaf error-message {
                    type string {
                        length "1..255";
                    }
                    description "Describes the L2TP error condition in human readable form.";
                }

                ///nokia-state/state/router/l2tp/tunnel/act-receive-window-size
                leaf act-receive-window-size {
                    type uint32;
                    description "The actual receive window size.";
                }

                ///nokia-state/state/router/l2tp/tunnel/blacklist-state
                leaf blacklist-state {
                    type types-l2tp:blacklist-state;
                    description "Indicates if this tunnel is deemed reachable or not.";
                }

                ///nokia-state/state/router/l2tp/tunnel/blacklist-time
                leaf blacklist-time {
                    type yang:date-and-time;
                    description "The time when this tunnel was placed in the tunnel-selection-blacklist.";
                }

                ///nokia-state/state/router/l2tp/tunnel/blacklist-remain-time
                leaf blacklist-remain-time {
                    type uint32;
                    units "seconds";
                    description "Indicates how long the tunnel must still remain in the tunnel-selection-blacklist.";
                }

                ///nokia-state/state/router/l2tp/tunnel/oper-session-limit
                leaf oper-session-limit {
                    type uint32;
                    description "The operational session limit of this tunnel.";
                }

                ///nokia-state/state/router/l2tp/tunnel/connection
                container connection {
                    description "Enter the connection context";

                    ///nokia-state/state/router/l2tp/tunnel/connection/rem-conn-id
                    leaf rem-conn-id {
                        type types-l2tp:connection-id;
                        description "The remote connection-id of control channel.";
                    }

                    ///nokia-state/state/router/l2tp/tunnel/connection/loc-tunnel-id
                    leaf loc-tunnel-id {
                        type types-l2tp:tunnel-id;
                        description "The local tunnel-id.";
                    }

                    ///nokia-state/state/router/l2tp/tunnel/connection/rem-tunnel-id
                    leaf rem-tunnel-id {
                        type types-l2tp:tunnel-id;
                        description "The remote tunnel-id.";
                    }

                    ///nokia-state/state/router/l2tp/tunnel/connection/transport-type
                    leaf transport-type {
                        type types-l2tp:transport-type;
                        description "The transport type used to carry L2TP messages.";
                    }

                    ///nokia-state/state/router/l2tp/tunnel/connection/peer
                    leaf peer {
                        type types-sros:ip-address;
                        description "The peer address";
                    }

                    ///nokia-state/state/router/l2tp/tunnel/connection/rem-udp-port
                    leaf rem-udp-port {
                        type inet:port-number;
                        description "The remote UDP port of this L2TP tunnel.";
                    }

                    ///nokia-state/state/router/l2tp/tunnel/connection/tx-dst-address
                    leaf tx-dst-address {
                        type types-sros:ip-address;
                        description
                            "The address used as destination IP address for transmitting
                             L2TP control messages";
                    }

                    ///nokia-state/state/router/l2tp/tunnel/connection/tx-dst-udp-port
                    leaf tx-dst-udp-port {
                        type inet:port-number;
                        description "The destination UDP port used while transmitting L2TP control messages.";
                    }

                    ///nokia-state/state/router/l2tp/tunnel/connection/rx-src-address
                    leaf rx-src-address {
                        type types-sros:ip-address;
                        description
                            "The address found as source IP address in received L2TP control
                             messages";
                    }

                    ///nokia-state/state/router/l2tp/tunnel/connection/rx-src-udp-port
                    leaf rx-src-udp-port {
                        type inet:port-number;
                        description "The source UDP port found in received L2TP control messages.";
                    }

                    ///nokia-state/state/router/l2tp/tunnel/connection/local-address
                    leaf local-address {
                        type types-sros:ip-address;
                        description "The local address";
                    }

                    ///nokia-state/state/router/l2tp/tunnel/connection/loc-udp-port
                    leaf loc-udp-port {
                        type inet:port-number;
                        description "The local UDP port of this L2TP tunnel.";
                    }

                    ///nokia-state/state/router/l2tp/tunnel/connection/local-name
                    leaf local-name {
                        type types-sros:named-item-64;
                        description "The local host name.";
                    }

                    ///nokia-state/state/router/l2tp/tunnel/connection/remote-name
                    leaf remote-name {
                        type types-sros:named-item-64;
                        description "The remote host name.";
                    }

                } // container connection

                ///nokia-state/state/router/l2tp/tunnel/parameters
                container parameters {
                    description "Enter the parameters context";

                    ///nokia-state/state/router/l2tp/tunnel/parameters/protocol
                    leaf protocol {
                        type types-l2tp:protocol-version;
                        description "The protocol version being used";
                    }

                    ///nokia-state/state/router/l2tp/tunnel/parameters/tunnel-group-name
                    leaf tunnel-group-name {
                        type types-sros:named-item-64;
                        description "The name of the tunnel group to which this tunnel belongs";
                    }

                    ///nokia-state/state/router/l2tp/tunnel/parameters/assignment-id
                    leaf assignment-id {
                        type types-sros:named-item {
                            length "1..32";
                        }
                        description "The identifier assigned to this tunnel.";
                    }

                    ///nokia-state/state/router/l2tp/tunnel/parameters/preference
                    leaf preference {
                        type uint32;
                        description "The preference of the tunnel.";
                    }

                    ///nokia-state/state/router/l2tp/tunnel/parameters/hello-interval
                    leaf hello-interval {
                        type types-l2tp:base-hello-interval;
                        description "The hello interval.";
                    }

                    ///nokia-state/state/router/l2tp/tunnel/parameters/idle-timeout
                    leaf idle-timeout {
                        type types-l2tp:base-idle-timeout;
                        description "The idle timeout.";
                    }

                    ///nokia-state/state/router/l2tp/tunnel/parameters/destruct-timeout
                    leaf destruct-timeout {
                        type types-l2tp:base-destruct-timeout;
                        description "The destruction timeout.";
                    }

                    ///nokia-state/state/router/l2tp/tunnel/parameters/max-retries-estab
                    leaf max-retries-estab {
                        type types-l2tp:base-max-retries;
                        description "The maximum number of retries when the tunnel is established.";
                    }

                    ///nokia-state/state/router/l2tp/tunnel/parameters/max-retries-not-estab
                    leaf max-retries-not-estab {
                        type types-l2tp:base-max-retries;
                        description "The maximum number of retries when the tunnel is not established.";
                    }

                    ///nokia-state/state/router/l2tp/tunnel/parameters/radius-accounting-policy
                    leaf radius-accounting-policy {
                        type types-sros:named-item;
                        description "The RADIUS accounting policy.";
                    }

                    ///nokia-state/state/router/l2tp/tunnel/parameters/challenge
                    leaf challenge {
                        type boolean;
                        description "Indicates if challenge-response authentication is used or not.";
                    }

                    ///nokia-state/state/router/l2tp/tunnel/parameters/avp-hiding
                    leaf avp-hiding {
                        type types-l2tp:base-avp-hiding;
                        description "The AVP hiding.";
                    }

                    ///nokia-state/state/router/l2tp/tunnel/parameters/session-limit
                    leaf session-limit {
                        type types-l2tp:base-session-limit;
                        description "The administrative session limit of this L2TP tunnel";
                    }

                    ///nokia-state/state/router/l2tp/tunnel/parameters/df-bit-lac
                    leaf df-bit-lac {
                        type boolean;
                        description "Indicates if the DF (don't fragment) bit is set in data traffic transmitted as LAC.";
                    }

                } // container parameters

                ///nokia-state/state/router/l2tp/tunnel/failover
                container failover {
                    description "Enter the failover context";

                    ///nokia-state/state/router/l2tp/tunnel/failover/failover-state
                    leaf failover-state {
                        type types-l2tp:failover-state;
                        description "The failover state of this tunnel.";
                    }

                    ///nokia-state/state/router/l2tp/tunnel/failover/recovery-conn-id
                    leaf recovery-conn-id {
                        type types-l2tp:connection-id;
                        description "The connection-id of the recovery tunnel.";
                    }

                    ///nokia-state/state/router/l2tp/tunnel/failover/recovery-state
                    leaf recovery-state {
                        type types-l2tp:recovery-state;
                        description "The failover state of a recovery tunnel.";
                    }

                    ///nokia-state/state/router/l2tp/tunnel/failover/recovered-conn-id
                    leaf recovered-conn-id {
                        type types-l2tp:connection-id;
                        description "The connection-id of the recovered tunnel.";
                    }

                    ///nokia-state/state/router/l2tp/tunnel/failover/recovery-method
                    leaf recovery-method {
                        type types-l2tp:base-failover-recovery-method;
                        description "The recovery method.";
                    }

                    ///nokia-state/state/router/l2tp/tunnel/failover/track-srrp
                    leaf track-srrp {
                        type uint32;
                        description "The SRRP instance used for recovery.";
                    }

                    ///nokia-state/state/router/l2tp/tunnel/failover/ctrl-msg-behavior
                    leaf ctrl-msg-behavior {
                        type types-l2tp:control-msg-behavior;
                        description "The behavior of the system with respect to L2TP control traffic.";
                    }

                    ///nokia-state/state/router/l2tp/tunnel/failover/requested-recovery-time
                    leaf requested-recovery-time {
                        type types-l2tp:recovery-time;
                        description "The recovery time requested to the peer system.";
                    }

                    ///nokia-state/state/router/l2tp/tunnel/failover/peer-recovery-time
                    leaf peer-recovery-time {
                        type types-l2tp:recovery-time;
                        description "The recovery time requested by the peer system.";
                    }

                } // container failover

                ///nokia-state/state/router/l2tp/tunnel/l2tpv3
                container l2tpv3 {
                    description "Enter the l2tpv3 context";

                    ///nokia-state/state/router/l2tp/tunnel/l2tpv3/cookie-length
                    leaf cookie-length {
                        type types-l2tp:base-v3-cookie-length;
                        description "The cookie length.";
                    }

                    ///nokia-state/state/router/l2tp/tunnel/l2tpv3/digest-type
                    leaf digest-type {
                        type types-l2tp:base-v3-digest-type;
                        description "The digest type";
                    }

                    ///nokia-state/state/router/l2tp/tunnel/l2tpv3/local-nonce
                    leaf local-nonce {
                        type types-l2tp:nonce;
                        description "The nonce AVP added to the outgoing control messages.";
                    }

                    ///nokia-state/state/router/l2tp/tunnel/l2tpv3/remote-nonce
                    leaf remote-nonce {
                        type types-l2tp:nonce;
                        description "The nonce AVP found in incoming control messages.";
                    }

                    ///nokia-state/state/router/l2tp/tunnel/l2tpv3/rem-router-id
                    leaf rem-router-id {
                        type types-sros:ipv4-address;
                        description "The filter used on remote router ID.";
                    }

                    ///nokia-state/state/router/l2tp/tunnel/l2tpv3/public-tcp-mss-adjust
                    leaf public-tcp-mss-adjust {
                        type types-l2tp:base-v3-tcp-mss-adjust;
                        description "The TCP maximum segment size (MSS) on public network.";
                    }

                    ///nokia-state/state/router/l2tp/tunnel/l2tpv3/private-tcp-mss-adjust
                    leaf private-tcp-mss-adjust {
                        type types-l2tp:base-v3-tcp-mss-adjust;
                        description "The TCP maximum segment size (MSS) on private network.";
                    }

                    ///nokia-state/state/router/l2tp/tunnel/l2tpv3/pw-cap-list
                    container pw-cap-list {
                        description "Enter the pw-cap-list context";

                        ///nokia-state/state/router/l2tp/tunnel/l2tpv3/pw-cap-list/ethernet
                        leaf ethernet {
                            type boolean;
                            description "Ethernet pseudo-wire encapsulation is accepted";
                        }

                        ///nokia-state/state/router/l2tp/tunnel/l2tpv3/pw-cap-list/ethernet-vlan
                        leaf ethernet-vlan {
                            type boolean;
                            description "Ethernet VLAN pseudo-wire encapsulation is accepted";
                        }

                    } // container pw-cap-list

                } // container l2tpv3

                ///nokia-state/state/router/l2tp/tunnel/statistics
                container statistics {
                    description "Enter the statistics context";

                    ///nokia-state/state/router/l2tp/tunnel/statistics/last-cleared
                    leaf last-cleared {
                        type yang:date-and-time;
                        description "The time when the statistics were cleared.";
                    }

                    ///nokia-state/state/router/l2tp/tunnel/statistics/total-sessions
                    leaf total-sessions {
                        type yang:counter32;
                        description
                            "The total number of session creation attempts
                             in this tunnel since the last re-initialization
                             of the local network management subsystem, or the last
                             time the system statistics were cleared.";
                    }

                    ///nokia-state/state/router/l2tp/tunnel/statistics/failed-sessions
                    leaf failed-sessions {
                        type yang:counter32;
                        description
                            "The total number of sessions in this tunnel
                             that failed to reach the established state since the last
                             re-initialization of the local network management subsystem,
                             or the last time the system statistics were cleared.";
                    }

                    ///nokia-state/state/router/l2tp/tunnel/statistics/active-sessions
                    leaf active-sessions {
                        type yang:gauge32;
                        description
                            "The total number of sessions currently established
                             in this tunnel.";
                    }

                    ///nokia-state/state/router/l2tp/tunnel/statistics/sessions
                    leaf sessions {
                        type yang:gauge32;
                        description "The actual number of sessions in this tunnel.";
                    }

                    ///nokia-state/state/router/l2tp/tunnel/statistics/rx-control-octets
                    leaf rx-control-octets {
                        type yang:counter64;
                        units "octets";
                        description
                            "The number of control-channel octets received by the
                             tunnel.";
                    }

                    ///nokia-state/state/router/l2tp/tunnel/statistics/rx-control-packets
                    leaf rx-control-packets {
                        type yang:counter32;
                        units "packets";
                        description
                            "The number of control-channel packets received by the
                             tunnel.";
                    }

                    ///nokia-state/state/router/l2tp/tunnel/statistics/errored-packets
                    leaf errored-packets {
                        type yang:gauge32;
                        units "packets";
                        description
                            "The accumulated number of control packets that were
                             received by the current tunnel endpoints in this tunnel group.";
                    }

                    ///nokia-state/state/router/l2tp/tunnel/statistics/tx-control-octets
                    leaf tx-control-octets {
                        type yang:counter64;
                        units "octets";
                        description
                            "The number of control-channel octets transmitted by the
                             tunnel.";
                    }

                    ///nokia-state/state/router/l2tp/tunnel/statistics/tx-control-packets
                    leaf tx-control-packets {
                        type yang:counter32;
                        units "packets";
                        description
                            "The number of control-channel packets transmitted by the
                             tunnel.";
                    }

                    ///nokia-state/state/router/l2tp/tunnel/statistics/transmission-errors
                    leaf transmission-errors {
                        type yang:gauge32;
                        units "packets";
                        description
                            "The accumulated number of control packet transmission errors
                             for the tunnel.";
                    }

                    ///nokia-state/state/router/l2tp/tunnel/statistics/fsm-msg-accepted
                    leaf fsm-msg-accepted {
                        type yang:counter32;
                        units "packets";
                        description
                            "The number of Finite State Machine (FSM) messages that were
                             accepted on this tunnel since the last re-initialization of the local
                             network management subsystem, or the last time the tunnel statistics were
                             cleared.";
                    }

                    ///nokia-state/state/router/l2tp/tunnel/statistics/fsm-msg-duplicates
                    leaf fsm-msg-duplicates {
                        type yang:counter32;
                        units "packets";
                        description
                            "The number of duplicate Finite State Machine (FSM) messages that
                             were received on this tunnel since the last re-initialization of the local
                             network management subsystem, or the last time the tunnel statistics were
                             cleared.";
                    }

                    ///nokia-state/state/router/l2tp/tunnel/statistics/fsm-msg-out-of-rx-window
                    leaf fsm-msg-out-of-rx-window {
                        type yang:counter32;
                        units "packets";
                        description
                            "The number of Finite State Machine (FSM) messages that were received
                             out of the receive window on this tunnel since the last re-initialization of
                             the local network management subsystem, or the last time the tunnel statistics
                             were cleared.";
                    }

                    ///nokia-state/state/router/l2tp/tunnel/statistics/max-unsent-queue-length
                    leaf max-unsent-queue-length {
                        type yang:gauge32;
                        units "packets";
                        description
                            "The maximum length of the unsent message queue on this tunnel since the last
                             re-initialization of the local network management subsystem, or the last time
                             the tunnel statistics were cleared.";
                    }

                    ///nokia-state/state/router/l2tp/tunnel/statistics/cur-unsent-queue-length
                    leaf cur-unsent-queue-length {
                        type yang:gauge32;
                        units "packets";
                        description "The current length of the unsent message queue on this tunnel.";
                    }

                    ///nokia-state/state/router/l2tp/tunnel/statistics/max-ack-queue-length
                    leaf max-ack-queue-length {
                        type yang:gauge32;
                        units "packets";
                        description
                            "The maximum length of the to-be-acknowledged message queue on this tunnel since
                             the last re-initialization of the local network management subsystem, or the
                             last time the tunnel statistics were cleared.";
                    }

                    ///nokia-state/state/router/l2tp/tunnel/statistics/cur-ack-queue-length
                    leaf cur-ack-queue-length {
                        type yang:gauge32;
                        units "packets";
                        description "The current length of the to-be-acknowledged  message queue on this tunnel.";
                    }

                    ///nokia-state/state/router/l2tp/tunnel/statistics/cur-window-size
                    leaf cur-window-size {
                        type yang:gauge32;
                        description "The current size of the receive window on this tunnel.";
                    }

                    ///nokia-state/state/router/l2tp/tunnel/statistics/protocol
                    list protocol {
                        key "type id";
                        description "Enter the protocol list instance";

                        ///nokia-state/state/router/l2tp/tunnel/statistics/protocol/type
                        leaf type {
                            type types-l2tp:proto-stats-type;
                            description "The statistics type.";
                        }

                        ///nokia-state/state/router/l2tp/tunnel/statistics/protocol/id
                        leaf id {
                            type uint32 {
                                range "0..69|4294967294|4294967295";
                            }
                            description "The counter id.";
                        }

                        ///nokia-state/state/router/l2tp/tunnel/statistics/protocol/name
                        leaf name {
                            type types-sros:display-string;
                            description "The human-readable identifier of the statistic.";
                        }

                        ///nokia-state/state/router/l2tp/tunnel/statistics/protocol/value
                        leaf value {
                            type yang:counter32;
                            description "The counter value";
                        }

                    } // list protocol

                } // container statistics

            } // list tunnel

            ///nokia-state/state/router/l2tp/session
            list session {
                key "session-conn-id";
                description "Enter the session list instance";

                ///nokia-state/state/router/l2tp/session/session-conn-id
                leaf session-conn-id {
                    type types-l2tp:connection-id;
                    description "The local connection-id of the session.";
                }

                ///nokia-state/state/router/l2tp/session/oper-state
                leaf oper-state {
                    type types-l2tp:session-oper-state;
                    description "The operational state of the session.";
                }

                ///nokia-state/state/router/l2tp/session/start-time
                leaf start-time {
                    type yang:date-and-time;
                    description "The time when this session reached the state idle, wait-tunnel, wait-reply or wait-acceptance.";
                }

                ///nokia-state/state/router/l2tp/session/established-time
                leaf established-time {
                    type yang:date-and-time;
                    description "The time when this session entered the state established.";
                }

                ///nokia-state/state/router/l2tp/session/closed-time
                leaf closed-time {
                    type yang:date-and-time;
                    description "The time when this session entered the state closed or closed-by-peer.";
                }

                ///nokia-state/state/router/l2tp/session/cdn-result
                leaf cdn-result {
                    type types-l2tp:cdn-result;
                    description "The result of a transmitted or received CDN message.";
                }

                ///nokia-state/state/router/l2tp/session/general-error
                leaf general-error {
                    type types-l2tp:general-error;
                    description "The general error of a transmitted or received CDN message.";
                }

                ///nokia-state/state/router/l2tp/session/error-message
                leaf error-message {
                    type string {
                        length "0..255";
                    }
                    description "Describes an L2TP error condition in human readable form.";
                }

                ///nokia-state/state/router/l2tp/session/mlppp-bundle
                leaf mlppp-bundle {
                    type types-l2tp:mlppp-bundle-index;
                    description "The index of the MLPPP bundle to which this session belongs.";
                }

                ///nokia-state/state/router/l2tp/session/pw-type
                leaf pw-type {
                    type types-l2tp:pseudo-wire-type;
                    description "The pseudo-wire type of the session.";
                }

                ///nokia-state/state/router/l2tp/session/connection
                container connection {
                    description "Enter the connection context";

                    ///nokia-state/state/router/l2tp/session/connection/loc-tunnel-id
                    leaf loc-tunnel-id {
                        type types-l2tp:tunnel-id;
                        description "The local tunnel-id.";
                    }

                    ///nokia-state/state/router/l2tp/session/connection/rem-tunnel-id
                    leaf rem-tunnel-id {
                        type types-l2tp:tunnel-id;
                        description "The remote tunnel-id.";
                    }

                    ///nokia-state/state/router/l2tp/session/connection/loc-session-id
                    leaf loc-session-id {
                        type types-l2tp:session-id;
                        description "The local session-id.";
                    }

                    ///nokia-state/state/router/l2tp/session/connection/rem-session-id
                    leaf rem-session-id {
                        type types-l2tp:session-id;
                        description "The remote session-id.";
                    }

                    ///nokia-state/state/router/l2tp/session/connection/rem-connection-id
                    leaf rem-connection-id {
                        type types-l2tp:connection-id;
                        description "The remote connection-id of the session.";
                    }

                    ///nokia-state/state/router/l2tp/session/connection/control-connection-id
                    leaf control-connection-id {
                        type types-l2tp:connection-id;
                        description "The local connection-id of the control connection of the tunnel.";
                    }

                } // container connection

                ///nokia-state/state/router/l2tp/session/l2tpv3
                container l2tpv3 {
                    description "Enter the l2tpv3 context";

                    ///nokia-state/state/router/l2tp/session/l2tpv3/rx-cookie
                    leaf rx-cookie {
                        type binary {
                            length "1..8";
                        }
                        description "The cookie found in received data packets.";
                    }

                    ///nokia-state/state/router/l2tp/session/l2tpv3/tx-cookie
                    leaf tx-cookie {
                        type binary {
                            length "1..8";
                        }
                        description "The cookie used in transmitted data packets.";
                    }

                    ///nokia-state/state/router/l2tp/session/l2tpv3/endpoint-id
                    leaf endpoint-id {
                        type binary {
                            length "1..250";
                        }
                        description "The endpoint identification of the session.";
                    }

                    ///nokia-state/state/router/l2tp/session/l2tpv3/endpoint-description
                    leaf endpoint-description {
                        type types-sros:display-string-or-empty {
                            length "0..80";
                        }
                        description "The endpoint description of the session.";
                    }

                    ///nokia-state/state/router/l2tp/session/l2tpv3/seq-num-in-rx
                    leaf seq-num-in-rx {
                        type types-l2tp:seq-num-present-in-packet-type;
                        description "Indicates in which received packets sequence numbers are present.";
                    }

                    ///nokia-state/state/router/l2tp/session/l2tpv3/seq-num-in-tx
                    leaf seq-num-in-tx {
                        type types-l2tp:seq-num-present-in-packet-type;
                        description "Indicates in which received packets sequence numbers are present.";
                    }

                    ///nokia-state/state/router/l2tp/session/l2tpv3/l2-sub-layer-in-rx
                    leaf l2-sub-layer-in-rx {
                        type boolean;
                        description "Indicates if the l2 sub-layer is present in received packets.";
                    }

                    ///nokia-state/state/router/l2tp/session/l2tpv3/l2-sub-layer-in-tx
                    leaf l2-sub-layer-in-tx {
                        type boolean;
                        description "Indicates if the l2 sub-layer is present in transmitted packets.";
                    }

                } // container l2tpv3

                ///nokia-state/state/router/l2tp/session/statistics
                container statistics {
                    description "Enter the statistics context";

                    ///nokia-state/state/router/l2tp/session/statistics/ethernet-tunnel
                    container ethernet-tunnel {
                        description "Enter the ethernet-tunnel context";

                        ///nokia-state/state/router/l2tp/session/statistics/ethernet-tunnel/rx-packets
                        leaf rx-packets {
                            type yang:counter64;
                            units "packets";
                            description "The the number of packets received.";
                        }

                        ///nokia-state/state/router/l2tp/session/statistics/ethernet-tunnel/rx-octets
                        leaf rx-octets {
                            type yang:counter64;
                            units "octets";
                            description "The number of octets received.";
                        }

                        ///nokia-state/state/router/l2tp/session/statistics/ethernet-tunnel/rx-errors
                        leaf rx-errors {
                            type yang:counter64;
                            units "packets";
                            description "The number of packets dropped while receiving.";
                        }

                        ///nokia-state/state/router/l2tp/session/statistics/ethernet-tunnel/rx-cookie-mismatch
                        leaf rx-cookie-mismatch {
                            type yang:counter64;
                            units "packets";
                            description
                                "The number of packets dropped because the received cookie value
                                 did not match the cookie value negotiated during session establishment.";
                        }

                        ///nokia-state/state/router/l2tp/session/statistics/ethernet-tunnel/rx-session-id-mismatch
                        leaf rx-session-id-mismatch {
                            type yang:counter64;
                            units "packets";
                            description
                                "The number of packets dropped because the received session-id
                                 did not match the session-id negotiated during session establishment.";
                        }

                        ///nokia-state/state/router/l2tp/session/statistics/ethernet-tunnel/tx-packets
                        leaf tx-packets {
                            type yang:counter64;
                            units "packets";
                            description "The number of packets transmitted.";
                        }

                        ///nokia-state/state/router/l2tp/session/statistics/ethernet-tunnel/tx-octets
                        leaf tx-octets {
                            type yang:counter64;
                            units "octets";
                            description "The number of octets transmitted.";
                        }

                        ///nokia-state/state/router/l2tp/session/statistics/ethernet-tunnel/tx-errors
                        leaf tx-errors {
                            type yang:counter64;
                            units "packets";
                            description "The number of packets dropped while transmitting.";
                        }

                    } // container ethernet-tunnel

                } // container statistics

            } // list session

            ///nokia-state/state/router/l2tp/oper-ethernet-tunnel
            list oper-ethernet-tunnel {
                key "tunnel-group-name vc-id";
                description "Enter the oper-ethernet-tunnel list instance";

                ///nokia-state/state/router/l2tp/oper-ethernet-tunnel/tunnel-group-name
                leaf tunnel-group-name {
                    type types-sros:named-item-64 {
                        length "1..63";
                    }
                    description "The name of the tunnel group to which this ethernet tunnel belongs";
                }

                ///nokia-state/state/router/l2tp/oper-ethernet-tunnel/vc-id
                leaf vc-id {
                    type types-services:vc-id;
                    description "The virtual circuit identifier of the ethernet tunnel";
                }

                ///nokia-state/state/router/l2tp/oper-ethernet-tunnel/loc-conn-id
                leaf loc-conn-id {
                    type types-l2tp:connection-id;
                    description "The local connection-id of the ethernet tunnel.";
                }

                ///nokia-state/state/router/l2tp/oper-ethernet-tunnel/down-reason
                leaf down-reason {
                    type string {
                        length "0..80";
                    }
                    description "The reason for the ethernet tunnel not being established.";
                }

                ///nokia-state/state/router/l2tp/oper-ethernet-tunnel/reconnect-timeout
                leaf reconnect-timeout {
                    type types-l2tp:base-v3-reconnect-timeout;
                    description "The reconnect timeout for an ethernet tunnel.";
                }

                ///nokia-state/state/router/l2tp/oper-ethernet-tunnel/remaining-time
                leaf remaining-time {
                    type uint32;
                    units "seconds";
                    description "The remaining time before a reconnection attempt is made.";
                }

                ///nokia-state/state/router/l2tp/oper-ethernet-tunnel/sap-id
                leaf sap-id {
                    type types-sros:sap;
                    description "The SAP-id.";
                }

                ///nokia-state/state/router/l2tp/oper-ethernet-tunnel/sap-service-name
                leaf sap-service-name {
                    type types-sros:named-item-64;
                    description "The service of the SAP.";
                }

                ///nokia-state/state/router/l2tp/oper-ethernet-tunnel/control-conn-id
                leaf control-conn-id {
                    type types-l2tp:connection-id;
                    description "The control connection-id of the L2TP tunnel controling the ethernet tunnel.";
                }

                ///nokia-state/state/router/l2tp/oper-ethernet-tunnel/matches-config
                leaf matches-config {
                    type boolean;
                    description
                        "Indicates if the operational settings of the ethernet tunnel match the tunnel
                         group configuration.";
                }

            } // list oper-ethernet-tunnel

            ///nokia-state/state/router/l2tp/udp-peer
            list udp-peer {
                key "ip-address udp-port";
                description "Enter the udp-peer list instance";

                ///nokia-state/state/router/l2tp/udp-peer/ip-address
                leaf ip-address {
                    type types-sros:ip-address;
                    description "The peer address";
                }

                ///nokia-state/state/router/l2tp/udp-peer/udp-port
                leaf udp-port {
                    type inet:port-number;
                    description "The UDP port.";
                }

                ///nokia-state/state/router/l2tp/udp-peer/draining
                leaf draining {
                    type boolean;
                    description "Indicates if this peer is being drained.";
                }

                ///nokia-state/state/router/l2tp/udp-peer/reachability
                leaf reachability {
                    type types-l2tp:peer-reachability;
                    description "Indicates if this peer is deemed reachable or not.";
                }

                ///nokia-state/state/router/l2tp/udp-peer/unreachable-time
                leaf unreachable-time {
                    type yang:date-and-time;
                    description "The time when this peer was deemed unreachable for the last time.";
                }

                ///nokia-state/state/router/l2tp/udp-peer/remaining-time
                leaf remaining-time {
                    type uint32;
                    units "seconds";
                    description "The remaining time that the peer will remain in the selection-blacklist.";
                }

                ///nokia-state/state/router/l2tp/udp-peer/roles-capability
                leaf roles-capability {
                    type types-l2tp:peer-roles;
                    description "The roles the peer can take.";
                }

                ///nokia-state/state/router/l2tp/udp-peer/actual-roles
                leaf actual-roles {
                    type types-l2tp:peer-roles;
                    description "The roles the peer currently has.";
                }

                ///nokia-state/state/router/l2tp/udp-peer/statistics
                container statistics {
                    description "Enter the statistics context";

                    ///nokia-state/state/router/l2tp/udp-peer/statistics/tunnels
                    leaf tunnels {
                        type yang:gauge32;
                        description "The actual number of tunnels associated with this peer.";
                    }

                    ///nokia-state/state/router/l2tp/udp-peer/statistics/active-tunnels
                    leaf active-tunnels {
                        type yang:gauge32;
                        description "The actual number of tunnels associated with this peer that are currently established.";
                    }

                    ///nokia-state/state/router/l2tp/udp-peer/statistics/sessions
                    leaf sessions {
                        type yang:gauge32;
                        description "The actual number of sessions associated with this peer.";
                    }

                    ///nokia-state/state/router/l2tp/udp-peer/statistics/active-sessions
                    leaf active-sessions {
                        type yang:gauge32;
                        description "The actual number of sessions associated with this peer that are currently established.";
                    }

                    ///nokia-state/state/router/l2tp/udp-peer/statistics/rx-control-octets
                    leaf rx-control-octets {
                        type yang:counter64;
                        units "octets";
                        description
                            "The number of control channel octets received from this peer since the last re-initialization
                             of the local network management subsystem, or the last time the tunnel statistics were cleared.";
                    }

                    ///nokia-state/state/router/l2tp/udp-peer/statistics/rx-control-packets
                    leaf rx-control-packets {
                        type yang:counter32;
                        units "packets";
                        description
                            "The number of control channel packets received from this peer since the last re-initialization
                             of the local network management subsystem, or the last time the tunnel statistics were cleared.";
                    }

                    ///nokia-state/state/router/l2tp/udp-peer/statistics/errored-packets
                    leaf errored-packets {
                        type yang:counter32;
                        units "packets";
                        description
                            "The number of errored packets received from this peer since the last re-initialization
                             of the local network management subsystem, or the last time the tunnel statistics were cleared.";
                    }

                    ///nokia-state/state/router/l2tp/udp-peer/statistics/tx-control-octets
                    leaf tx-control-octets {
                        type yang:counter64;
                        units "octets";
                        description
                            "The number of control channel octets transmitted to this peer since the last re-initialization
                             of the local network management subsystem, or the last time the tunnel statistics were cleared.";
                    }

                    ///nokia-state/state/router/l2tp/udp-peer/statistics/tx-control-packets
                    leaf tx-control-packets {
                        type yang:counter32;
                        units "packets";
                        description
                            "The number of control channel packets transmitted to this peer since the last re-initialization
                             of the local network management subsystem, or the last time the tunnel statistics were cleared.";
                    }

                    ///nokia-state/state/router/l2tp/udp-peer/statistics/transmission-errors
                    leaf transmission-errors {
                        type yang:counter32;
                        units "packets";
                        description
                            "The number of packets transmission error for this peer since the last re-initialization
                             of the local network management subsystem, or the last time the tunnel statistics were cleared.";
                    }

                    ///nokia-state/state/router/l2tp/udp-peer/statistics/fsm-msg-accepted
                    leaf fsm-msg-accepted {
                        type yang:counter32;
                        units "packets";
                        description
                            "The number of Finite State Machine messages from this peer accepted since the last re-initialization
                             of the local network management subsystem, or the last time the tunnel statistics were cleared.";
                    }

                    ///nokia-state/state/router/l2tp/udp-peer/statistics/fsm-msg-duplicates
                    leaf fsm-msg-duplicates {
                        type yang:counter32;
                        units "packets";
                        description
                            "The number of duplicate Finite State Machine messages from this peer received since the last re-initialization
                             of the local network management subsystem, or the last time the tunnel statistics were cleared.";
                    }

                    ///nokia-state/state/router/l2tp/udp-peer/statistics/fsm-msg-out-of-rx-window
                    leaf fsm-msg-out-of-rx-window {
                        type yang:counter32;
                        units "packets";
                        description
                            "The number of Finite State Machine (FSM) messages that were received
                             out of the receive window from this peer since the last re-initialization of
                             the local network management subsystem, or the last time the tunnel statistics
                             were cleared.";
                    }

                    ///nokia-state/state/router/l2tp/udp-peer/statistics/last-cleared
                    leaf last-cleared {
                        type yang:date-and-time;
                        description "The time when the statistics were cleared for the last time.";
                    }

                    ///nokia-state/state/router/l2tp/udp-peer/statistics/protocol
                    list protocol {
                        key "type id";
                        description "Enter the protocol list instance";

                        ///nokia-state/state/router/l2tp/udp-peer/statistics/protocol/type
                        leaf type {
                            type types-l2tp:proto-stats-type;
                            description "The statistics type.";
                        }

                        ///nokia-state/state/router/l2tp/udp-peer/statistics/protocol/id
                        leaf id {
                            type uint32 {
                                range "0..69|4294967294|4294967295";
                            }
                            description "The counter id.";
                        }

                        ///nokia-state/state/router/l2tp/udp-peer/statistics/protocol/name
                        leaf name {
                            type types-sros:display-string;
                            description "The human-readable identifier of the statistic.";
                        }

                        ///nokia-state/state/router/l2tp/udp-peer/statistics/protocol/value
                        leaf value {
                            type yang:counter32;
                            description "The counter value";
                        }

                    } // list protocol

                } // container statistics

            } // list udp-peer

            ///nokia-state/state/router/l2tp/ip-peer
            list ip-peer {
                key "ip-address";
                description "Enter the ip-peer list instance";

                ///nokia-state/state/router/l2tp/ip-peer/ip-address
                leaf ip-address {
                    type types-sros:ip-address;
                    description "The peer address";
                }

                ///nokia-state/state/router/l2tp/ip-peer/draining
                leaf draining {
                    type boolean;
                    description "Indicates if this peer is being drained.";
                }

                ///nokia-state/state/router/l2tp/ip-peer/reachability
                leaf reachability {
                    type types-l2tp:peer-reachability;
                    description "Indicates if this peer is deemed reachable or not.";
                }

                ///nokia-state/state/router/l2tp/ip-peer/unreachable-time
                leaf unreachable-time {
                    type yang:date-and-time;
                    description "The time when this peer was deemed unreachable for the last time.";
                }

                ///nokia-state/state/router/l2tp/ip-peer/remaining-time
                leaf remaining-time {
                    type uint32;
                    units "seconds";
                    description "The remaining time that the peer will remain in the selection-blacklist.";
                }

                ///nokia-state/state/router/l2tp/ip-peer/roles-capability
                leaf roles-capability {
                    type types-l2tp:peer-roles;
                    description "The roles the peer can take.";
                }

                ///nokia-state/state/router/l2tp/ip-peer/actual-roles
                leaf actual-roles {
                    type types-l2tp:peer-roles;
                    description "The roles the peer currently has.";
                }

                ///nokia-state/state/router/l2tp/ip-peer/statistics
                container statistics {
                    description "Enter the statistics context";

                    ///nokia-state/state/router/l2tp/ip-peer/statistics/tunnels
                    leaf tunnels {
                        type yang:gauge32;
                        description "The actual number of tunnels associated with this peer.";
                    }

                    ///nokia-state/state/router/l2tp/ip-peer/statistics/active-tunnels
                    leaf active-tunnels {
                        type yang:gauge32;
                        description "The actual number of tunnels associated with this peer that are currently established.";
                    }

                    ///nokia-state/state/router/l2tp/ip-peer/statistics/sessions
                    leaf sessions {
                        type yang:gauge32;
                        description "The actual number of sessions associated with this peer.";
                    }

                    ///nokia-state/state/router/l2tp/ip-peer/statistics/active-sessions
                    leaf active-sessions {
                        type yang:gauge32;
                        description "The actual number of sessions associated with this peer that are currently established.";
                    }

                    ///nokia-state/state/router/l2tp/ip-peer/statistics/rx-control-octets
                    leaf rx-control-octets {
                        type yang:counter64;
                        units "octets";
                        description
                            "The number of control channel octets received from this peer since the last re-initialization
                             of the local network management subsystem, or the last time the tunnel statistics were cleared.";
                    }

                    ///nokia-state/state/router/l2tp/ip-peer/statistics/rx-control-packets
                    leaf rx-control-packets {
                        type yang:counter32;
                        units "packets";
                        description
                            "The number of control channel packets received from this peer since the last re-initialization
                             of the local network management subsystem, or the last time the tunnel statistics were cleared.";
                    }

                    ///nokia-state/state/router/l2tp/ip-peer/statistics/errored-packets
                    leaf errored-packets {
                        type yang:counter32;
                        units "packets";
                        description
                            "The number of errored packets received from this peer since the last re-initialization
                             of the local network management subsystem, or the last time the tunnel statistics were cleared.";
                    }

                    ///nokia-state/state/router/l2tp/ip-peer/statistics/tx-control-octets
                    leaf tx-control-octets {
                        type yang:counter64;
                        units "octets";
                        description
                            "The number of control channel octets transmitted to this peer since the last re-initialization
                             of the local network management subsystem, or the last time the tunnel statistics were cleared.";
                    }

                    ///nokia-state/state/router/l2tp/ip-peer/statistics/tx-control-packets
                    leaf tx-control-packets {
                        type yang:counter32;
                        units "packets";
                        description
                            "The number of control channel packets transmitted to this peer since the last re-initialization
                             of the local network management subsystem, or the last time the tunnel statistics were cleared.";
                    }

                    ///nokia-state/state/router/l2tp/ip-peer/statistics/transmission-errors
                    leaf transmission-errors {
                        type yang:counter32;
                        units "packets";
                        description
                            "The number of packets transmission error for this peer since the last re-initialization
                             of the local network management subsystem, or the last time the tunnel statistics were cleared.";
                    }

                    ///nokia-state/state/router/l2tp/ip-peer/statistics/fsm-msg-accepted
                    leaf fsm-msg-accepted {
                        type yang:counter32;
                        units "packets";
                        description
                            "The number of Finite State Machine messages from this peer accepted since the last re-initialization
                             of the local network management subsystem, or the last time the tunnel statistics were cleared.";
                    }

                    ///nokia-state/state/router/l2tp/ip-peer/statistics/fsm-msg-duplicates
                    leaf fsm-msg-duplicates {
                        type yang:counter32;
                        units "packets";
                        description
                            "The number of duplicate Finite State Machine messages from this peer received since the last re-initialization
                             of the local network management subsystem, or the last time the tunnel statistics were cleared.";
                    }

                    ///nokia-state/state/router/l2tp/ip-peer/statistics/fsm-msg-out-of-rx-window
                    leaf fsm-msg-out-of-rx-window {
                        type yang:counter32;
                        units "packets";
                        description
                            "The number of Finite State Machine (FSM) messages that were received
                             out of the receive window from this peer since the last re-initialization of
                             the local network management subsystem, or the last time the tunnel statistics
                             were cleared.";
                    }

                    ///nokia-state/state/router/l2tp/ip-peer/statistics/last-cleared
                    leaf last-cleared {
                        type yang:date-and-time;
                        description "The time when the statistics were cleared for the last time.";
                    }

                    ///nokia-state/state/router/l2tp/ip-peer/statistics/protocol
                    list protocol {
                        key "type id";
                        description "Enter the protocol list instance";

                        ///nokia-state/state/router/l2tp/ip-peer/statistics/protocol/type
                        leaf type {
                            type types-l2tp:proto-stats-type;
                            description "The statistics type.";
                        }

                        ///nokia-state/state/router/l2tp/ip-peer/statistics/protocol/id
                        leaf id {
                            type uint32 {
                                range "0..69|4294967294|4294967295";
                            }
                            description "The counter id.";
                        }

                        ///nokia-state/state/router/l2tp/ip-peer/statistics/protocol/name
                        leaf name {
                            type types-sros:display-string;
                            description "The human-readable identifier of the statistic.";
                        }

                        ///nokia-state/state/router/l2tp/ip-peer/statistics/protocol/value
                        leaf value {
                            type yang:counter32;
                            description "The counter value";
                        }

                    } // list protocol

                } // container statistics

            } // list ip-peer

            ///nokia-state/state/router/l2tp/vas-tunnel
            list vas-tunnel {
                key "tunnel-conn-id";
                description "Enter the vas-tunnel list instance";

                ///nokia-state/state/router/l2tp/vas-tunnel/tunnel-conn-id
                leaf tunnel-conn-id {
                    type types-l2tp:connection-id;
                    description "The connection-id of the VAS tunnel.";
                }

                ///nokia-state/state/router/l2tp/vas-tunnel/transport-type
                leaf transport-type {
                    type types-l2tp:transport-type;
                    description "The transport type used to carry L2TP messages.";
                }

                ///nokia-state/state/router/l2tp/vas-tunnel/local-address
                leaf local-address {
                    type types-sros:ip-address;
                    description "The local address";
                }

                ///nokia-state/state/router/l2tp/vas-tunnel/loc-udp-port
                leaf loc-udp-port {
                    type inet:port-number;
                    description "The local UDP port of this VAS tunnel.";
                }

                ///nokia-state/state/router/l2tp/vas-tunnel/remote-address
                leaf remote-address {
                    type types-sros:ip-address;
                    description "The remote address";
                }

                ///nokia-state/state/router/l2tp/vas-tunnel/rem-udp-port
                leaf rem-udp-port {
                    type inet:port-number;
                    description "The remote UDP port of this VAS tunnel.";
                }

                ///nokia-state/state/router/l2tp/vas-tunnel/base-router
                leaf base-router {
                    type types-sros:router-instance;
                    description "The virtual router instance used as the base of the VAS tunnel.";
                }

                ///nokia-state/state/router/l2tp/vas-tunnel/loc-tunnel-id
                leaf loc-tunnel-id {
                    type types-l2tp:tunnel-id;
                    description "The local tunnel-id.";
                }

                ///nokia-state/state/router/l2tp/vas-tunnel/rem-tunnel-id
                leaf rem-tunnel-id {
                    type types-l2tp:tunnel-id;
                    description "The remote tunnel-id.";
                }

                ///nokia-state/state/router/l2tp/vas-tunnel/rem-conn-id
                leaf rem-conn-id {
                    type types-l2tp:connection-id;
                    description "The remote connection-id of the VAS tunnel.";
                }

                ///nokia-state/state/router/l2tp/vas-tunnel/vas-session
                list vas-session {
                    key "session-conn-id";
                    description "Enter the vas-session list instance";

                    ///nokia-state/state/router/l2tp/vas-tunnel/vas-session/session-conn-id
                    leaf session-conn-id {
                        type types-l2tp:connection-id;
                        description "The connection-id of the VAS session.";
                    }

                    ///nokia-state/state/router/l2tp/vas-tunnel/vas-session/loc-session-id
                    leaf loc-session-id {
                        type types-l2tp:session-id;
                        description "The local session-id.";
                    }

                    ///nokia-state/state/router/l2tp/vas-tunnel/vas-session/rem-session-id
                    leaf rem-session-id {
                        type types-l2tp:session-id;
                        description "The remote session-id.";
                    }

                    ///nokia-state/state/router/l2tp/vas-tunnel/vas-session/rem-conn-id
                    leaf rem-conn-id {
                        type types-l2tp:connection-id;
                        description "The remote connection-id of the VAS session.";
                    }

                } // list vas-session

            } // list vas-tunnel

            ///nokia-state/state/router/l2tp/mlppp-bundle
            list mlppp-bundle {
                key "bundle-index";
                description "Enter the mlppp-bundle list instance";

                ///nokia-state/state/router/l2tp/mlppp-bundle/bundle-index
                leaf bundle-index {
                    type uint32;
                    description "The bundle index";
                }

                ///nokia-state/state/router/l2tp/mlppp-bundle/service-name
                leaf service-name {
                    type types-sros:named-item-64;
                    description "The service to which this MLPPP bundle belongs.";
                }

                ///nokia-state/state/router/l2tp/mlppp-bundle/forwarding-tunnel-id
                leaf forwarding-tunnel-id {
                    type types-l2tp:tunnel-id;
                    description
                        "The id of the LTS (L2TP Tunnel Stitching) tunnel if this bundle
                         is associated with PPP sessions that are stiched to another L2TP tunnel.";
                }

                ///nokia-state/state/router/l2tp/mlppp-bundle/user-name
                leaf user-name {
                    type types-sros:named-item;
                    description
                        "The user name of the subscriber associated with this MLPPP bundle or another
                         string used to identify that subscriber.";
                }

                ///nokia-state/state/router/l2tp/mlppp-bundle/local-endpoint
                container local-endpoint {
                    description "Enter the local-endpoint context";

                    ///nokia-state/state/router/l2tp/mlppp-bundle/local-endpoint/endpoint-class
                    leaf endpoint-class {
                        type types-ppp:mlppp-endpoint-class;
                        description "Endpoint class";
                    }

                    ///nokia-state/state/router/l2tp/mlppp-bundle/local-endpoint/endpoint-id
                    leaf endpoint-id {
                        type binary {
                            length "1..20";
                        }
                        description "Endpoint identifier";
                    }

                    ///nokia-state/state/router/l2tp/mlppp-bundle/local-endpoint/description
                    leaf description {
                        type types-sros:description;
                        description "The endpoint description.";
                    }

                } // container local-endpoint

                ///nokia-state/state/router/l2tp/mlppp-bundle/remote-endpoint
                container remote-endpoint {
                    description "Enter the remote-endpoint context";

                    ///nokia-state/state/router/l2tp/mlppp-bundle/remote-endpoint/endpoint-class
                    leaf endpoint-class {
                        type types-ppp:mlppp-endpoint-class;
                        description "Endpoint class";
                    }

                    ///nokia-state/state/router/l2tp/mlppp-bundle/remote-endpoint/endpoint-id
                    leaf endpoint-id {
                        type binary {
                            length "1..20";
                        }
                        description "Endpoint identifier";
                    }

                    ///nokia-state/state/router/l2tp/mlppp-bundle/remote-endpoint/description
                    leaf description {
                        type types-sros:description;
                        description "The endpoint description.";
                    }

                } // container remote-endpoint

                ///nokia-state/state/router/l2tp/mlppp-bundle/link
                list link {
                    key "session-conn-id";
                    description "Enter the link list instance";

                    ///nokia-state/state/router/l2tp/mlppp-bundle/link/session-conn-id
                    leaf session-conn-id {
                        type types-l2tp:connection-id;
                        description "The local connection-id of the session.";
                    }

                    ///nokia-state/state/router/l2tp/mlppp-bundle/link/oper-state
                    leaf oper-state {
                        type types-l2tp:session-oper-state;
                        description "The operational state of the session.";
                    }

                } // list link

            } // list mlppp-bundle

        } // container l2tp

    } // grouping state-router-l2tp

}
