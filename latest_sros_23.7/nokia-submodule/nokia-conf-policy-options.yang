submodule nokia-conf-policy-options {

    yang-version "1.1";

    belongs-to nokia-conf { prefix "conf"; }

    import nokia-sros-yang-extensions     { prefix "sros-ext"; }
    import nokia-types-bgp                { prefix "types-bgp"; }
    import nokia-types-policy             { prefix "types-policy"; }
    import nokia-types-sros               { prefix "types-sros"; }

    include nokia-conf-groups;

    sros-ext:sros-major-release "rel23";
    organization "Nokia";
    contact
        "Nokia SR OS Support
         Web: <http://www.nokia.com>";
    description
        "Nokia YANG Data model to configure policy-options on SR OS based routers.

         Copyright 2016 Nokia. All rights reserved. Reproduction of this document
         is authorized on the condition that the foregoing copyright notice is included.

         This nokia-conf-policy-options YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-07-14";

    grouping conf-policy-options {
        container policy-options {
            description "Enter the policy-options context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list as-path {
                key "name";
                description "Enter the as-path list instance";

                leaf name {
                    type types-sros:named-item;
                    description "AS path name";
                }

                leaf expression {
                    type types-sros:policy-as-path-regexp;
                    description "Regular expression string";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list as-path

            list as-path-group {
                key "name";
                sros-ext:shared-model-management {
                    sros-ext:openconfig false;
                }
                description "Enter the as-path-group list instance";

                leaf name {
                    type types-sros:named-item;
                    description "AS path group name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list entry {
                    key "entry";
                    description "Enter the entry list instance";

                    leaf entry {
                        type uint32 {
                            range "1..128";
                        }
                        description "AS path entry ID";
                    }

                    leaf expression {
                        type types-sros:policy-as-path-regexp;
                        mandatory true;
                        description "Regular expression string";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list entry

            } // list as-path-group

            list damping {
                key "name";
                description "Enter the damping list instance";

                leaf name {
                    type types-sros:named-item;
                    description "Damping profile name";
                }

                leaf half-life {
                    type uint32 {
                        range "1..45";
                    }
                    units "minutes";
                    description "Time after the FOM value is halved";
                }

                leaf max-suppress {
                    type uint32 {
                        range "1..720";
                    }
                    units "minutes";
                    description "Maximum time for a route to remain suppressed";
                }

                leaf reuse {
                    type uint32 {
                        range "1..20000";
                    }
                    description "Value below which a suppressed route can be used again";
                }

                leaf suppress {
                    type uint32 {
                        range "1..20000";
                    }
                    description "Value above which a route is suppressed";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list damping

            container global-variables {
                description "Enter the global-variables context";

                list name {
                    key "variable-name";
                    max-elements 1000;
                    description "Enter the name list instance";

                    leaf variable-name {
                        type types-policy:policy-var-name;
                        description "Global variable name used to reference policy functions";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice variable-type {
                        mandatory true;
                        case value {

                            leaf value {
                                type types-sros:named-item;
                                description "Policy variable value";
                            }

                        }
                        case number {

                            leaf number {
                                type uint64 {
                                    range "0..4294967295";
                                }
                                description "Numerical value of the policy variable";
                            }

                        }
                        case address {

                            leaf address {
                                type types-sros:ip-address;
                                description "IP address of the policy variable";
                            }

                        }
                        case decimal {

                            leaf decimal {
                                type decimal64 {
                                    range "0.000..4294967295.000";
                                    fraction-digits 3;
                                }
                                description "Attribute decimal to which variable name is resolved";
                            }

                        }
                        case prefix {

                            leaf prefix {
                                type types-sros:ip-prefix;
                                description "Prefix value associated with the variable name";
                            }

                        }
                    }
                } // list name

            } // container global-variables

            list community {
                key "name";
                description "Enter the community list instance";

                leaf name {
                    type types-sros:policy-community-name;
                    description "Community name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list member {
                    key "member";
                    description "Add a list entry for member";

                    leaf member {
                        type types-sros:member-community;
                        description "Community member value";
                    }

                } // list member

                container expression {
                    presence "Enable the expression context";
                    description "Enable the expression context";

                    leaf expr {
                        type types-sros:expression-community;
                        mandatory true;
                        description "Community expression value";
                    }

                    leaf exact {
                        type boolean;
                        default "false";
                        description "Match exactly for the specified expression";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container expression

            } // list community

            list prefix-list {
                key "name";
                description "Enter the prefix-list list instance";

                leaf name {
                    type types-sros:named-item-64;
                    description "Prefix list name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list prefix {
                    key "ip-prefix type";
                    description "Enter the prefix list instance";

                    leaf ip-prefix {
                        type types-sros:ip-prefix;
                        description "IP prefix associated with the prefix length";
                    }

                    leaf type {
                        type enumeration {
                            enum exact                          { value 1; }
                            enum longer                         { value 2; }
                            enum through                        { value 3; }
                            enum range                          { value 4; }
                            enum to                             { value 5; }
                            enum address-mask                   { value 6; }
                        }
                        description "Prefix list match type";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice length {
                        case range {

                            leaf start-length {
                                type uint32 {
                                    range "0..128";
                                }
                                description "Start in the prefix range length";
                            }

                            leaf end-length {
                                type uint32 {
                                    range "0..128";
                                }
                                description "Prefix range end length";
                            }

                        }
                        case through {

                            leaf through-length {
                                type uint32 {
                                    range "0..128";
                                }
                                description "Prefix through length";
                            }

                        }
                        case to {

                            list to-prefix {
                                when "../type = 'to'" {
                                    description "Active only when 'type' is to";
                                }
                                key "ip-prefix";
                                description "Add a list entry for to-prefix";

                                leaf ip-prefix {
                                    type types-sros:ip-prefix;
                                    description "IP prefix for \"to\" match type";
                                }

                            } // list to-prefix

                        }
                        case address-mask {

                            list mask-pattern {
                                when "../type = 'address-mask'" {
                                    description "Active only when 'type' is address-mask";
                                }
                                key "address";
                                description "Add a list entry for mask-pattern";

                                leaf address {
                                    type types-sros:ip-address;
                                    description "Address mask for matching routes to the prefix entry";
                                }

                            } // list mask-pattern

                        }
                    }
                } // list prefix

            } // list prefix-list

            list route-distinguisher-list {
                key "name";
                description "Enter the route-distinguisher-list list instance";

                leaf name {
                    type types-sros:named-item-64 {
                        pattern "[^@]*" {
                            error-message "name cannot contain @";
                        }
                    }
                    description "Route distinguisher list name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list rd-entry {
                    key "rd";
                    max-elements 128;
                    description "Add a list entry for rd-entry";

                    leaf rd {
                        type string {
                            length "3..28";
                            pattern "(((((((([0-9]|[1-9][0-9]|1[0-9][0-9]|2[0-4][0-9]|25[0-5])\\.){3}([0-9]|[1-9][0-9]|1[0-9][0-9]|2[0-4][0-9]|25[0-5]))))/((\\d|[0-2]\\d|3[0-2])))|([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])):(([0-9]|[1-9][0-9]{1,3}|[1-5][0-9]{1,4}|6[0-4][0-9]{1,3}|65[0-4][0-9][0-9]|655[0-2][0-9]|6553[0-5])|\\*))|((([1-9]|[1-9][0-9]{1,3}|[1-5][0-9]{1,4}|6[0-4][0-9]{1,3}|65[0-4][0-9][0-9]|655[0-2][0-9]|6553[0-5])):(([0-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])|\\*))" {
                                error-message "RD not valid";
                            }
                        }
                        description "Route distinguisher";
                    }

                } // list rd-entry

            } // list route-distinguisher-list

            list policy-statement {
                key "name";
                max-elements 65535;
                sros-ext:shared-model-management {
                    sros-ext:openconfig false;
                }
                description "Enter the policy-statement list instance";

                leaf name {
                    type types-sros:named-item-64;
                    description "Route policy statement name";
                }

                leaf description {
                    type types-sros:description;
                    description "Text description";
                }

                leaf entry-type {
                    type enumeration {
                        enum numbered                       { value 1; }
                        enum named                          { value 2; }
                    }
                    default "numbered";
                    description "The entry type for a route policy entry";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list entry {
                    when "../entry-type = 'numbered'" {
                        description "Active only when 'entry-type' is numbered";
                    }
                    key "entry-id";
                    description "Enter the entry list instance";

                    leaf entry-id {
                        type uint32 {
                            range "1..4294967295";
                        }
                        description "Entry ID for a route policy entry";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container conditional-expression {
                        presence "Enable the conditional-expression context";
                        description "Enable the conditional-expression context";

                        leaf route-exists {
                            type string {
                                length "1..255";
                                pattern "\\s*\\[.+\\]\\s*(all|none)?" {
                                    error-message " enter valid prefix between [ ] and optionally add all or none";
                                }
                            }
                            description "Conditional expression to test route existence";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container conditional-expression

                    container from {
                        presence "Enable the from context";
                        description "Enable the from context";

                        leaf level {
                            type int32 {
                                range "1..2";
                            }
                            description "IS-IS route level as a match criterion";
                        }

                        leaf-list prefix-list {
                            type union {
                                type types-policy:param-midstring-64;
                                type string;
                            }
                            max-elements 28;
                            ordered-by user;
                            description "Prefix list as match criterion";
                        }

                        leaf area {
                            type types-sros:ipv4-address;
                            description "OSPF area as a match criterion";
                        }

                        leaf aggregate-contributor {
                            type boolean;
                            default "false";
                            description "Enable aggregate route match criterion";
                        }

                        leaf evpn-type {
                            type enumeration {
                                enum ethernet-auto-discovery        { value 1; }
                                enum mac-ip-advertisement           { value 2; }
                                enum inclusive-multicast            { value 3; }
                                enum ethernet-segment               { value 4; }
                                enum ip-prefix                      { value 5; }
                                enum selective-multicast            { value 6; }
                                enum multicast-join-sync            { value 7; }
                                enum multicast-leave-sync           { value 8; }
                                enum selective-pmsi-auto-discovery  { value 10; }
                            }
                            description "EVPN type as a match criterion for the entry";
                        }

                        leaf external {
                            type boolean;
                            default "false";
                            description "Specify the external IS-IS route as a match criterion";
                        }

                        leaf-list family {
                            type types-bgp:ip-family-identifier;
                            max-elements 20;
                            description "Address family as the match condition";
                        }

                        leaf group-address {
                            type union {
                                type types-policy:param-midstring;
                                type string;
                            }
                            description "Prefix list of multicast group addresses for mathcing";
                        }

                        leaf host-ip {
                            type union {
                                type types-policy:param-midstring;
                                type string;
                            }
                            description "Prefix list of IGMP host IP addresses for matching";
                        }

                        leaf-list interface {
                            type union {
                                type types-sros:named-item;
                                type types-sros:interface-name;
                                type types-sros:interface-name;
                                type types-sros:interface-name;
                            }
                            max-elements 1;
                            ordered-by user;
                            description "Interface name as match criterion";
                        }

                        leaf mvpn-type {
                            type enumeration {
                                enum intra-as-ipmsi-auto-discovery  { value 1; }
                                enum inter-as-ipmsi-auto-discovery  { value 2; }
                                enum s-pmsi-auto-discovery          { value 3; }
                                enum intra-as-segment-leaf-auto-discovery { value 4; }
                                enum source-active-auto-discovery   { value 5; }
                                enum shared-tree-join               { value 6; }
                                enum source-tree-join               { value 7; }
                            }
                            description "MVPN type as a match criterion for the entry";
                        }

                        leaf origin {
                            type enumeration {
                                enum igp                            { value 2; }
                                enum egp                            { value 3; }
                                enum incomplete                     { value 4; }
                                enum any                            { value 5; }
                                enum aaa                            { value 6; }
                                enum dynamic                        { value 7; }
                                enum static                         { value 8; }
                                enum bonding                        { value 9; }
                                enum pfcp                           { value 10; }
                            }
                            description "Route origin match criteria";
                        }

                        leaf origin-validation-state {
                            type enumeration {
                                enum valid                          { value 1; }
                                enum not-found                      { value 2; }
                                enum invalid                        { value 3; }
                            }
                            description "Origin validation state used for match criteria";
                        }

                        leaf ospf-type {
                            type int32 {
                                range "1..2";
                            }
                            description "OSPF type metric applied to unmatching route entries";
                        }

                        leaf path-type {
                            type enumeration {
                                enum ibgp                           { value 2; }
                                enum ebgp                           { value 3; }
                            }
                            description "Path type as a match criterion";
                        }

                        leaf policy {
                            type union {
                                type string {
                                    length "1..255";
                                    pattern ".*[\\[].*" {
                                        error-message "expression not valid.";
                                    }
                                }
                                type string;
                            }
                            description "Policy statement as a match criterion";
                        }

                        leaf route-distinguisher-list {
                            type union {
                                type types-policy:param-midstring-64;
                                type string;
                            }
                            description "Route distinguisher list as a match criterion";
                        }

                        leaf state {
                            type enumeration {
                                enum srrp-master                    { value 2; }
                                enum srrp-non-master                { value 3; }
                                enum ipsec-master-with-peer         { value 6; }
                                enum ipsec-master-without-peer      { value 7; }
                                enum ipsec-non-master               { value 8; }
                                enum fsg-active                     { value 10; }
                                enum fsg-standby                    { value 11; }
                            }
                            description "State used as a match criterion";
                        }

                        leaf tag {
                            type union {
                                type int64 {
                                    range "1..4294967295";
                                }
                                type enumeration {
                                    enum no-tag                         { value 0; }
                                }
                            }
                            description "Route tag used as a match criterion";
                        }

                        leaf color {
                            type int64 {
                                range "0..4294967295";
                            }
                            description "Color ID as a match criterion";
                        }

                        leaf distinguisher {
                            type int64 {
                                range "0..4294967295";
                            }
                            description "SR policy distinguisher as a match criterion";
                        }

                        leaf endpoint {
                            type types-sros:ip-address;
                            description "SR policy endpoint address as a match criterion";
                        }

                        leaf srv6-sid-prefix {
                            type union {
                                type types-policy:policy-var-name;
                                type types-sros:ipv6-unicast-prefix;
                            }
                            description "SRv6 SID value as the match criterion for the BGP route";
                        }

                        leaf srv6-tlv {
                            type enumeration {
                                enum present                        { value 1; }
                                enum not-present                    { value 2; }
                            }
                            description "SRv6 TLV presence as match criterion for BGP route";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container neighbor {
                            description "Enter the neighbor context";

                            choice neighbor {
                                case ip-address {

                                    leaf ip-address {
                                        type union {
                                            type types-sros:ip-address;
                                            type types-sros:ip-address-with-zone;
                                        }
                                        description "IP address to match the neighbor";
                                    }

                                }
                                case prefix-list {

                                    leaf prefix-list {
                                        type union {
                                            type types-policy:param-midstring;
                                            type string;
                                        }
                                        description "Name to match the neighbor prefix list";
                                    }

                                }
                            }
                        } // container neighbor

                        container interface-subnets {
                            description "Enter the interface-subnets context";

                            leaf service {
                                type string;
                                default "Base";
                                description "Service ID of the interface subnets";
                            }

                            leaf-list ip-int-name {
                                type types-sros:interface-name;
                                max-elements 10;
                                ordered-by user;
                                description "Interface name as the match criterion";
                            }

                        } // container interface-subnets

                        container as-path {
                            description "Enter the as-path context";

                            choice as-path {
                                case name {

                                    leaf name {
                                        type union {
                                            type types-policy:param-midstring;
                                            type string;
                                        }
                                        description "AS path name to match";
                                    }

                                }
                                case group {

                                    leaf group {
                                        type union {
                                            type types-policy:param-midstring;
                                            type string;
                                        }
                                        description "AS path group as a match criterion";
                                    }

                                }
                            }
                            container length {
                                description "Enter the length context";

                                leaf value {
                                    type types-policy:value-255-param-name;
                                    description "AS numbers in the AS path that match on the BGP route";
                                }

                                leaf qualifier {
                                    type types-policy:policy-qualifier;
                                    default "equal";
                                    description "Higher or lower values to be accepted as match criteria";
                                }

                                leaf unique {
                                    type boolean;
                                    default "false";
                                    description "Use unique AS numbers as matching criteria";
                                }

                            } // container length

                        } // container as-path

                        container cluster-id {
                            description "Enter the cluster-id context";

                            choice cluster-id {
                                case ip-address {

                                    leaf-list ip-address {
                                        type types-sros:ipv4-prefix-with-host-bits;
                                        max-elements 5;
                                        ordered-by user;
                                        description "Cluster list attribute IP addresses for route matching";
                                    }

                                }
                                case none-cluster-list {

                                    leaf none-cluster-list {
                                        type boolean;
                                        default "false";
                                        description "Specify matching BGP routes without a cluster ID";
                                    }

                                }
                            }
                        } // container cluster-id

                        container community {
                            description "Enter the community context";

                            choice community {
                                case name {

                                    leaf name {
                                        type union {
                                            type types-policy:param-midstring-64 {
                                                pattern "[^\\]\\[]+" {
                                                    error-message "String must not contain square brackets ([]).";
                                                }
                                            }
                                            type string;
                                        }
                                        description "Community list name";
                                    }

                                }
                                case expression {

                                    leaf expression {
                                        type string {
                                            length "1..900";
                                        }
                                        description "Community expression name as a match criterion";
                                    }

                                }
                            }
                            container count {
                                description "Enter the count context";

                                leaf value {
                                    type types-policy:value-param-1024-name;
                                    description "Number of BGP communities to match the BGP route";
                                }

                                leaf qualifier {
                                    type types-policy:policy-qualifier;
                                    default "equal";
                                    description "Higher or lower values to be accepted as match criteria";
                                }

                                leaf type {
                                    type enumeration {
                                        enum standard                       { value 2; }
                                        enum extended                       { value 3; }
                                        enum large                          { value 4; }
                                    }
                                    description "Community count to match the community count criteria";
                                }

                            } // container count

                        } // container community

                        container flowspec {
                            description "Enter the flowspec context";

                            leaf dest {
                                type union {
                                    type types-policy:param-midstring;
                                    type string;
                                }
                                description "BGP FlowSpec route matches per destination IP prefix";
                            }

                            leaf source {
                                type union {
                                    type types-policy:param-midstring;
                                    type string;
                                }
                                description "BGP FlowSpec route matches per the source IP prefix";
                            }

                        } // container flowspec

                        container local-preference {
                            description "Enter the local-preference context";

                            leaf value {
                                type types-policy:value-param-name-metric;
                                description "BGP routes per local preference value or variable name";
                            }

                            leaf qualifier {
                                type types-policy:policy-qualifier;
                                default "equal";
                                description "Higher or lower values to be accepted as match criteria";
                            }

                        } // container local-preference

                        container metric {
                            description "Enter the metric context";

                            leaf value {
                                type types-policy:value-param-name-metric;
                                description "Local preference value or variable name";
                            }

                            leaf qualifier {
                                type types-policy:policy-qualifier;
                                default "equal";
                                description "Higher or lower values to be accepted as match criteria";
                            }

                        } // container metric

                        container next-hop {
                            description "Enter the next-hop context";

                            choice next-hop {
                                case ip-address {

                                    leaf ip-address {
                                        type types-sros:ip-unicast-address;
                                        description "IP address of the next hop to match";
                                    }

                                }
                                case prefix-list {

                                    leaf prefix-list {
                                        type union {
                                            type types-policy:param-midstring;
                                            type string;
                                        }
                                        description "Name of a next hop prefix list to match";
                                    }

                                }
                            }
                        } // container next-hop

                        container protocol {
                            description "Enter the protocol context";

                            leaf-list name {
                                type enumeration {
                                    enum direct                         { value 2; }
                                    enum static                         { value 3; }
                                    enum bgp                            { value 4; }
                                    enum isis                           { value 5; }
                                    enum ospf                           { value 6; }
                                    enum rip                            { value 7; }
                                    enum aggregate                      { value 8; }
                                    enum bgp-vpn                        { value 9; }
                                    enum igmp                           { value 10; }
                                    enum pim                            { value 11; }
                                    enum ospf3                          { value 12; }
                                    enum ldp                            { value 13; }
                                    enum sub-mgmt                       { value 14; }
                                    enum mld                            { value 15; }
                                    enum managed                        { value 16; }
                                    enum vpn-leak                       { value 18; }
                                    enum nat                            { value 21; }
                                    enum periodic                       { value 22; }
                                    enum ipsec                          { value 23; }
                                    enum dhcpv6-pd                      { value 25; }
                                    enum dhcpv6-na                      { value 26; }
                                    enum dhcpv6-ta                      { value 27; }
                                    enum dhcpv6-pd-excl                 { value 28; }
                                    enum ripng                          { value 29; }
                                    enum bgp-label                      { value 31; }
                                    enum direct-interface               { value 32; }
                                    enum arp-nd                         { value 33; }
                                    enum rib-api                        { value 34; }
                                    enum dhcp-client                    { value 36; }
                                    enum evpn-ifl                       { value 37; }
                                    enum srv6                           { value 39; }
                                    enum video                          { value 40; }
                                }
                                max-elements 5;
                                description "List of protocol names as the match criterion";
                            }

                            leaf instance {
                                type union {
                                    type enumeration {
                                        enum all                            { value -1; }
                                    }
                                    type uint32 {
                                        range "0..127";
                                    }
                                }
                                default "0";
                                description "Instance for protocol IS-IS, OSPF, or OSPFv3 to match";
                            }

                        } // container protocol

                        container source-address {
                            description "Enter the source-address context";

                            choice source-address {
                                case ip-address {

                                    leaf ip-address {
                                        type types-sros:ip-address;
                                        description "Source IP address to match";
                                    }

                                }
                                case prefix-list {

                                    leaf prefix-list {
                                        type union {
                                            type types-policy:param-midstring;
                                            type string;
                                        }
                                        description "Name of a source address prefix list to match";
                                    }

                                }
                            }
                        } // container source-address

                        container policy-variables {
                            description "Enter the policy-variables context";

                            list name {
                                key "variable-name";
                                max-elements 10;
                                description "Enter the name list instance";

                                leaf variable-name {
                                    type types-policy:policy-var-name;
                                    description "Global variable name used to reference policy functions";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                choice variable-type {
                                    mandatory true;
                                    case value {

                                        leaf value {
                                            type types-sros:named-item;
                                            description "Policy variable value";
                                        }

                                    }
                                    case number {

                                        leaf number {
                                            type uint64 {
                                                range "0..4294967295";
                                            }
                                            description "Numerical value of the policy variable";
                                        }

                                    }
                                    case address {

                                        leaf address {
                                            type types-sros:ip-address;
                                            description "IP address of the policy variable";
                                        }

                                    }
                                    case decimal {

                                        leaf decimal {
                                            type decimal64 {
                                                range "0.000..4294967295.000";
                                                fraction-digits 3;
                                            }
                                            description "Attribute decimal to which variable name is resolved";
                                        }

                                    }
                                    case prefix {

                                        leaf prefix {
                                            type types-sros:ip-prefix;
                                            description "Prefix value associated with the variable name";
                                        }

                                    }
                                }
                            } // list name

                        } // container policy-variables

                    } // container from

                    container to {
                        presence "Enable the to context";
                        description "Enable the to context";

                        leaf level {
                            type int32 {
                                range "1..2";
                            }
                            description "IS-IS route level as a match criterion";
                        }

                        leaf-list prefix-list {
                            type union {
                                type types-policy:param-midstring-64;
                                type string;
                            }
                            max-elements 28;
                            ordered-by user;
                            description "Prefix list as match criterion";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container neighbor {
                            description "Enter the neighbor context";

                            choice neighbor {
                                case ip-address {

                                    leaf ip-address {
                                        type union {
                                            type types-sros:ip-address;
                                            type types-sros:ip-address-with-zone;
                                        }
                                        description "IP address to match the neighbor";
                                    }

                                }
                                case prefix-list {

                                    leaf prefix-list {
                                        type union {
                                            type types-policy:param-midstring;
                                            type string;
                                        }
                                        description "Name to match the neighbor prefix list";
                                    }

                                }
                            }
                        } // container neighbor

                        container protocol {
                            description "Enter the protocol context";

                            leaf-list name {
                                type enumeration {
                                    enum bgp                            { value 4; }
                                    enum isis                           { value 5; }
                                    enum ospf                           { value 6; }
                                    enum rip                            { value 7; }
                                    enum bgp-vpn                        { value 9; }
                                    enum ospf3                          { value 12; }
                                    enum ldp                            { value 13; }
                                    enum vpn-leak                       { value 18; }
                                    enum ripng                          { value 29; }
                                    enum bgp-label                      { value 31; }
                                    enum evpn-ifl                       { value 37; }
                                }
                                max-elements 2;
                                description "Protocol name to match";
                            }

                            leaf instance {
                                type union {
                                    type enumeration {
                                        enum all                            { value -1; }
                                    }
                                    type uint32 {
                                        range "0..127";
                                    }
                                }
                                default "0";
                                description "Instance for the IS-IS, OSPF, or OSPF3 protocol";
                            }

                        } // container protocol

                    } // container to

                    container action {
                        presence "Enable the action context";
                        description "Enable the action context";

                        leaf action-type {
                            type enumeration {
                                enum accept                         { value 1; }
                                enum reject                         { value 2; }
                                enum next-entry                     { value 3; }
                                enum next-policy                    { value 4; }
                            }
                            mandatory true;
                            description "Action type for routes matching the route policy entry";
                        }

                        leaf add-paths-send-limit {
                            type union {
                                type int32 {
                                    range "1..16";
                                }
                                type enumeration {
                                    enum multipaths                     { value -1; }
                                }
                            }
                            description "BGP Add-Paths send limit applied for routes";
                        }

                        leaf admin-tag-policy {
                            type union {
                                type types-policy:param-midstring-64;
                                type string;
                            }
                            description "Administrative tag policy name";
                        }

                        leaf advertise-label {
                            type enumeration {
                                enum per-prefix                     { value 1; }
                                enum pop                            { value 2; }
                                enum pop-and-forward                { value 3; }
                            }
                            description "Label allocation for matched BGP routes";
                        }

                        leaf bgp-high-priority {
                            type boolean;
                            default "false";
                            description "Tag routes as high priority for fast table updates";
                        }

                        leaf bgp-leak {
                            type boolean;
                            default "false";
                            description "Allow leaking for BGP routes";
                        }

                        leaf create-mpls-tunnel {
                            type boolean;
                            default "false";
                            description "Create an MPLS tunnel";
                        }

                        leaf create-udp-tunnel {
                            type boolean;
                            default "false";
                            description "Create an MPLS-over-UDP tunnel";
                        }

                        leaf damping {
                            type union {
                                type enumeration {
                                    enum none                           { value 0; }
                                }
                                type types-policy:param-midstring;
                                type string;
                            }
                            description "Damping profile used for routes";
                        }

                        leaf dest-class {
                            type types-sros:class-index;
                            description "Default destination class for the policy statement";
                        }

                        leaf egress-statistics {
                            type boolean;
                            default "false";
                            description "Enable egress statistics for BGP-LU routes";
                        }

                        leaf ingress-statistics {
                            type boolean;
                            default "false";
                            description "Enable ingress statistics for BGP-LU routes";
                        }

                        leaf flex-algo {
                            type types-policy:value-param-name-flex-algo;
                            description "Flexible algorithm for BGP next-hop autobind operation";
                        }

                        leaf install-backup-path {
                            type boolean;
                            default "false";
                            description "Install a preprogrammed backup path for the prefix";
                        }

                        leaf local-preference {
                            type types-policy:value-param-name-metric;
                            description "BGP local preference for routes not matching any entry";
                        }

                        leaf nat-policy {
                            type union {
                                type types-policy:param-midstring;
                                type string;
                            }
                            description "BGP-VPN imported route and a NAT policy association";
                        }

                        leaf next-hop {
                            type union {
                                type enumeration {
                                    enum peer-address                   { value -2; }
                                    enum self                           { value -1; }
                                }
                                type types-sros:ip-address;
                                type string {
                                    length "1..32";
                                    pattern "@.+@" {
                                        error-message "String must start and end with an at-sign (@)";
                                    }
                                }
                            }
                            description "Next-hop IP address applied to routes";
                        }

                        leaf origin {
                            type union {
                                type enumeration {
                                    enum igp                            { value 2; }
                                    enum egp                            { value 3; }
                                    enum incomplete                     { value 4; }
                                }
                                type string {
                                    length "1..32";
                                    pattern "@.+@" {
                                        error-message "String must start and end with an at-sign (@)";
                                    }
                                }
                            }
                            description "BGP origin for routes that are exported into BGP";
                        }

                        leaf origin-validation-state {
                            type union {
                                type enumeration {
                                    enum valid                          { value 1; }
                                    enum not-found                      { value 2; }
                                    enum invalid                        { value 3; }
                                }
                                type string {
                                    length "1..32";
                                    pattern "@.+@" {
                                        error-message "String must start and end with an at-sign (@)";
                                    }
                                }
                            }
                            description "Origin validation state for routes";
                        }

                        leaf prefer-transport-frr {
                            type boolean;
                            default "false";
                            description "Enable transport FRR preference";
                        }

                        leaf preference {
                            type union {
                                type uint32 {
                                    range "1..255";
                                }
                                type string {
                                    length "1..32";
                                    pattern "@.+@" {
                                        error-message "String must start and end with an at-sign (@)";
                                    }
                                }
                            }
                            description "Route preference applied to routes";
                        }

                        leaf resolve-static {
                            type boolean;
                            default "false";
                            description "Resolve next hop of a static route for the BGP next hop";
                        }

                        leaf source-class {
                            type types-sros:class-index;
                            description "Default source class for the policy statement";
                        }

                        leaf sticky-ecmp {
                            type boolean;
                            default "false";
                            description "Specify the sticky ECMP flag for BGP ECMP routes";
                        }

                        leaf tag {
                            type union {
                                type uint32 {
                                    range "1..4294967295";
                                }
                                type string {
                                    length "1..32";
                                    pattern "@.+@" {
                                        error-message "String must start and end with an at-sign (@)";
                                    }
                                }
                            }
                            description "OSPF RIP or IS-IS tag applied to routes";
                        }

                        leaf type {
                            type union {
                                type int32 {
                                    range "1..2";
                                }
                                type string {
                                    length "1..32";
                                    pattern "@.+@" {
                                        error-message "String must start and end with an at-sign (@)";
                                    }
                                }
                            }
                            description "OSPF metric type applied to routes";
                        }

                        leaf route-table-install {
                            type boolean;
                            default "true";
                            description "Allow BGP route installation in the route table";
                        }

                        leaf sr-maintenance-policy {
                            type union {
                                type types-policy:param-midstring;
                                type string;
                            }
                            description "SR maintenance policy as an action";
                        }

                        leaf srv6-locator {
                            type union {
                                type types-policy:param-midstring-64;
                                type string;
                            }
                            description "Locator for SRv6 TLV to use";
                        }

                        leaf srv6-micro-segment-locator {
                            type union {
                                type types-policy:param-midstring-64;
                                type string;
                            }
                            description "Micro-segment locator for SRv6 TLV to use";
                        }

                        leaf srv6-return-path-bfd-sid {
                            when "../sr-maintenance-policy" {
                                description "sr-maintenance-policy must be set to access this leaf";
                            }
                            type union {
                                type types-policy:policy-var-name;
                                type types-sros:ipv6-address;
                            }
                            description "SRv6 return path BFD SID applied to SRv6 policy routes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container aigp-metric {
                            description "Enter the aigp-metric context";

                            choice action {
                                case add {

                                    leaf add {
                                        type types-policy:value-param-name-metric;
                                        description "AIGP metric to add";
                                    }

                                }
                                case set {

                                    leaf set {
                                        type types-policy:value-param-name-metric-igp;
                                        description "AIGP metric";
                                    }

                                }
                            }
                        } // container aigp-metric

                        container as-path {
                            description "Enter the as-path context";

                            choice action {
                                case add {

                                    leaf add {
                                        type union {
                                            type types-policy:param-midstring;
                                            type string;
                                        }
                                        description "AS path to add";
                                    }

                                }
                                case replace {

                                    leaf replace {
                                        type union {
                                            type types-policy:param-midstring;
                                            type string;
                                        }
                                        description "AS path to replace";
                                    }

                                }
                            }
                        } // container as-path

                        container as-path-prepend {
                            description "Enter the as-path-prepend context";

                            leaf as-path {
                                type types-policy:value-param-name-range;
                                description "AS number to prepend to the AS path attribute";
                            }

                            leaf repeat {
                                type types-policy:repeat-value-param-name;
                                default "1";
                                description "Number of times to prepend the specified AS number";
                            }

                        } // container as-path-prepend

                        container bgp-tunnel-metric {
                            description "Enter the bgp-tunnel-metric context";

                            leaf value {
                                type types-policy:value-param-name;
                                description "BGP tunnel table metric value";
                            }

                            leaf prefer-aigp {
                                type boolean;
                                default "false";
                                description "Use AIGP attribute as tunnel metric when present";
                            }

                            leaf prefer-med {
                                type boolean;
                                default "false";
                                description "Use MED attribute as tunnel metric when present";
                            }

                        } // container bgp-tunnel-metric

                        container metric {
                            description "Enter the metric context";

                            choice action {
                                case add {

                                    leaf add {
                                        type types-policy:value-param-name-metric;
                                        description "Metric to add";
                                    }

                                }
                                case subtract {

                                    leaf subtract {
                                        type types-policy:value-param-name-metric;
                                        description "Metric to subtract";
                                    }

                                }
                                case set {

                                    leaf set {
                                        type union {
                                            type enumeration {
                                                enum igp                            { status obsolete; }
                                            }
                                            type int64 {
                                                range "0..4294967295";
                                            }
                                            type string {
                                                length "1..32";
                                                pattern "@.+@" {
                                                    error-message "String must start and end with an at-sign (@)";
                                                }
                                            }
                                        }
                                        description "Metric to assign";
                                    }

                                }
                            }
                        } // container metric

                        container multicast-redirection {
                            description "Enter the multicast-redirection context";

                            leaf fwd-service {
                                type string;
                                default "Base";
                                description "Service ID for multicast redirection";
                            }

                            leaf ip-int-name {
                                type types-sros:interface-name;
                                description "Alternate interface where IGMP messages are redirected";
                            }

                        } // container multicast-redirection

                        container sr-label-index {
                            description "Enter the sr-label-index context";

                            leaf value {
                                type types-policy:value-524287-param-name;
                                description "BGP SR label index associated with routes";
                            }

                            leaf prefer-igp {
                                type boolean;
                                default "false";
                                description "Use the SR label index from the IGP route when present";
                            }

                        } // container sr-label-index

                        container bgp-med {
                            description "Enter the bgp-med context";

                            choice action {
                                case set {

                                    leaf set {
                                        type types-policy:value-param-name-bgp-med-igp;
                                        description "BGP-MED assignment";
                                    }

                                }
                                case adjust {

                                    leaf adjust {
                                        type string {
                                            length "1..64";
                                            pattern "(.*@.+@.*)|(.*_med_.*)|(.*_igp_.*)" {
                                                error-message "Expression must contain variable _igp_ or _med_ or @parameter@";
                                            }
                                            pattern ".*[+\\-*].*" {
                                                error-message "Expression must contain one valid operator. Supported operators are +, - and *";
                                            }
                                        }
                                        description "BGP-MED adjustment";
                                    }

                                }
                            }
                        } // container bgp-med

                        container forwarding-class {
                            description "Enter the forwarding-class context";

                            leaf fc {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "Forwarding class associated with the route";
                            }

                            leaf priority {
                                type enumeration {
                                    enum low                            { value 1; }
                                    enum high                           { value 2; }
                                }
                                description "Route priority";
                            }

                        } // container forwarding-class

                        container community {
                            description "Enter the community context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice action {
                                case action1 {

                                    leaf-list add {
                                        type union {
                                            type types-policy:param-midstring-64;
                                            type string;
                                        }
                                        max-elements 28;
                                        ordered-by user;
                                        description "List of community names to add";
                                    }

                                    leaf-list remove {
                                        type union {
                                            type types-policy:param-midstring-64;
                                            type string;
                                        }
                                        max-elements 28;
                                        ordered-by user;
                                        description "List of community names to remove";
                                    }

                                }
                                case action2 {

                                    leaf-list replace {
                                        type union {
                                            type types-policy:param-midstring-64;
                                            type string;
                                        }
                                        max-elements 28;
                                        ordered-by user;
                                        description "List of community names to replace";
                                    }

                                }
                            }
                        } // container community

                    } // container action

                } // list entry

                list named-entry {
                    when "../entry-type = 'named'" {
                        description "Active only when 'entry-type' is named";
                    }
                    key "entry-name";
                    max-elements 16384;
                    ordered-by user;
                    description "Enter the named-entry list instance";

                    leaf entry-name {
                        type types-sros:named-item-255;
                        description "Route policy entry name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container conditional-expression {
                        presence "Enable the conditional-expression context";
                        description "Enable the conditional-expression context";

                        leaf route-exists {
                            type string {
                                length "1..255";
                                pattern "\\s*\\[.+\\]\\s*(all|none)?" {
                                    error-message " enter valid prefix between [ ] and optionally add all or none";
                                }
                            }
                            description "Conditional expression to test route existence";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container conditional-expression

                    container from {
                        presence "Enable the from context";
                        description "Enable the from context";

                        leaf level {
                            type int32 {
                                range "1..2";
                            }
                            description "IS-IS route level as a match criterion";
                        }

                        leaf-list prefix-list {
                            type union {
                                type types-policy:param-midstring-64;
                                type string;
                            }
                            max-elements 28;
                            ordered-by user;
                            description "Prefix list as match criterion";
                        }

                        leaf area {
                            type types-sros:ipv4-address;
                            description "OSPF area as a match criterion";
                        }

                        leaf aggregate-contributor {
                            type boolean;
                            default "false";
                            description "Enable aggregate route match criterion";
                        }

                        leaf evpn-type {
                            type enumeration {
                                enum ethernet-auto-discovery        { value 1; }
                                enum mac-ip-advertisement           { value 2; }
                                enum inclusive-multicast            { value 3; }
                                enum ethernet-segment               { value 4; }
                                enum ip-prefix                      { value 5; }
                                enum selective-multicast            { value 6; }
                                enum multicast-join-sync            { value 7; }
                                enum multicast-leave-sync           { value 8; }
                                enum selective-pmsi-auto-discovery  { value 10; }
                            }
                            description "EVPN type as a match criterion for the entry";
                        }

                        leaf external {
                            type boolean;
                            default "false";
                            description "Specify the external IS-IS route as a match criterion";
                        }

                        leaf-list family {
                            type types-bgp:ip-family-identifier;
                            max-elements 20;
                            description "Address family as the match condition";
                        }

                        leaf group-address {
                            type union {
                                type types-policy:param-midstring;
                                type string;
                            }
                            description "Prefix list of multicast group addresses for mathcing";
                        }

                        leaf host-ip {
                            type union {
                                type types-policy:param-midstring;
                                type string;
                            }
                            description "Prefix list of IGMP host IP addresses for matching";
                        }

                        leaf-list interface {
                            type union {
                                type types-sros:named-item;
                                type types-sros:interface-name;
                                type types-sros:interface-name;
                                type types-sros:interface-name;
                            }
                            max-elements 1;
                            ordered-by user;
                            description "Interface name as match criterion";
                        }

                        leaf mvpn-type {
                            type enumeration {
                                enum intra-as-ipmsi-auto-discovery  { value 1; }
                                enum inter-as-ipmsi-auto-discovery  { value 2; }
                                enum s-pmsi-auto-discovery          { value 3; }
                                enum intra-as-segment-leaf-auto-discovery { value 4; }
                                enum source-active-auto-discovery   { value 5; }
                                enum shared-tree-join               { value 6; }
                                enum source-tree-join               { value 7; }
                            }
                            description "MVPN type as a match criterion for the entry";
                        }

                        leaf origin {
                            type enumeration {
                                enum igp                            { value 2; }
                                enum egp                            { value 3; }
                                enum incomplete                     { value 4; }
                                enum any                            { value 5; }
                                enum aaa                            { value 6; }
                                enum dynamic                        { value 7; }
                                enum static                         { value 8; }
                                enum bonding                        { value 9; }
                                enum pfcp                           { value 10; }
                            }
                            description "Route origin match criteria";
                        }

                        leaf origin-validation-state {
                            type enumeration {
                                enum valid                          { value 1; }
                                enum not-found                      { value 2; }
                                enum invalid                        { value 3; }
                            }
                            description "Origin validation state used for match criteria";
                        }

                        leaf ospf-type {
                            type int32 {
                                range "1..2";
                            }
                            description "OSPF type metric applied to unmatching route entries";
                        }

                        leaf path-type {
                            type enumeration {
                                enum ibgp                           { value 2; }
                                enum ebgp                           { value 3; }
                            }
                            description "Path type as a match criterion";
                        }

                        leaf policy {
                            type union {
                                type string {
                                    length "1..255";
                                    pattern ".*[\\[].*" {
                                        error-message "expression not valid.";
                                    }
                                }
                                type string;
                            }
                            description "Policy statement as a match criterion";
                        }

                        leaf route-distinguisher-list {
                            type union {
                                type types-policy:param-midstring-64;
                                type string;
                            }
                            description "Route distinguisher list as a match criterion";
                        }

                        leaf state {
                            type enumeration {
                                enum srrp-master                    { value 2; }
                                enum srrp-non-master                { value 3; }
                                enum ipsec-master-with-peer         { value 6; }
                                enum ipsec-master-without-peer      { value 7; }
                                enum ipsec-non-master               { value 8; }
                                enum fsg-active                     { value 10; }
                                enum fsg-standby                    { value 11; }
                            }
                            description "State used as a match criterion";
                        }

                        leaf tag {
                            type union {
                                type int64 {
                                    range "1..4294967295";
                                }
                                type enumeration {
                                    enum no-tag                         { value 0; }
                                }
                            }
                            description "Route tag used as a match criterion";
                        }

                        leaf color {
                            type int64 {
                                range "0..4294967295";
                            }
                            description "Color ID as a match criterion";
                        }

                        leaf distinguisher {
                            type int64 {
                                range "0..4294967295";
                            }
                            description "SR policy distinguisher as a match criterion";
                        }

                        leaf endpoint {
                            type types-sros:ip-address;
                            description "SR policy endpoint address as a match criterion";
                        }

                        leaf srv6-sid-prefix {
                            type union {
                                type types-policy:policy-var-name;
                                type types-sros:ipv6-unicast-prefix;
                            }
                            description "SRv6 SID value as the match criterion for the BGP route";
                        }

                        leaf srv6-tlv {
                            type enumeration {
                                enum present                        { value 1; }
                                enum not-present                    { value 2; }
                            }
                            description "SRv6 TLV presence as match criterion for BGP route";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container neighbor {
                            description "Enter the neighbor context";

                            choice neighbor {
                                case ip-address {

                                    leaf ip-address {
                                        type union {
                                            type types-sros:ip-address;
                                            type types-sros:ip-address-with-zone;
                                        }
                                        description "IP address to match the neighbor";
                                    }

                                }
                                case prefix-list {

                                    leaf prefix-list {
                                        type union {
                                            type types-policy:param-midstring;
                                            type string;
                                        }
                                        description "Name to match the neighbor prefix list";
                                    }

                                }
                            }
                        } // container neighbor

                        container interface-subnets {
                            description "Enter the interface-subnets context";

                            leaf service {
                                type string;
                                default "Base";
                                description "Service ID of the interface subnets";
                            }

                            leaf-list ip-int-name {
                                type types-sros:interface-name;
                                max-elements 10;
                                ordered-by user;
                                description "Interface name as the match criterion";
                            }

                        } // container interface-subnets

                        container as-path {
                            description "Enter the as-path context";

                            choice as-path {
                                case name {

                                    leaf name {
                                        type union {
                                            type types-policy:param-midstring;
                                            type string;
                                        }
                                        description "AS path name to match";
                                    }

                                }
                                case group {

                                    leaf group {
                                        type union {
                                            type types-policy:param-midstring;
                                            type string;
                                        }
                                        description "AS path group as a match criterion";
                                    }

                                }
                            }
                            container length {
                                description "Enter the length context";

                                leaf value {
                                    type types-policy:value-255-param-name;
                                    description "AS numbers in the AS path that match on the BGP route";
                                }

                                leaf qualifier {
                                    type types-policy:policy-qualifier;
                                    default "equal";
                                    description "Higher or lower values to be accepted as match criteria";
                                }

                                leaf unique {
                                    type boolean;
                                    default "false";
                                    description "Use unique AS numbers as matching criteria";
                                }

                            } // container length

                        } // container as-path

                        container cluster-id {
                            description "Enter the cluster-id context";

                            choice cluster-id {
                                case ip-address {

                                    leaf-list ip-address {
                                        type types-sros:ipv4-prefix-with-host-bits;
                                        max-elements 5;
                                        ordered-by user;
                                        description "Cluster list attribute IP addresses for route matching";
                                    }

                                }
                                case none-cluster-list {

                                    leaf none-cluster-list {
                                        type boolean;
                                        default "false";
                                        description "Specify matching BGP routes without a cluster ID";
                                    }

                                }
                            }
                        } // container cluster-id

                        container community {
                            description "Enter the community context";

                            choice community {
                                case name {

                                    leaf name {
                                        type union {
                                            type types-policy:param-midstring-64 {
                                                pattern "[^\\]\\[]+" {
                                                    error-message "String must not contain square brackets ([]).";
                                                }
                                            }
                                            type string;
                                        }
                                        description "Community list name";
                                    }

                                }
                                case expression {

                                    leaf expression {
                                        type string {
                                            length "1..900";
                                        }
                                        description "Community expression name as a match criterion";
                                    }

                                }
                            }
                            container count {
                                description "Enter the count context";

                                leaf value {
                                    type types-policy:value-param-1024-name;
                                    description "Number of BGP communities to match the BGP route";
                                }

                                leaf qualifier {
                                    type types-policy:policy-qualifier;
                                    default "equal";
                                    description "Higher or lower values to be accepted as match criteria";
                                }

                                leaf type {
                                    type enumeration {
                                        enum standard                       { value 2; }
                                        enum extended                       { value 3; }
                                        enum large                          { value 4; }
                                    }
                                    description "Community count to match the community count criteria";
                                }

                            } // container count

                        } // container community

                        container flowspec {
                            description "Enter the flowspec context";

                            leaf dest {
                                type union {
                                    type types-policy:param-midstring;
                                    type string;
                                }
                                description "BGP FlowSpec route matches per destination IP prefix";
                            }

                            leaf source {
                                type union {
                                    type types-policy:param-midstring;
                                    type string;
                                }
                                description "BGP FlowSpec route matches per the source IP prefix";
                            }

                        } // container flowspec

                        container local-preference {
                            description "Enter the local-preference context";

                            leaf value {
                                type types-policy:value-param-name-metric;
                                description "BGP routes per local preference value or variable name";
                            }

                            leaf qualifier {
                                type types-policy:policy-qualifier;
                                default "equal";
                                description "Higher or lower values to be accepted as match criteria";
                            }

                        } // container local-preference

                        container metric {
                            description "Enter the metric context";

                            leaf value {
                                type types-policy:value-param-name-metric;
                                description "Local preference value or variable name";
                            }

                            leaf qualifier {
                                type types-policy:policy-qualifier;
                                default "equal";
                                description "Higher or lower values to be accepted as match criteria";
                            }

                        } // container metric

                        container next-hop {
                            description "Enter the next-hop context";

                            choice next-hop {
                                case ip-address {

                                    leaf ip-address {
                                        type types-sros:ip-unicast-address;
                                        description "IP address of the next hop to match";
                                    }

                                }
                                case prefix-list {

                                    leaf prefix-list {
                                        type union {
                                            type types-policy:param-midstring;
                                            type string;
                                        }
                                        description "Name of a next hop prefix list to match";
                                    }

                                }
                            }
                        } // container next-hop

                        container protocol {
                            description "Enter the protocol context";

                            leaf-list name {
                                type enumeration {
                                    enum direct                         { value 2; }
                                    enum static                         { value 3; }
                                    enum bgp                            { value 4; }
                                    enum isis                           { value 5; }
                                    enum ospf                           { value 6; }
                                    enum rip                            { value 7; }
                                    enum aggregate                      { value 8; }
                                    enum bgp-vpn                        { value 9; }
                                    enum igmp                           { value 10; }
                                    enum pim                            { value 11; }
                                    enum ospf3                          { value 12; }
                                    enum ldp                            { value 13; }
                                    enum sub-mgmt                       { value 14; }
                                    enum mld                            { value 15; }
                                    enum managed                        { value 16; }
                                    enum vpn-leak                       { value 18; }
                                    enum nat                            { value 21; }
                                    enum periodic                       { value 22; }
                                    enum ipsec                          { value 23; }
                                    enum dhcpv6-pd                      { value 25; }
                                    enum dhcpv6-na                      { value 26; }
                                    enum dhcpv6-ta                      { value 27; }
                                    enum dhcpv6-pd-excl                 { value 28; }
                                    enum ripng                          { value 29; }
                                    enum bgp-label                      { value 31; }
                                    enum direct-interface               { value 32; }
                                    enum arp-nd                         { value 33; }
                                    enum rib-api                        { value 34; }
                                    enum dhcp-client                    { value 36; }
                                    enum evpn-ifl                       { value 37; }
                                    enum srv6                           { value 39; }
                                    enum video                          { value 40; }
                                }
                                max-elements 5;
                                description "List of protocol names as the match criterion";
                            }

                            leaf instance {
                                type union {
                                    type enumeration {
                                        enum all                            { value -1; }
                                    }
                                    type uint32 {
                                        range "0..127";
                                    }
                                }
                                default "0";
                                description "Instance for protocol IS-IS, OSPF, or OSPFv3 to match";
                            }

                        } // container protocol

                        container source-address {
                            description "Enter the source-address context";

                            choice source-address {
                                case ip-address {

                                    leaf ip-address {
                                        type types-sros:ip-address;
                                        description "Source IP address to match";
                                    }

                                }
                                case prefix-list {

                                    leaf prefix-list {
                                        type union {
                                            type types-policy:param-midstring;
                                            type string;
                                        }
                                        description "Name of a source address prefix list to match";
                                    }

                                }
                            }
                        } // container source-address

                        container policy-variables {
                            description "Enter the policy-variables context";

                            list name {
                                key "variable-name";
                                max-elements 10;
                                description "Enter the name list instance";

                                leaf variable-name {
                                    type types-policy:policy-var-name;
                                    description "Global variable name used to reference policy functions";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                choice variable-type {
                                    mandatory true;
                                    case value {

                                        leaf value {
                                            type types-sros:named-item;
                                            description "Policy variable value";
                                        }

                                    }
                                    case number {

                                        leaf number {
                                            type uint64 {
                                                range "0..4294967295";
                                            }
                                            description "Numerical value of the policy variable";
                                        }

                                    }
                                    case address {

                                        leaf address {
                                            type types-sros:ip-address;
                                            description "IP address of the policy variable";
                                        }

                                    }
                                    case decimal {

                                        leaf decimal {
                                            type decimal64 {
                                                range "0.000..4294967295.000";
                                                fraction-digits 3;
                                            }
                                            description "Attribute decimal to which variable name is resolved";
                                        }

                                    }
                                    case prefix {

                                        leaf prefix {
                                            type types-sros:ip-prefix;
                                            description "Prefix value associated with the variable name";
                                        }

                                    }
                                }
                            } // list name

                        } // container policy-variables

                    } // container from

                    container to {
                        presence "Enable the to context";
                        description "Enable the to context";

                        leaf level {
                            type int32 {
                                range "1..2";
                            }
                            description "IS-IS route level as a match criterion";
                        }

                        leaf-list prefix-list {
                            type union {
                                type types-policy:param-midstring-64;
                                type string;
                            }
                            max-elements 28;
                            ordered-by user;
                            description "Prefix list as match criterion";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container neighbor {
                            description "Enter the neighbor context";

                            choice neighbor {
                                case ip-address {

                                    leaf ip-address {
                                        type union {
                                            type types-sros:ip-address;
                                            type types-sros:ip-address-with-zone;
                                        }
                                        description "IP address to match the neighbor";
                                    }

                                }
                                case prefix-list {

                                    leaf prefix-list {
                                        type union {
                                            type types-policy:param-midstring;
                                            type string;
                                        }
                                        description "Name to match the neighbor prefix list";
                                    }

                                }
                            }
                        } // container neighbor

                        container protocol {
                            description "Enter the protocol context";

                            leaf-list name {
                                type enumeration {
                                    enum bgp                            { value 4; }
                                    enum isis                           { value 5; }
                                    enum ospf                           { value 6; }
                                    enum rip                            { value 7; }
                                    enum bgp-vpn                        { value 9; }
                                    enum ospf3                          { value 12; }
                                    enum ldp                            { value 13; }
                                    enum vpn-leak                       { value 18; }
                                    enum ripng                          { value 29; }
                                    enum bgp-label                      { value 31; }
                                    enum evpn-ifl                       { value 37; }
                                }
                                max-elements 2;
                                description "Protocol name to match";
                            }

                            leaf instance {
                                type union {
                                    type enumeration {
                                        enum all                            { value -1; }
                                    }
                                    type uint32 {
                                        range "0..127";
                                    }
                                }
                                default "0";
                                description "Instance for the IS-IS, OSPF, or OSPF3 protocol";
                            }

                        } // container protocol

                    } // container to

                    container action {
                        presence "Enable the action context";
                        description "Enable the action context";

                        leaf action-type {
                            type enumeration {
                                enum accept                         { value 1; }
                                enum reject                         { value 2; }
                                enum next-entry                     { value 3; }
                                enum next-policy                    { value 4; }
                            }
                            mandatory true;
                            description "Action type for routes matching the route policy entry";
                        }

                        leaf add-paths-send-limit {
                            type union {
                                type int32 {
                                    range "1..16";
                                }
                                type enumeration {
                                    enum multipaths                     { value -1; }
                                }
                            }
                            description "BGP Add-Paths send limit applied for routes";
                        }

                        leaf admin-tag-policy {
                            type union {
                                type types-policy:param-midstring-64;
                                type string;
                            }
                            description "Administrative tag policy name";
                        }

                        leaf advertise-label {
                            type enumeration {
                                enum per-prefix                     { value 1; }
                                enum pop                            { value 2; }
                                enum pop-and-forward                { value 3; }
                            }
                            description "Label allocation for matched BGP routes";
                        }

                        leaf bgp-high-priority {
                            type boolean;
                            default "false";
                            description "Tag routes as high priority for fast table updates";
                        }

                        leaf bgp-leak {
                            type boolean;
                            default "false";
                            description "Allow leaking for BGP routes";
                        }

                        leaf create-mpls-tunnel {
                            type boolean;
                            default "false";
                            description "Create an MPLS tunnel";
                        }

                        leaf create-udp-tunnel {
                            type boolean;
                            default "false";
                            description "Create an MPLS-over-UDP tunnel";
                        }

                        leaf damping {
                            type union {
                                type enumeration {
                                    enum none                           { value 0; }
                                }
                                type types-policy:param-midstring;
                                type string;
                            }
                            description "Damping profile used for routes";
                        }

                        leaf dest-class {
                            type types-sros:class-index;
                            description "Default destination class for the policy statement";
                        }

                        leaf egress-statistics {
                            type boolean;
                            default "false";
                            description "Enable egress statistics for BGP-LU routes";
                        }

                        leaf ingress-statistics {
                            type boolean;
                            default "false";
                            description "Enable ingress statistics for BGP-LU routes";
                        }

                        leaf flex-algo {
                            type types-policy:value-param-name-flex-algo;
                            description "Flexible algorithm for BGP next-hop autobind operation";
                        }

                        leaf install-backup-path {
                            type boolean;
                            default "false";
                            description "Install a preprogrammed backup path for the prefix";
                        }

                        leaf local-preference {
                            type types-policy:value-param-name-metric;
                            description "BGP local preference for routes not matching any entry";
                        }

                        leaf nat-policy {
                            type union {
                                type types-policy:param-midstring;
                                type string;
                            }
                            description "BGP-VPN imported route and a NAT policy association";
                        }

                        leaf next-hop {
                            type union {
                                type enumeration {
                                    enum peer-address                   { value -2; }
                                    enum self                           { value -1; }
                                }
                                type types-sros:ip-address;
                                type string {
                                    length "1..32";
                                    pattern "@.+@" {
                                        error-message "String must start and end with an at-sign (@)";
                                    }
                                }
                            }
                            description "Next-hop IP address applied to routes";
                        }

                        leaf origin {
                            type union {
                                type enumeration {
                                    enum igp                            { value 2; }
                                    enum egp                            { value 3; }
                                    enum incomplete                     { value 4; }
                                }
                                type string {
                                    length "1..32";
                                    pattern "@.+@" {
                                        error-message "String must start and end with an at-sign (@)";
                                    }
                                }
                            }
                            description "BGP origin for routes that are exported into BGP";
                        }

                        leaf origin-validation-state {
                            type union {
                                type enumeration {
                                    enum valid                          { value 1; }
                                    enum not-found                      { value 2; }
                                    enum invalid                        { value 3; }
                                }
                                type string {
                                    length "1..32";
                                    pattern "@.+@" {
                                        error-message "String must start and end with an at-sign (@)";
                                    }
                                }
                            }
                            description "Origin validation state for routes";
                        }

                        leaf prefer-transport-frr {
                            type boolean;
                            default "false";
                            description "Enable transport FRR preference";
                        }

                        leaf preference {
                            type union {
                                type uint32 {
                                    range "1..255";
                                }
                                type string {
                                    length "1..32";
                                    pattern "@.+@" {
                                        error-message "String must start and end with an at-sign (@)";
                                    }
                                }
                            }
                            description "Route preference applied to routes";
                        }

                        leaf resolve-static {
                            type boolean;
                            default "false";
                            description "Resolve next hop of a static route for the BGP next hop";
                        }

                        leaf source-class {
                            type types-sros:class-index;
                            description "Default source class for the policy statement";
                        }

                        leaf sticky-ecmp {
                            type boolean;
                            default "false";
                            description "Specify the sticky ECMP flag for BGP ECMP routes";
                        }

                        leaf tag {
                            type union {
                                type uint32 {
                                    range "1..4294967295";
                                }
                                type string {
                                    length "1..32";
                                    pattern "@.+@" {
                                        error-message "String must start and end with an at-sign (@)";
                                    }
                                }
                            }
                            description "OSPF RIP or IS-IS tag applied to routes";
                        }

                        leaf type {
                            type union {
                                type int32 {
                                    range "1..2";
                                }
                                type string {
                                    length "1..32";
                                    pattern "@.+@" {
                                        error-message "String must start and end with an at-sign (@)";
                                    }
                                }
                            }
                            description "OSPF metric type applied to routes";
                        }

                        leaf route-table-install {
                            type boolean;
                            default "true";
                            description "Allow BGP route installation in the route table";
                        }

                        leaf sr-maintenance-policy {
                            type union {
                                type types-policy:param-midstring;
                                type string;
                            }
                            description "SR maintenance policy as an action";
                        }

                        leaf srv6-locator {
                            type union {
                                type types-policy:param-midstring-64;
                                type string;
                            }
                            description "Locator for SRv6 TLV to use";
                        }

                        leaf srv6-micro-segment-locator {
                            type union {
                                type types-policy:param-midstring-64;
                                type string;
                            }
                            description "Micro-segment locator for SRv6 TLV to use";
                        }

                        leaf srv6-return-path-bfd-sid {
                            when "../sr-maintenance-policy" {
                                description "sr-maintenance-policy must be set to access this leaf";
                            }
                            type union {
                                type types-policy:policy-var-name;
                                type types-sros:ipv6-address;
                            }
                            description "SRv6 return path BFD SID applied to SRv6 policy routes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container aigp-metric {
                            description "Enter the aigp-metric context";

                            choice action {
                                case add {

                                    leaf add {
                                        type types-policy:value-param-name-metric;
                                        description "AIGP metric to add";
                                    }

                                }
                                case set {

                                    leaf set {
                                        type types-policy:value-param-name-metric-igp;
                                        description "AIGP metric";
                                    }

                                }
                            }
                        } // container aigp-metric

                        container as-path {
                            description "Enter the as-path context";

                            choice action {
                                case add {

                                    leaf add {
                                        type union {
                                            type types-policy:param-midstring;
                                            type string;
                                        }
                                        description "AS path to add";
                                    }

                                }
                                case replace {

                                    leaf replace {
                                        type union {
                                            type types-policy:param-midstring;
                                            type string;
                                        }
                                        description "AS path to replace";
                                    }

                                }
                            }
                        } // container as-path

                        container as-path-prepend {
                            description "Enter the as-path-prepend context";

                            leaf as-path {
                                type types-policy:value-param-name-range;
                                description "AS number to prepend to the AS path attribute";
                            }

                            leaf repeat {
                                type types-policy:repeat-value-param-name;
                                default "1";
                                description "Number of times to prepend the specified AS number";
                            }

                        } // container as-path-prepend

                        container bgp-tunnel-metric {
                            description "Enter the bgp-tunnel-metric context";

                            leaf value {
                                type types-policy:value-param-name;
                                description "BGP tunnel table metric value";
                            }

                            leaf prefer-aigp {
                                type boolean;
                                default "false";
                                description "Use AIGP attribute as tunnel metric when present";
                            }

                            leaf prefer-med {
                                type boolean;
                                default "false";
                                description "Use MED attribute as tunnel metric when present";
                            }

                        } // container bgp-tunnel-metric

                        container metric {
                            description "Enter the metric context";

                            choice action {
                                case add {

                                    leaf add {
                                        type types-policy:value-param-name-metric;
                                        description "Metric to add";
                                    }

                                }
                                case subtract {

                                    leaf subtract {
                                        type types-policy:value-param-name-metric;
                                        description "Metric to subtract";
                                    }

                                }
                                case set {

                                    leaf set {
                                        type union {
                                            type enumeration {
                                                enum igp                            { status obsolete; }
                                            }
                                            type int64 {
                                                range "0..4294967295";
                                            }
                                            type string {
                                                length "1..32";
                                                pattern "@.+@" {
                                                    error-message "String must start and end with an at-sign (@)";
                                                }
                                            }
                                        }
                                        description "Metric to assign";
                                    }

                                }
                            }
                        } // container metric

                        container multicast-redirection {
                            description "Enter the multicast-redirection context";

                            leaf fwd-service {
                                type string;
                                default "Base";
                                description "Service ID for multicast redirection";
                            }

                            leaf ip-int-name {
                                type types-sros:interface-name;
                                description "Alternate interface where IGMP messages are redirected";
                            }

                        } // container multicast-redirection

                        container sr-label-index {
                            description "Enter the sr-label-index context";

                            leaf value {
                                type types-policy:value-524287-param-name;
                                description "BGP SR label index associated with routes";
                            }

                            leaf prefer-igp {
                                type boolean;
                                default "false";
                                description "Use the SR label index from the IGP route when present";
                            }

                        } // container sr-label-index

                        container bgp-med {
                            description "Enter the bgp-med context";

                            choice action {
                                case set {

                                    leaf set {
                                        type types-policy:value-param-name-bgp-med-igp;
                                        description "BGP-MED assignment";
                                    }

                                }
                                case adjust {

                                    leaf adjust {
                                        type string {
                                            length "1..64";
                                            pattern "(.*@.+@.*)|(.*_med_.*)|(.*_igp_.*)" {
                                                error-message "Expression must contain variable _igp_ or _med_ or @parameter@";
                                            }
                                            pattern ".*[+\\-*].*" {
                                                error-message "Expression must contain one valid operator. Supported operators are +, - and *";
                                            }
                                        }
                                        description "BGP-MED adjustment";
                                    }

                                }
                            }
                        } // container bgp-med

                        container forwarding-class {
                            description "Enter the forwarding-class context";

                            leaf fc {
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                description "Forwarding class associated with the route";
                            }

                            leaf priority {
                                type enumeration {
                                    enum low                            { value 1; }
                                    enum high                           { value 2; }
                                }
                                description "Route priority";
                            }

                        } // container forwarding-class

                        container community {
                            description "Enter the community context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice action {
                                case action1 {

                                    leaf-list add {
                                        type union {
                                            type types-policy:param-midstring-64;
                                            type string;
                                        }
                                        max-elements 28;
                                        ordered-by user;
                                        description "List of community names to add";
                                    }

                                    leaf-list remove {
                                        type union {
                                            type types-policy:param-midstring-64;
                                            type string;
                                        }
                                        max-elements 28;
                                        ordered-by user;
                                        description "List of community names to remove";
                                    }

                                }
                                case action2 {

                                    leaf-list replace {
                                        type union {
                                            type types-policy:param-midstring-64;
                                            type string;
                                        }
                                        max-elements 28;
                                        ordered-by user;
                                        description "List of community names to replace";
                                    }

                                }
                            }
                        } // container community

                    } // container action

                } // list named-entry

                container default-action {
                    presence "Enable the default-action context";
                    description "Enable the default-action context";

                    leaf action-type {
                        type enumeration {
                            enum accept                         { value 1; }
                            enum reject                         { value 2; }
                            enum next-entry                     { value 3; }
                            enum next-policy                    { value 4; }
                        }
                        mandatory true;
                        description "Action type for routes matching the route policy entry";
                    }

                    leaf add-paths-send-limit {
                        type union {
                            type int32 {
                                range "1..16";
                            }
                            type enumeration {
                                enum multipaths                     { value -1; }
                            }
                        }
                        description "BGP Add-Paths send limit applied for routes";
                    }

                    leaf admin-tag-policy {
                        type union {
                            type types-policy:param-midstring-64;
                            type string;
                        }
                        description "Administrative tag policy name";
                    }

                    leaf advertise-label {
                        type enumeration {
                            enum per-prefix                     { value 1; }
                            enum pop                            { value 2; }
                            enum pop-and-forward                { value 3; }
                        }
                        description "Label allocation for matched BGP routes";
                    }

                    leaf bgp-high-priority {
                        type boolean;
                        default "false";
                        description "Tag routes as high priority for fast table updates";
                    }

                    leaf bgp-leak {
                        type boolean;
                        default "false";
                        description "Allow leaking for BGP routes";
                    }

                    leaf create-mpls-tunnel {
                        type boolean;
                        default "false";
                        description "Create an MPLS tunnel";
                    }

                    leaf create-udp-tunnel {
                        type boolean;
                        default "false";
                        description "Create an MPLS-over-UDP tunnel";
                    }

                    leaf damping {
                        type union {
                            type enumeration {
                                enum none                           { value 0; }
                            }
                            type types-policy:param-midstring;
                            type string;
                        }
                        description "Damping profile used for routes";
                    }

                    leaf dest-class {
                        type types-sros:class-index;
                        description "Default destination class for the policy statement";
                    }

                    leaf egress-statistics {
                        type boolean;
                        default "false";
                        description "Enable egress statistics for BGP-LU routes";
                    }

                    leaf ingress-statistics {
                        type boolean;
                        default "false";
                        description "Enable ingress statistics for BGP-LU routes";
                    }

                    leaf flex-algo {
                        type types-policy:value-param-name-flex-algo;
                        description "Flexible algorithm for BGP next-hop autobind operation";
                    }

                    leaf install-backup-path {
                        type boolean;
                        default "false";
                        description "Install a preprogrammed backup path for the prefix";
                    }

                    leaf local-preference {
                        type types-policy:value-param-name-metric;
                        description "BGP local preference for routes not matching any entry";
                    }

                    leaf nat-policy {
                        type union {
                            type types-policy:param-midstring;
                            type string;
                        }
                        description "BGP-VPN imported route and a NAT policy association";
                    }

                    leaf next-hop {
                        type union {
                            type enumeration {
                                enum peer-address                   { value -2; }
                                enum self                           { value -1; }
                            }
                            type types-sros:ip-address;
                            type string {
                                length "1..32";
                                pattern "@.+@" {
                                    error-message "String must start and end with an at-sign (@)";
                                }
                            }
                        }
                        description "Next-hop IP address applied to routes";
                    }

                    leaf origin {
                        type union {
                            type enumeration {
                                enum igp                            { value 2; }
                                enum egp                            { value 3; }
                                enum incomplete                     { value 4; }
                            }
                            type string {
                                length "1..32";
                                pattern "@.+@" {
                                    error-message "String must start and end with an at-sign (@)";
                                }
                            }
                        }
                        description "BGP origin for routes that are exported into BGP";
                    }

                    leaf origin-validation-state {
                        type union {
                            type enumeration {
                                enum valid                          { value 1; }
                                enum not-found                      { value 2; }
                                enum invalid                        { value 3; }
                            }
                            type string {
                                length "1..32";
                                pattern "@.+@" {
                                    error-message "String must start and end with an at-sign (@)";
                                }
                            }
                        }
                        description "Origin validation state for routes";
                    }

                    leaf prefer-transport-frr {
                        type boolean;
                        default "false";
                        description "Enable transport FRR preference";
                    }

                    leaf preference {
                        type union {
                            type uint32 {
                                range "1..255";
                            }
                            type string {
                                length "1..32";
                                pattern "@.+@" {
                                    error-message "String must start and end with an at-sign (@)";
                                }
                            }
                        }
                        description "Route preference applied to routes";
                    }

                    leaf resolve-static {
                        type boolean;
                        default "false";
                        description "Resolve next hop of a static route for the BGP next hop";
                    }

                    leaf source-class {
                        type types-sros:class-index;
                        description "Default source class for the policy statement";
                    }

                    leaf sticky-ecmp {
                        type boolean;
                        default "false";
                        description "Specify the sticky ECMP flag for BGP ECMP routes";
                    }

                    leaf tag {
                        type union {
                            type uint32 {
                                range "1..4294967295";
                            }
                            type string {
                                length "1..32";
                                pattern "@.+@" {
                                    error-message "String must start and end with an at-sign (@)";
                                }
                            }
                        }
                        description "OSPF RIP or IS-IS tag applied to routes";
                    }

                    leaf type {
                        type union {
                            type int32 {
                                range "1..2";
                            }
                            type string {
                                length "1..32";
                                pattern "@.+@" {
                                    error-message "String must start and end with an at-sign (@)";
                                }
                            }
                        }
                        description "OSPF metric type applied to routes";
                    }

                    leaf route-table-install {
                        type boolean;
                        default "true";
                        description "Allow BGP route installation in the route table";
                    }

                    leaf sr-maintenance-policy {
                        type union {
                            type types-policy:param-midstring;
                            type string;
                        }
                        description "SR maintenance policy as an action";
                    }

                    leaf srv6-locator {
                        type union {
                            type types-policy:param-midstring-64;
                            type string;
                        }
                        description "Locator for SRv6 TLV to use";
                    }

                    leaf srv6-micro-segment-locator {
                        type union {
                            type types-policy:param-midstring-64;
                            type string;
                        }
                        description "Micro-segment locator for SRv6 TLV to use";
                    }

                    leaf srv6-return-path-bfd-sid {
                        when "../sr-maintenance-policy" {
                            description "sr-maintenance-policy must be set to access this leaf";
                        }
                        type union {
                            type types-policy:policy-var-name;
                            type types-sros:ipv6-address;
                        }
                        description "SRv6 return path BFD SID applied to SRv6 policy routes";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container aigp-metric {
                        description "Enter the aigp-metric context";

                        choice action {
                            case add {

                                leaf add {
                                    type types-policy:value-param-name-metric;
                                    description "AIGP metric to add";
                                }

                            }
                            case set {

                                leaf set {
                                    type types-policy:value-param-name-metric-igp;
                                    description "AIGP metric";
                                }

                            }
                        }
                    } // container aigp-metric

                    container as-path {
                        description "Enter the as-path context";

                        choice action {
                            case add {

                                leaf add {
                                    type union {
                                        type types-policy:param-midstring;
                                        type string;
                                    }
                                    description "AS path to add";
                                }

                            }
                            case replace {

                                leaf replace {
                                    type union {
                                        type types-policy:param-midstring;
                                        type string;
                                    }
                                    description "AS path to replace";
                                }

                            }
                        }
                    } // container as-path

                    container as-path-prepend {
                        description "Enter the as-path-prepend context";

                        leaf as-path {
                            type types-policy:value-param-name-range;
                            description "AS number to prepend to the AS path attribute";
                        }

                        leaf repeat {
                            type types-policy:repeat-value-param-name;
                            default "1";
                            description "Number of times to prepend the specified AS number";
                        }

                    } // container as-path-prepend

                    container bgp-tunnel-metric {
                        description "Enter the bgp-tunnel-metric context";

                        leaf value {
                            type types-policy:value-param-name;
                            description "BGP tunnel table metric value";
                        }

                        leaf prefer-aigp {
                            type boolean;
                            default "false";
                            description "Use AIGP attribute as tunnel metric when present";
                        }

                        leaf prefer-med {
                            type boolean;
                            default "false";
                            description "Use MED attribute as tunnel metric when present";
                        }

                    } // container bgp-tunnel-metric

                    container metric {
                        description "Enter the metric context";

                        choice action {
                            case add {

                                leaf add {
                                    type types-policy:value-param-name-metric;
                                    description "Metric to add";
                                }

                            }
                            case subtract {

                                leaf subtract {
                                    type types-policy:value-param-name-metric;
                                    description "Metric to subtract";
                                }

                            }
                            case set {

                                leaf set {
                                    type union {
                                        type enumeration {
                                            enum igp                            { status obsolete; }
                                        }
                                        type int64 {
                                            range "0..4294967295";
                                        }
                                        type string {
                                            length "1..32";
                                            pattern "@.+@" {
                                                error-message "String must start and end with an at-sign (@)";
                                            }
                                        }
                                    }
                                    description "Metric to assign";
                                }

                            }
                        }
                    } // container metric

                    container multicast-redirection {
                        description "Enter the multicast-redirection context";

                        leaf fwd-service {
                            type string;
                            default "Base";
                            description "Service ID for multicast redirection";
                        }

                        leaf ip-int-name {
                            type types-sros:interface-name;
                            description "Alternate interface where IGMP messages are redirected";
                        }

                    } // container multicast-redirection

                    container sr-label-index {
                        description "Enter the sr-label-index context";

                        leaf value {
                            type types-policy:value-524287-param-name;
                            description "BGP SR label index associated with routes";
                        }

                        leaf prefer-igp {
                            type boolean;
                            default "false";
                            description "Use the SR label index from the IGP route when present";
                        }

                    } // container sr-label-index

                    container bgp-med {
                        description "Enter the bgp-med context";

                        choice action {
                            case set {

                                leaf set {
                                    type types-policy:value-param-name-bgp-med-igp;
                                    description "BGP-MED assignment";
                                }

                            }
                            case adjust {

                                leaf adjust {
                                    type string {
                                        length "1..64";
                                        pattern "(.*@.+@.*)|(.*_med_.*)|(.*_igp_.*)" {
                                            error-message "Expression must contain variable _igp_ or _med_ or @parameter@";
                                        }
                                        pattern ".*[+\\-*].*" {
                                            error-message "Expression must contain one valid operator. Supported operators are +, - and *";
                                        }
                                    }
                                    description "BGP-MED adjustment";
                                }

                            }
                        }
                    } // container bgp-med

                    container community {
                        description "Enter the community context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice action {
                            case action1 {

                                leaf-list add {
                                    type union {
                                        type types-policy:param-midstring-64;
                                        type string;
                                    }
                                    max-elements 28;
                                    ordered-by user;
                                    description "List of community names to add";
                                }

                                leaf-list remove {
                                    type union {
                                        type types-policy:param-midstring-64;
                                        type string;
                                    }
                                    max-elements 28;
                                    ordered-by user;
                                    description "List of community names to remove";
                                }

                            }
                            case action2 {

                                leaf-list replace {
                                    type union {
                                        type types-policy:param-midstring-64;
                                        type string;
                                    }
                                    max-elements 28;
                                    ordered-by user;
                                    description "List of community names to replace";
                                }

                            }
                        }
                    } // container community

                } // container default-action

            } // list policy-statement

        } // container policy-options

    } // grouping conf-policy-options

}
