submodule nokia-state-mcast-cac {

    yang-version "1.1";

    belongs-to nokia-state { prefix "state"; }

    import ietf-yang-types                { prefix "yang"; }
    import nokia-sros-yang-extensions     { prefix "sros-ext"; }
    import nokia-types-mcast-cac          { prefix "types-mcast-cac"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for mcast cac on SR OS based routers.

         Copyright 2016 Nokia. All rights reserved. Reproduction of this document
         is authorized on the condition that the foregoing copyright notice is included.

         This nokia-state-mcast-cac YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-mcast-cac-mcac {
        ///nokia-state/state/mcac
        container mcac {
            description "Enable the mcac context";

            ///nokia-state/state/mcac/interface-policy
            list interface-policy {
                key "policy-name";
                description "Enter the interface-policy list instance";

                ///nokia-state/state/mcac/interface-policy/policy-name
                leaf policy-name {
                    type string {
                        length "1..32";
                    }
                    description "MCAC interface policy name";
                }

                ///nokia-state/state/mcac/interface-policy/mandatory-bw-use
                leaf mandatory-bw-use {
                    type types-mcast-cac:bandwidth;
                    description
                        "Operational in-use bandwidth for the mandatory channels
                         for this interface policy.";
                }

                ///nokia-state/state/mcac/interface-policy/optional-bw-use
                leaf optional-bw-use {
                    type types-mcast-cac:bandwidth;
                    description
                        "Operational in-use bandwidth for the optional channels
                         for this interface policy.";
                }

            } // list interface-policy

            ///nokia-state/state/mcac/policy
            list policy {
                key "policy-name";
                description "Enter the policy list instance";

                ///nokia-state/state/mcac/policy/policy-name
                leaf policy-name {
                    type string {
                        length "1..32";
                    }
                    description "Name of the global MCAC channel definition policy";
                }

                ///nokia-state/state/mcac/policy/historical-router-access-information
                list historical-router-access-information {
                    key "router-instance application interface group source";
                    description "Enter the historical-router-access-information list instance";

                    ///nokia-state/state/mcac/policy/historical-router-access-information/router-instance
                    leaf router-instance {
                        type types-sros:vrtr-id;
                        description ".";
                    }

                    ///nokia-state/state/mcac/policy/historical-router-access-information/application
                    leaf application {
                        type types-mcast-cac:router-application;
                        description ".";
                    }

                    ///nokia-state/state/mcac/policy/historical-router-access-information/interface
                    leaf interface {
                        type string {
                            length "0..32";
                        }
                        description ".";
                    }

                    ///nokia-state/state/mcac/policy/historical-router-access-information/group
                    leaf group {
                        type types-sros:ip-address;
                        description "Group address.";
                    }

                    ///nokia-state/state/mcac/policy/historical-router-access-information/source
                    leaf source {
                        type types-sros:ip-address;
                        description "Source address.";
                    }

                    ///nokia-state/state/mcac/policy/historical-router-access-information/action
                    leaf action {
                        type types-mcast-cac:policy-action;
                        description
                            "The action specified by the mcac policy for the application
                             interface to act upon.";
                    }

                    ///nokia-state/state/mcac/policy/historical-router-access-information/reason
                    leaf reason {
                        type enumeration {
                            enum bundle-disabled                { value 1; }
                            enum bundle-no-available-bandwidth  { value 2; }
                            enum interface-no-available-bandwidth { value 3; }
                            enum no-channel-in-policy           { value 4; }
                            enum algorithm-passed               { value 5; }
                            enum user-no-available-bandwidth    { value 6; }
                            enum subscriber-no-mcac-policy      { value 7; }
                            enum interface-policy-no-available-bandwidth { value 8; }
                            enum low-memory                     { value 9; }
                        }
                        description
                            "The reason for the action specified by the mcac policy
                             for the application interface to act upon.";
                    }

                    ///nokia-state/state/mcac/policy/historical-router-access-information/channel-type
                    leaf channel-type {
                        type types-mcast-cac:channel-type;
                        description
                            "The channel type configured at the mcac policy at the time of
                             request from the application interface.";
                    }

                    ///nokia-state/state/mcac/policy/historical-router-access-information/channel-bandwidth
                    leaf channel-bandwidth {
                        type types-mcast-cac:bandwidth;
                        description
                            "The channel bandwidth configured at the mcac policy at the
                             time of request from the application interface.";
                    }

                    ///nokia-state/state/mcac/policy/historical-router-access-information/bundle-available-bw
                    leaf bundle-available-bw {
                        type types-mcast-cac:bandwidth;
                        description
                            "The available bundle bandwidth after the requested channel was
                             either accepted or discarded by the mcac policy.";
                    }

                    ///nokia-state/state/mcac/policy/historical-router-access-information/interface-available-bw
                    leaf interface-available-bw {
                        type types-mcast-cac:bandwidth;
                        description
                            "The available interface bandwidth after the requested channel was
                             either accepted or discarded by the mcac policy.";
                    }

                    ///nokia-state/state/mcac/policy/historical-router-access-information/reapplied
                    leaf reapplied {
                        type boolean;
                        description
                            "The mcac policy was reapplied on the already
                             accepted channel due lag constraints.";
                    }

                    ///nokia-state/state/mcac/policy/historical-router-access-information/apply-attempts
                    leaf apply-attempts {
                        type uint32;
                        description
                            "The number of times the mcac policy was applied for
                             a particular channel entry by the application.";
                    }

                    ///nokia-state/state/mcac/policy/historical-router-access-information/time
                    leaf time {
                        type yang:date-and-time;
                        description
                            "The timestamp of the last time the mcac policy was
                             applied for this channel entry.";
                    }

                } // list historical-router-access-information

                ///nokia-state/state/mcac/policy/historical-service-access-information
                list historical-service-access-information {
                    key "service application port encap-value group source";
                    description "Enter the historical-service-access-information list instance";

                    ///nokia-state/state/mcac/policy/historical-service-access-information/service
                    leaf service {
                        type types-services:service-id;
                        description ".";
                    }

                    ///nokia-state/state/mcac/policy/historical-service-access-information/application
                    leaf application {
                        type types-mcast-cac:service-application;
                        description ".";
                    }

                    ///nokia-state/state/mcac/policy/historical-service-access-information/port
                    leaf port {
                        type types-sros:port;
                        description ".";
                    }

                    ///nokia-state/state/mcac/policy/historical-service-access-information/encap-value
                    leaf encap-value {
                        type types-sros:encap-val;
                        description ".";
                    }

                    ///nokia-state/state/mcac/policy/historical-service-access-information/group
                    leaf group {
                        type types-sros:ip-address;
                        description "Group address.";
                    }

                    ///nokia-state/state/mcac/policy/historical-service-access-information/source
                    leaf source {
                        type types-sros:ip-address;
                        description "Source address.";
                    }

                    ///nokia-state/state/mcac/policy/historical-service-access-information/action
                    leaf action {
                        type types-mcast-cac:policy-action;
                        description
                            "The action specified by the mcac policy for the application
                             interface to act upon.";
                    }

                    ///nokia-state/state/mcac/policy/historical-service-access-information/reason
                    leaf reason {
                        type enumeration {
                            enum bundle-disabled                { value 1; }
                            enum bundle-no-available-bandwidth  { value 2; }
                            enum interface-no-available-bandwidth { value 3; }
                            enum no-channel-in-policy           { value 4; }
                            enum algorithm-passed               { value 5; }
                            enum user-no-available-bandwidth    { value 6; }
                            enum subscriber-no-mcac-policy      { value 7; }
                            enum interface-policy-no-available-bandwidth { value 8; }
                            enum low-memory                     { value 9; }
                        }
                        description
                            "The reason for the action specified by the mcac policy
                             for the application interface to act upon.";
                    }

                    ///nokia-state/state/mcac/policy/historical-service-access-information/channel-type
                    leaf channel-type {
                        type types-mcast-cac:channel-type;
                        description
                            "The channel type configured at the mcac policy at the time of
                             request from the application interface.";
                    }

                    ///nokia-state/state/mcac/policy/historical-service-access-information/channel-bandwidth
                    leaf channel-bandwidth {
                        type types-mcast-cac:bandwidth;
                        description
                            "The channel bandwidth configured at the mcac policy at the
                             time of request from the application interface.";
                    }

                    ///nokia-state/state/mcac/policy/historical-service-access-information/bundle-available-bw
                    leaf bundle-available-bw {
                        type types-mcast-cac:bandwidth;
                        description
                            "The available bundle bandwidth after the requested channel was
                             either accepted or discarded by the mcac policy.";
                    }

                    ///nokia-state/state/mcac/policy/historical-service-access-information/interface-available-bw
                    leaf interface-available-bw {
                        type types-mcast-cac:bandwidth;
                        description
                            "The available interface bandwidth after the requested channel was
                             either accepted or discarded by the mcac policy.";
                    }

                    ///nokia-state/state/mcac/policy/historical-service-access-information/reapplied
                    leaf reapplied {
                        type boolean;
                        description
                            "The mcac policy was reapplied on the already
                             accepted channel due lag constraints.";
                    }

                    ///nokia-state/state/mcac/policy/historical-service-access-information/apply-attempts
                    leaf apply-attempts {
                        type uint32;
                        description
                            "The number of times the mcac policy was applied for
                             a particular channel entry by the application.";
                    }

                    ///nokia-state/state/mcac/policy/historical-service-access-information/time
                    leaf time {
                        type yang:date-and-time;
                        description
                            "The timestamp of the last time the mcac policy was
                             applied for this channel entry.";
                    }

                } // list historical-service-access-information

                ///nokia-state/state/mcac/policy/bundle
                list bundle {
                    key "bundle-name";
                    description "Enter the bundle list instance";

                    ///nokia-state/state/mcac/policy/bundle/bundle-name
                    leaf bundle-name {
                        type string {
                            length "1..32";
                        }
                        description "Multicast policy bundle name";
                    }

                    ///nokia-state/state/mcac/policy/bundle/operational-router-interface-data
                    list operational-router-interface-data {
                        key "router-instance application interface";
                        description "Enter the operational-router-interface-data list instance";

                        ///nokia-state/state/mcac/policy/bundle/operational-router-interface-data/router-instance
                        leaf router-instance {
                            type types-sros:vrtr-id;
                            description ".";
                        }

                        ///nokia-state/state/mcac/policy/bundle/operational-router-interface-data/application
                        leaf application {
                            type types-mcast-cac:router-application;
                            description ".";
                        }

                        ///nokia-state/state/mcac/policy/bundle/operational-router-interface-data/interface
                        leaf interface {
                            type string {
                                length "0..32";
                            }
                            description ".";
                        }

                        ///nokia-state/state/mcac/policy/bundle/operational-router-interface-data/number-of-active-channels
                        leaf number-of-active-channels {
                            type yang:counter32;
                            description "Number of active channels.";
                        }

                        ///nokia-state/state/mcac/policy/bundle/operational-router-interface-data/bandwidth
                        leaf bandwidth {
                            type types-mcast-cac:bandwidth;
                            description "maximum bandwidth allowed.";
                        }

                        ///nokia-state/state/mcac/policy/bundle/operational-router-interface-data/available-bw
                        leaf available-bw {
                            type types-mcast-cac:bandwidth;
                            description "Available bandwidth";
                        }

                        ///nokia-state/state/mcac/policy/bundle/operational-router-interface-data/available-mandatory-bw
                        leaf available-mandatory-bw {
                            type types-mcast-cac:bandwidth;
                            description "Available pre-reserved bandwidth for the mandatory channels.";
                        }

                        ///nokia-state/state/mcac/policy/bundle/operational-router-interface-data/mandatory-bw-use
                        leaf mandatory-bw-use {
                            type types-mcast-cac:bandwidth;
                            description "In-use bandwidth for the mandatory channels.";
                        }

                        ///nokia-state/state/mcac/policy/bundle/operational-router-interface-data/optional-bw-use
                        leaf optional-bw-use {
                            type types-mcast-cac:bandwidth;
                            description "In-use bandwidth for the optional channels.";
                        }

                        ///nokia-state/state/mcac/policy/bundle/operational-router-interface-data/ports-down
                        leaf ports-down {
                            type uint32;
                            description "Number of ports down.";
                        }

                        ///nokia-state/state/mcac/policy/bundle/operational-router-interface-data/constraints-level
                        leaf constraints-level {
                            type types-mcast-cac:constraints-level;
                            description
                                "Current lag constraints bundle level id for the
                                 number of ports down";
                        }

                    } // list operational-router-interface-data

                    ///nokia-state/state/mcac/policy/bundle/operational-router-group-interface-data
                    list operational-router-group-interface-data {
                        key "router-instance application group-interface port encap-value";
                        description "Enter the operational-router-group-interface-data list instance";

                        ///nokia-state/state/mcac/policy/bundle/operational-router-group-interface-data/router-instance
                        leaf router-instance {
                            type types-sros:vrtr-id;
                            description ".";
                        }

                        ///nokia-state/state/mcac/policy/bundle/operational-router-group-interface-data/application
                        leaf application {
                            type types-mcast-cac:router-application;
                            description ".";
                        }

                        ///nokia-state/state/mcac/policy/bundle/operational-router-group-interface-data/group-interface
                        leaf group-interface {
                            type string {
                                length "0..32";
                            }
                            description ".";
                        }

                        ///nokia-state/state/mcac/policy/bundle/operational-router-group-interface-data/port
                        leaf port {
                            type types-sros:port;
                            description ".";
                        }

                        ///nokia-state/state/mcac/policy/bundle/operational-router-group-interface-data/encap-value
                        leaf encap-value {
                            type types-sros:encap-val;
                            description ".";
                        }

                        ///nokia-state/state/mcac/policy/bundle/operational-router-group-interface-data/number-of-active-channels
                        leaf number-of-active-channels {
                            type yang:counter32;
                            description "Number of active channels.";
                        }

                        ///nokia-state/state/mcac/policy/bundle/operational-router-group-interface-data/bandwidth
                        leaf bandwidth {
                            type types-mcast-cac:bandwidth;
                            description "maximum bandwidth allowed.";
                        }

                        ///nokia-state/state/mcac/policy/bundle/operational-router-group-interface-data/available-bw
                        leaf available-bw {
                            type types-mcast-cac:bandwidth;
                            description "Available bandwidth";
                        }

                        ///nokia-state/state/mcac/policy/bundle/operational-router-group-interface-data/available-mandatory-bw
                        leaf available-mandatory-bw {
                            type types-mcast-cac:bandwidth;
                            description "Available pre-reserved bandwidth for the mandatory channels.";
                        }

                        ///nokia-state/state/mcac/policy/bundle/operational-router-group-interface-data/mandatory-bw-use
                        leaf mandatory-bw-use {
                            type types-mcast-cac:bandwidth;
                            description "In-use bandwidth for the mandatory channels.";
                        }

                        ///nokia-state/state/mcac/policy/bundle/operational-router-group-interface-data/optional-bw-use
                        leaf optional-bw-use {
                            type types-mcast-cac:bandwidth;
                            description "In-use bandwidth for the optional channels.";
                        }

                        ///nokia-state/state/mcac/policy/bundle/operational-router-group-interface-data/ports-down
                        leaf ports-down {
                            type uint32;
                            description "Number of ports down.";
                        }

                        ///nokia-state/state/mcac/policy/bundle/operational-router-group-interface-data/constraints-level
                        leaf constraints-level {
                            type types-mcast-cac:constraints-level;
                            description
                                "Current lag constraints bundle level id for the
                                 number of ports down";
                        }

                    } // list operational-router-group-interface-data

                    ///nokia-state/state/mcac/policy/bundle/historical-router-access-information
                    list historical-router-access-information {
                        key "router-instance application interface group source";
                        description "Enter the historical-router-access-information list instance";

                        ///nokia-state/state/mcac/policy/bundle/historical-router-access-information/router-instance
                        leaf router-instance {
                            type types-sros:vrtr-id;
                            description ".";
                        }

                        ///nokia-state/state/mcac/policy/bundle/historical-router-access-information/application
                        leaf application {
                            type types-mcast-cac:router-application;
                            description ".";
                        }

                        ///nokia-state/state/mcac/policy/bundle/historical-router-access-information/interface
                        leaf interface {
                            type string {
                                length "0..32";
                            }
                            description ".";
                        }

                        ///nokia-state/state/mcac/policy/bundle/historical-router-access-information/group
                        leaf group {
                            type types-sros:ip-address;
                            description "Group address.";
                        }

                        ///nokia-state/state/mcac/policy/bundle/historical-router-access-information/source
                        leaf source {
                            type types-sros:ip-address;
                            description "Source address.";
                        }

                        ///nokia-state/state/mcac/policy/bundle/historical-router-access-information/action
                        leaf action {
                            type types-mcast-cac:policy-action;
                            description
                                "The action specified by the mcac policy for the application
                                 interface to act upon.";
                        }

                        ///nokia-state/state/mcac/policy/bundle/historical-router-access-information/reason
                        leaf reason {
                            type enumeration {
                                enum bundle-disabled                { value 1; }
                                enum bundle-no-available-bandwidth  { value 2; }
                                enum interface-no-available-bandwidth { value 3; }
                                enum no-channel-in-policy           { value 4; }
                                enum algorithm-passed               { value 5; }
                                enum user-no-available-bandwidth    { value 6; }
                                enum subscriber-no-mcac-policy      { value 7; }
                                enum interface-policy-no-available-bandwidth { value 8; }
                                enum low-memory                     { value 9; }
                            }
                            description
                                "The reason for the action specified by the mcac policy
                                 for the application interface to act upon.";
                        }

                        ///nokia-state/state/mcac/policy/bundle/historical-router-access-information/channel-type
                        leaf channel-type {
                            type types-mcast-cac:channel-type;
                            description
                                "The channel type configured at the mcac policy at the time of
                                 request from the application interface.";
                        }

                        ///nokia-state/state/mcac/policy/bundle/historical-router-access-information/channel-bandwidth
                        leaf channel-bandwidth {
                            type types-mcast-cac:bandwidth;
                            description
                                "The channel bandwidth configured at the mcac policy at the
                                 time of request from the application interface.";
                        }

                        ///nokia-state/state/mcac/policy/bundle/historical-router-access-information/bundle-available-bw
                        leaf bundle-available-bw {
                            type types-mcast-cac:bandwidth;
                            description
                                "The available bundle bandwidth after the requested channel was
                                 either accepted or discarded by the mcac policy.";
                        }

                        ///nokia-state/state/mcac/policy/bundle/historical-router-access-information/interface-available-bw
                        leaf interface-available-bw {
                            type types-mcast-cac:bandwidth;
                            description
                                "The available interface bandwidth after the requested channel was
                                 either accepted or discarded by the mcac policy.";
                        }

                        ///nokia-state/state/mcac/policy/bundle/historical-router-access-information/reapplied
                        leaf reapplied {
                            type boolean;
                            description
                                "The mcac policy was reapplied on the already
                                 accepted channel due lag constraints.";
                        }

                        ///nokia-state/state/mcac/policy/bundle/historical-router-access-information/apply-attempts
                        leaf apply-attempts {
                            type uint32;
                            description
                                "The number of times the mcac policy was applied for
                                 a particular channel entry by the application.";
                        }

                        ///nokia-state/state/mcac/policy/bundle/historical-router-access-information/time
                        leaf time {
                            type yang:date-and-time;
                            description
                                "The timestamp of the last time the mcac policy was
                                 applied for this channel entry.";
                        }

                    } // list historical-router-access-information

                    ///nokia-state/state/mcac/policy/bundle/operational-service-data
                    list operational-service-data {
                        key "service application port encap-value";
                        description "Enter the operational-service-data list instance";

                        ///nokia-state/state/mcac/policy/bundle/operational-service-data/service
                        leaf service {
                            type types-services:service-id;
                            description ".";
                        }

                        ///nokia-state/state/mcac/policy/bundle/operational-service-data/application
                        leaf application {
                            type types-mcast-cac:service-application;
                            description ".";
                        }

                        ///nokia-state/state/mcac/policy/bundle/operational-service-data/port
                        leaf port {
                            type types-sros:port;
                            description ".";
                        }

                        ///nokia-state/state/mcac/policy/bundle/operational-service-data/encap-value
                        leaf encap-value {
                            type types-sros:encap-val;
                            description ".";
                        }

                        ///nokia-state/state/mcac/policy/bundle/operational-service-data/number-of-active-channels
                        leaf number-of-active-channels {
                            type yang:counter32;
                            description "Number of active channels.";
                        }

                        ///nokia-state/state/mcac/policy/bundle/operational-service-data/bandwidth
                        leaf bandwidth {
                            type types-mcast-cac:bandwidth;
                            description "maximum bandwidth allowed.";
                        }

                        ///nokia-state/state/mcac/policy/bundle/operational-service-data/available-bw
                        leaf available-bw {
                            type types-mcast-cac:bandwidth;
                            description "Available bandwidth";
                        }

                        ///nokia-state/state/mcac/policy/bundle/operational-service-data/available-mandatory-bw
                        leaf available-mandatory-bw {
                            type types-mcast-cac:bandwidth;
                            description "Available pre-reserved bandwidth for the mandatory channels.";
                        }

                        ///nokia-state/state/mcac/policy/bundle/operational-service-data/mandatory-bw-use
                        leaf mandatory-bw-use {
                            type types-mcast-cac:bandwidth;
                            description "In-use bandwidth for the mandatory channels.";
                        }

                        ///nokia-state/state/mcac/policy/bundle/operational-service-data/optional-bw-use
                        leaf optional-bw-use {
                            type types-mcast-cac:bandwidth;
                            description "In-use bandwidth for the optional channels.";
                        }

                        ///nokia-state/state/mcac/policy/bundle/operational-service-data/ports-down
                        leaf ports-down {
                            type uint32;
                            description "Number of ports down.";
                        }

                        ///nokia-state/state/mcac/policy/bundle/operational-service-data/constraints-level
                        leaf constraints-level {
                            type types-mcast-cac:constraints-level;
                            description
                                "Current lag constraints bundle level id for the
                                 number of ports down";
                        }

                    } // list operational-service-data

                    ///nokia-state/state/mcac/policy/bundle/historical-service-access-information
                    list historical-service-access-information {
                        key "service application port encap-value group source";
                        description "Enter the historical-service-access-information list instance";

                        ///nokia-state/state/mcac/policy/bundle/historical-service-access-information/service
                        leaf service {
                            type types-services:service-id;
                            description ".";
                        }

                        ///nokia-state/state/mcac/policy/bundle/historical-service-access-information/application
                        leaf application {
                            type types-mcast-cac:service-application;
                            description ".";
                        }

                        ///nokia-state/state/mcac/policy/bundle/historical-service-access-information/port
                        leaf port {
                            type types-sros:port;
                            description ".";
                        }

                        ///nokia-state/state/mcac/policy/bundle/historical-service-access-information/encap-value
                        leaf encap-value {
                            type types-sros:encap-val;
                            description ".";
                        }

                        ///nokia-state/state/mcac/policy/bundle/historical-service-access-information/group
                        leaf group {
                            type types-sros:ip-address;
                            description "Group address.";
                        }

                        ///nokia-state/state/mcac/policy/bundle/historical-service-access-information/source
                        leaf source {
                            type types-sros:ip-address;
                            description "Source address.";
                        }

                        ///nokia-state/state/mcac/policy/bundle/historical-service-access-information/action
                        leaf action {
                            type types-mcast-cac:policy-action;
                            description
                                "The action specified by the mcac policy for the application
                                 interface to act upon.";
                        }

                        ///nokia-state/state/mcac/policy/bundle/historical-service-access-information/reason
                        leaf reason {
                            type enumeration {
                                enum bundle-disabled                { value 1; }
                                enum bundle-no-available-bandwidth  { value 2; }
                                enum interface-no-available-bandwidth { value 3; }
                                enum no-channel-in-policy           { value 4; }
                                enum algorithm-passed               { value 5; }
                                enum user-no-available-bandwidth    { value 6; }
                                enum subscriber-no-mcac-policy      { value 7; }
                                enum interface-policy-no-available-bandwidth { value 8; }
                                enum low-memory                     { value 9; }
                            }
                            description
                                "The reason for the action specified by the mcac policy
                                 for the application interface to act upon.";
                        }

                        ///nokia-state/state/mcac/policy/bundle/historical-service-access-information/channel-type
                        leaf channel-type {
                            type types-mcast-cac:channel-type;
                            description
                                "The channel type configured at the mcac policy at the time of
                                 request from the application interface.";
                        }

                        ///nokia-state/state/mcac/policy/bundle/historical-service-access-information/channel-bandwidth
                        leaf channel-bandwidth {
                            type types-mcast-cac:bandwidth;
                            description
                                "The channel bandwidth configured at the mcac policy at the
                                 time of request from the application interface.";
                        }

                        ///nokia-state/state/mcac/policy/bundle/historical-service-access-information/bundle-available-bw
                        leaf bundle-available-bw {
                            type types-mcast-cac:bandwidth;
                            description
                                "The available bundle bandwidth after the requested channel was
                                 either accepted or discarded by the mcac policy.";
                        }

                        ///nokia-state/state/mcac/policy/bundle/historical-service-access-information/interface-available-bw
                        leaf interface-available-bw {
                            type types-mcast-cac:bandwidth;
                            description
                                "The available interface bandwidth after the requested channel was
                                 either accepted or discarded by the mcac policy.";
                        }

                        ///nokia-state/state/mcac/policy/bundle/historical-service-access-information/reapplied
                        leaf reapplied {
                            type boolean;
                            description
                                "The mcac policy was reapplied on the already
                                 accepted channel due lag constraints.";
                        }

                        ///nokia-state/state/mcac/policy/bundle/historical-service-access-information/apply-attempts
                        leaf apply-attempts {
                            type uint32;
                            description
                                "The number of times the mcac policy was applied for
                                 a particular channel entry by the application.";
                        }

                        ///nokia-state/state/mcac/policy/bundle/historical-service-access-information/time
                        leaf time {
                            type yang:date-and-time;
                            description
                                "The timestamp of the last time the mcac policy was
                                 applied for this channel entry.";
                        }

                    } // list historical-service-access-information

                } // list bundle

            } // list policy

        } // container mcac

    } // grouping state-mcast-cac-mcac

}
