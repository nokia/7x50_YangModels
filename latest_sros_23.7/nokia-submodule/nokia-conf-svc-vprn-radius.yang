submodule nokia-conf-svc-vprn-radius {

    yang-version "1.1";

    belongs-to nokia-conf { prefix "conf"; }

    import nokia-sros-yang-extensions     { prefix "sros-ext"; }
    import nokia-types-radius             { prefix "types-radius"; }
    import nokia-types-sros               { prefix "types-sros"; }

    include nokia-conf-groups;
    include nokia-conf-isa;
    include nokia-conf-python;
    include nokia-conf-service;
    include nokia-conf-svc-vprn;

    sros-ext:sros-major-release "rel23";
    organization "Nokia";
    contact
        "Nokia SR OS Support
         Web: <http://www.nokia.com>";
    description
        "Nokia YANG Data model to configure RADIUS on SR OS based routers.

         Copyright 2016 Nokia. All rights reserved. Reproduction of this document
         is authorized on the condition that the foregoing copyright notice is included.

         This nokia-conf-svc-vprn-radius YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping conf-svc-vprn-radius {
        ///nokia-conf/configure/service/vprn/radius
        container radius {
            description "Enable the radius context";

            ///nokia-conf/configure/service/vprn/radius/apply-groups
            leaf-list apply-groups {
                type leafref {
                    path "../../../../groups/group/name";
                }
                max-elements 8;
                ordered-by user;
                description "Apply a configuration group at this level";
            }

            ///nokia-conf/configure/service/vprn/radius/apply-groups-exclude
            leaf-list apply-groups-exclude {
                type leafref {
                    path "../../../../groups/group/name";
                }
                max-elements 8;
                ordered-by user;
                description "Exclude a configuration group at this level";
            }

            ///nokia-conf/configure/service/vprn/radius/server
            list server {
                key "name";
                max-elements 64;
                description "Enter the server list instance";

                ///nokia-conf/configure/service/vprn/radius/server/name
                leaf name {
                    type types-sros:named-item;
                    description "External RADIUS server name";
                }

                ///nokia-conf/configure/service/vprn/radius/server/description
                leaf description {
                    type types-sros:description;
                    description "Text description";
                }

                ///nokia-conf/configure/service/vprn/radius/server/address
                leaf address {
                    type types-sros:ip-unicast-address;
                    mandatory true;
                    description "IP address of the RADIUS server";
                }

                ///nokia-conf/configure/service/vprn/radius/server/secret
                leaf secret {
                    type types-sros:encrypted-leaf {
                        length "1..115";
                    }
                    mandatory true;
                    description "Secret key associated with this RADIUS server";
                }

                ///nokia-conf/configure/service/vprn/radius/server/accept-coa
                leaf accept-coa {
                    type boolean;
                    default "false";
                    description "Process Change of Authorization (CoA) messages";
                }

                ///nokia-conf/configure/service/vprn/radius/server/acct-port
                leaf acct-port {
                    type types-sros:tcp-udp-port-non-zero;
                    default "1813";
                    description "UDP port number of the RADIUS for accounting events";
                }

                ///nokia-conf/configure/service/vprn/radius/server/auth-port
                leaf auth-port {
                    type types-sros:tcp-udp-port-non-zero;
                    default "1812";
                    description "UDP port number of the RADIUS to be used as match criteria";
                }

                ///nokia-conf/configure/service/vprn/radius/server/pending-requests-limit
                leaf pending-requests-limit {
                    type uint32 {
                        range "1..4096";
                    }
                    default "4096";
                    description "Limit of the number for pending RADIUS requests";
                }

                ///nokia-conf/configure/service/vprn/radius/server/python-policy
                leaf python-policy {
                    type leafref {
                        path "../../../../../python/python-policy/name";
                    }
                    description "Python script policy to modify CoA messages";
                }

                ///nokia-conf/configure/service/vprn/radius/server/apply-groups
                leaf-list apply-groups {
                    type leafref {
                        path "../../../../../groups/group/name";
                    }
                    max-elements 8;
                    ordered-by user;
                    description "Apply a configuration group at this level";
                }

                ///nokia-conf/configure/service/vprn/radius/server/apply-groups-exclude
                leaf-list apply-groups-exclude {
                    type leafref {
                        path "../../../../../groups/group/name";
                    }
                    max-elements 8;
                    ordered-by user;
                    description "Exclude a configuration group at this level";
                }

            } // list server

            ///nokia-conf/configure/service/vprn/radius/proxy
            list proxy {
                key "name";
                max-elements 8;
                description "Enter the proxy list instance";

                ///nokia-conf/configure/service/vprn/radius/proxy/name
                leaf name {
                    type types-sros:named-item;
                    description "RADIUS proxy name";
                }

                ///nokia-conf/configure/service/vprn/radius/proxy/admin-state
                leaf admin-state {
                    type types-sros:admin-state;
                    default "disable";
                    description "Administrative state of RADIUS proxy";
                }

                ///nokia-conf/configure/service/vprn/radius/proxy/description
                leaf description {
                    type types-sros:description;
                    description "Text description";
                }

                ///nokia-conf/configure/service/vprn/radius/proxy/purpose
                leaf purpose {
                    type enumeration {
                        enum accounting                     { value 1; }
                        enum authentication                 { value 2; }
                        enum accounting-authentication      { value 3; }
                    }
                    sros-ext:immutable;
                    mandatory true;
                    description "Purpose of the RADIUS proxy";
                }

                ///nokia-conf/configure/service/vprn/radius/proxy/wlan-gw-group
                leaf wlan-gw-group {
                    type leafref {
                        path "../../../../../isa/wlan-gw-group/id";
                    }
                    sros-ext:immutable;
                    description "ISA WLAN gateway group";
                }

                ///nokia-conf/configure/service/vprn/radius/proxy/secret
                leaf secret {
                    type types-sros:encrypted-leaf {
                        length "1..115";
                    }
                    description "Format of the secret key to access the RADIUS proxy server";
                }

                ///nokia-conf/configure/service/vprn/radius/proxy/send-accounting-response
                leaf send-accounting-response {
                    type boolean;
                    default "false";
                    description "Allow RADIUS proxy server to respond to Accounting-Response messages";
                }

                ///nokia-conf/configure/service/vprn/radius/proxy/python-policy
                leaf python-policy {
                    type leafref {
                        path "../../../../../python/python-policy/name";
                    }
                    description "Python policy";
                }

                ///nokia-conf/configure/service/vprn/radius/proxy/apply-groups
                leaf-list apply-groups {
                    type leafref {
                        path "../../../../../groups/group/name";
                    }
                    max-elements 8;
                    ordered-by user;
                    description "Apply a configuration group at this level";
                }

                ///nokia-conf/configure/service/vprn/radius/proxy/apply-groups-exclude
                leaf-list apply-groups-exclude {
                    type leafref {
                        path "../../../../../groups/group/name";
                    }
                    max-elements 8;
                    ordered-by user;
                    description "Exclude a configuration group at this level";
                }

                ///nokia-conf/configure/service/vprn/radius/proxy/load-balance-key
                container load-balance-key {
                    description "Enter the load-balance-key context";

                    ///nokia-conf/configure/service/vprn/radius/proxy/load-balance-key/load-balance-key
                    choice load-balance-key {
                        ///nokia-conf/configure/service/vprn/radius/proxy/load-balance-key/load-balance-key/source-ip-udp
                        case source-ip-udp {

                            ///nokia-conf/configure/service/vprn/radius/proxy/load-balance-key/load-balance-key/source-ip-udp/source-ip-udp
                            leaf source-ip-udp {
                                type empty;
                                description "Key to consist of the source IP address and source UDP port of the RADIUS message";
                            }

                        }
                        ///nokia-conf/configure/service/vprn/radius/proxy/load-balance-key/load-balance-key/attributes
                        case attributes {

                            ///nokia-conf/configure/service/vprn/radius/proxy/load-balance-key/load-balance-key/attributes/attribute-1
                            container attribute-1 {
                                description "Enter the attribute-1 context";

                                ///nokia-conf/configure/service/vprn/radius/proxy/load-balance-key/load-balance-key/attributes/attribute-1/type
                                leaf type {
                                    type types-radius:radius-attribute-type;
                                    description "Attribute type to cache for this RADIUS Proxy server";
                                }

                                ///nokia-conf/configure/service/vprn/radius/proxy/load-balance-key/load-balance-key/attributes/attribute-1/vendor
                                leaf vendor {
                                    type types-radius:radius-vendor-id;
                                    description "Vendor-Id attribute";
                                }

                            } // container attribute-1

                            ///nokia-conf/configure/service/vprn/radius/proxy/load-balance-key/load-balance-key/attributes/attribute-2
                            container attribute-2 {
                                description "Enter the attribute-2 context";

                                ///nokia-conf/configure/service/vprn/radius/proxy/load-balance-key/load-balance-key/attributes/attribute-2/type
                                leaf type {
                                    type types-radius:radius-attribute-type;
                                    description "Attribute type to cache for this RADIUS Proxy server";
                                }

                                ///nokia-conf/configure/service/vprn/radius/proxy/load-balance-key/load-balance-key/attributes/attribute-2/vendor
                                leaf vendor {
                                    type types-radius:radius-vendor-id;
                                    description "Vendor-Id attribute";
                                }

                            } // container attribute-2

                            ///nokia-conf/configure/service/vprn/radius/proxy/load-balance-key/load-balance-key/attributes/attribute-3
                            container attribute-3 {
                                description "Enter the attribute-3 context";

                                ///nokia-conf/configure/service/vprn/radius/proxy/load-balance-key/load-balance-key/attributes/attribute-3/type
                                leaf type {
                                    type types-radius:radius-attribute-type;
                                    description "Attribute type to cache for this RADIUS Proxy server";
                                }

                                ///nokia-conf/configure/service/vprn/radius/proxy/load-balance-key/load-balance-key/attributes/attribute-3/vendor
                                leaf vendor {
                                    type types-radius:radius-vendor-id;
                                    description "Vendor-Id attribute";
                                }

                            } // container attribute-3

                            ///nokia-conf/configure/service/vprn/radius/proxy/load-balance-key/load-balance-key/attributes/attribute-4
                            container attribute-4 {
                                description "Enter the attribute-4 context";

                                ///nokia-conf/configure/service/vprn/radius/proxy/load-balance-key/load-balance-key/attributes/attribute-4/type
                                leaf type {
                                    type types-radius:radius-attribute-type;
                                    description "Attribute type to cache for this RADIUS Proxy server";
                                }

                                ///nokia-conf/configure/service/vprn/radius/proxy/load-balance-key/load-balance-key/attributes/attribute-4/vendor
                                leaf vendor {
                                    type types-radius:radius-vendor-id;
                                    description "Vendor-Id attribute";
                                }

                            } // container attribute-4

                            ///nokia-conf/configure/service/vprn/radius/proxy/load-balance-key/load-balance-key/attributes/attribute-5
                            container attribute-5 {
                                description "Enter the attribute-5 context";

                                ///nokia-conf/configure/service/vprn/radius/proxy/load-balance-key/load-balance-key/attributes/attribute-5/type
                                leaf type {
                                    type types-radius:radius-attribute-type;
                                    description "Attribute type to cache for this RADIUS Proxy server";
                                }

                                ///nokia-conf/configure/service/vprn/radius/proxy/load-balance-key/load-balance-key/attributes/attribute-5/vendor
                                leaf vendor {
                                    type types-radius:radius-vendor-id;
                                    description "Vendor-Id attribute";
                                }

                            } // container attribute-5

                        }
                    }
                } // container load-balance-key

                ///nokia-conf/configure/service/vprn/radius/proxy/cache
                container cache {
                    description "Enter the cache context";

                    ///nokia-conf/configure/service/vprn/radius/proxy/cache/admin-state
                    leaf admin-state {
                        type types-sros:admin-state;
                        default "disable";
                        description "Administrative state of the RADIUS proxy cache";
                    }

                    ///nokia-conf/configure/service/vprn/radius/proxy/cache/track-delete-hold-time
                    leaf track-delete-hold-time {
                        type types-sros:time-duration {
                            range "0..6000";
                        }
                        default "0";
                        description "Delete hold time";
                    }

                    ///nokia-conf/configure/service/vprn/radius/proxy/cache/timeout
                    leaf timeout {
                        type types-sros:time-duration {
                            range "60..3600";
                        }
                        default "300";
                        description "Idle timeout value";
                    }

                    ///nokia-conf/configure/service/vprn/radius/proxy/cache/key
                    container key {
                        presence "Enable the key context";
                        description "Enable the key context";

                        ///nokia-conf/configure/service/vprn/radius/proxy/cache/key/packet-type
                        leaf packet-type {
                            type enumeration {
                                enum access-request                 { value 1; }
                                enum access-accept                  { value 2; }
                            }
                            mandatory true;
                            description "Packet type of the RADIUS messages";
                        }

                        ///nokia-conf/configure/service/vprn/radius/proxy/cache/key/attribute-type
                        leaf attribute-type {
                            type types-radius:radius-attribute-type;
                            mandatory true;
                            description "RADIUS attribute type to cache for this RADIUS proxy server";
                        }

                        ///nokia-conf/configure/service/vprn/radius/proxy/cache/key/vendor
                        leaf vendor {
                            type types-radius:radius-vendor-id;
                            description "RADIUS Vendor ID";
                        }

                    } // container key

                    ///nokia-conf/configure/service/vprn/radius/proxy/cache/track-accounting
                    container track-accounting {
                        description "Enter the track-accounting context";

                        ///nokia-conf/configure/service/vprn/radius/proxy/cache/track-accounting/start
                        leaf start {
                            type boolean;
                            default "false";
                            description "Update host with client that generated accounting-start";
                        }

                        ///nokia-conf/configure/service/vprn/radius/proxy/cache/track-accounting/stop
                        leaf stop {
                            type boolean;
                            default "false";
                            description "Remove ESM host and forward accounting-stop packet";
                        }

                        ///nokia-conf/configure/service/vprn/radius/proxy/cache/track-accounting/interim-update
                        leaf interim-update {
                            type boolean;
                            default "false";
                            description "Update the ESM host with the RADIUS client that generated the interim update";
                        }

                        ///nokia-conf/configure/service/vprn/radius/proxy/cache/track-accounting/accounting-on
                        leaf accounting-on {
                            when "not(../../../wlan-gw-group)" {
                                description "disabled when WLAN Gateway ISA group ID is configured in proxy";
                            }
                            type boolean;
                            default "false";
                            description "Remove all ESM hosts associated with the RADIUS client";
                        }

                        ///nokia-conf/configure/service/vprn/radius/proxy/cache/track-accounting/accounting-off
                        leaf accounting-off {
                            when "not(../../../wlan-gw-group)" {
                                description "disabled when WLAN Gateway ISA group ID is configured in proxy";
                            }
                            type boolean;
                            default "false";
                            description "Remove all ESM hosts associated with the RADIUS client";
                        }

                    } // container track-accounting

                    ///nokia-conf/configure/service/vprn/radius/proxy/cache/track-authentication
                    container track-authentication {
                        description "Enter the track-authentication context";

                        ///nokia-conf/configure/service/vprn/radius/proxy/cache/track-authentication/accept
                        leaf accept {
                            type boolean;
                            default "true";
                            description "Track Access-Accept message for mobility";
                        }

                    } // container track-authentication

                } // container cache

                ///nokia-conf/configure/service/vprn/radius/proxy/attribute-matching
                container attribute-matching {
                    description "Enter the attribute-matching context";

                    ///nokia-conf/configure/service/vprn/radius/proxy/attribute-matching/type
                    leaf type {
                        type types-radius:radius-attribute-type;
                        description "Matching attribute type to RADIUS server policy";
                    }

                    ///nokia-conf/configure/service/vprn/radius/proxy/attribute-matching/vendor
                    leaf vendor {
                        type types-radius:radius-vendor-id;
                        description "Matching Vendor ID to RADIUS server policy";
                    }

                    ///nokia-conf/configure/service/vprn/radius/proxy/attribute-matching/entry
                    list entry {
                        key "index";
                        description "Enter the entry list instance";

                        ///nokia-conf/configure/service/vprn/radius/proxy/attribute-matching/entry/index
                        leaf index {
                            type uint32 {
                                range "1..32";
                            }
                            description "Index of this entry";
                        }

                        ///nokia-conf/configure/service/vprn/radius/proxy/attribute-matching/entry/prefix-string
                        leaf prefix-string {
                            type types-sros:display-string {
                                length "1..128";
                            }
                            description "Prefix string";
                        }

                        ///nokia-conf/configure/service/vprn/radius/proxy/attribute-matching/entry/suffix-string
                        leaf suffix-string {
                            type types-sros:display-string {
                                length "1..128";
                            }
                            description "Prefix string";
                        }

                        ///nokia-conf/configure/service/vprn/radius/proxy/attribute-matching/entry/accounting-server-policy
                        leaf accounting-server-policy {
                            type types-sros:named-item;
                            description "Accounting server policy";
                        }

                        ///nokia-conf/configure/service/vprn/radius/proxy/attribute-matching/entry/authentication-server-policy
                        leaf authentication-server-policy {
                            type types-sros:named-item;
                            description "Authentication server policy";
                        }

                        ///nokia-conf/configure/service/vprn/radius/proxy/attribute-matching/entry/apply-groups
                        leaf-list apply-groups {
                            type leafref {
                                path "../../../../../../../groups/group/name";
                            }
                            max-elements 8;
                            ordered-by user;
                            description "Apply a configuration group at this level";
                        }

                        ///nokia-conf/configure/service/vprn/radius/proxy/attribute-matching/entry/apply-groups-exclude
                        leaf-list apply-groups-exclude {
                            type leafref {
                                path "../../../../../../../groups/group/name";
                            }
                            max-elements 8;
                            ordered-by user;
                            description "Exclude a configuration group at this level";
                        }

                    } // list entry

                } // container attribute-matching

                ///nokia-conf/configure/service/vprn/radius/proxy/wlan-gw
                container wlan-gw {
                    when "../wlan-gw-group" {
                        description "disabled when no ISA group ID is configured in proxy";
                    }
                    description "Enter the wlan-gw context";

                    ///nokia-conf/configure/service/vprn/radius/proxy/wlan-gw/address
                    leaf address {
                        type types-sros:ipv4-unicast-address;
                        description "IPv4 address of the distributed RADIUS proxy server";
                    }

                    ///nokia-conf/configure/service/vprn/radius/proxy/wlan-gw/ipv6-address
                    leaf ipv6-address {
                        type types-sros:ipv6-unicast-without-local-address;
                        description "IPv6 address of the distributed RADIUS proxy server";
                    }

                    ///nokia-conf/configure/service/vprn/radius/proxy/wlan-gw/apply-groups
                    leaf-list apply-groups {
                        type leafref {
                            path "../../../../../../groups/group/name";
                        }
                        max-elements 8;
                        ordered-by user;
                        description "Apply a configuration group at this level";
                    }

                    ///nokia-conf/configure/service/vprn/radius/proxy/wlan-gw/apply-groups-exclude
                    leaf-list apply-groups-exclude {
                        type leafref {
                            path "../../../../../../groups/group/name";
                        }
                        max-elements 8;
                        ordered-by user;
                        description "Exclude a configuration group at this level";
                    }

                } // container wlan-gw

                ///nokia-conf/configure/service/vprn/radius/proxy/defaults
                container defaults {
                    description "Enter the defaults context";

                    ///nokia-conf/configure/service/vprn/radius/proxy/defaults/authentication-server-policy
                    leaf authentication-server-policy {
                        type types-sros:named-item;
                        description "Default authentication RADIUS server policy";
                    }

                    ///nokia-conf/configure/service/vprn/radius/proxy/defaults/accounting-server-policy
                    leaf accounting-server-policy {
                        type types-sros:named-item;
                        description "Default accounting RADIUS server policy";
                    }

                } // container defaults

                ///nokia-conf/configure/service/vprn/radius/proxy/interface
                list interface {
                    when "not(../wlan-gw-group)" {
                        description "disabled when WLAN Gateway ISA group ID is configured in proxy";
                    }
                    key "interface-name";
                    description "Add a list entry for interface";

                    ///nokia-conf/configure/service/vprn/radius/proxy/interface/interface-name
                    leaf interface-name {
                        type leafref {
                            path "../../../../interface/interface-name";
                        }
                        description "IP interface name";
                    }

                } // list interface

            } // list proxy

        } // container radius

    } // grouping conf-svc-vprn-radius

}
