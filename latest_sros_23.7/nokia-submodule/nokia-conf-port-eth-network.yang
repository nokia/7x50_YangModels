submodule nokia-conf-port-eth-network {

    yang-version "1.1";

    belongs-to nokia-conf { prefix "conf"; }

    import nokia-sros-yang-extensions     { prefix "sros-ext"; }
    import nokia-types-qos                { prefix "types-qos"; }
    import nokia-types-sros               { prefix "types-sros"; }

    include nokia-conf-groups;
    include nokia-conf-log;
    include nokia-conf-qos;

    sros-ext:sros-major-release "rel23";
    organization "Nokia";
    contact
        "Nokia SR OS Support
         Web: <http://www.nokia.com>";
    description
        "Nokia YANG Data model to configure network capabilities for ethernet ports on SR OS based routers.

         Copyright 2016 Nokia. All rights reserved. Reproduction of this document
         is authorized on the condition that the foregoing copyright notice is included.

         This nokia-conf-port-eth-network YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-15";

    grouping conf-port-eth-network {
        ///nokia-conf/configure/port/ethernet/network
        container network {
            description "Enable the network context";

            ///nokia-conf/configure/port/ethernet/network/accounting-policy
            leaf accounting-policy {
                type leafref {
                    path "../../../../log/accounting-policy/policy-id";
                }
                description "Accounting policy that applies to the network port";
            }

            ///nokia-conf/configure/port/ethernet/network/collect-stats
            leaf collect-stats {
                type boolean;
                default "false";
                description "Collect accounting and statistical data";
            }

            ///nokia-conf/configure/port/ethernet/network/apply-groups
            leaf-list apply-groups {
                type leafref {
                    path "../../../../groups/group/name";
                }
                max-elements 8;
                ordered-by user;
                description "Apply a configuration group at this level";
            }

            ///nokia-conf/configure/port/ethernet/network/apply-groups-exclude
            leaf-list apply-groups-exclude {
                type leafref {
                    path "../../../../groups/group/name";
                }
                max-elements 8;
                ordered-by user;
                description "Exclude a configuration group at this level";
            }

            ///nokia-conf/configure/port/ethernet/network/egress
            container egress {
                description "Enter the egress context";

                ///nokia-conf/configure/port/ethernet/network/egress/queue-policy
                leaf queue-policy {
                    type leafref {
                        path "../../../../../qos/network-queue/network-queue-policy";
                    }
                    description "Network queue policy";
                }

                ///nokia-conf/configure/port/ethernet/network/egress/queue-group
                list queue-group {
                    key "queue-group-name instance-id";
                    description "Enter the queue-group list instance";

                    ///nokia-conf/configure/port/ethernet/network/egress/queue-group/queue-group-name
                    leaf queue-group-name {
                        type leafref {
                            path "../../../../../../qos/queue-group-templates/egress/queue-group/egress-queue-group-name";
                        }
                        description "Queue group name";
                    }

                    ///nokia-conf/configure/port/ethernet/network/egress/queue-group/instance-id
                    leaf instance-id {
                        type uint16 {
                            range "1..65535";
                        }
                        description "Instance ID for the egress queue group";
                    }

                    ///nokia-conf/configure/port/ethernet/network/egress/queue-group/accounting-policy
                    leaf accounting-policy {
                        type leafref {
                            path "../../../../../../log/accounting-policy/policy-id";
                        }
                        description "Accounting policy for the Ethernet port";
                    }

                    ///nokia-conf/configure/port/ethernet/network/egress/queue-group/collect-stats
                    leaf collect-stats {
                        type boolean;
                        default "false";
                        description "Collect accounting and statistical data";
                    }

                    ///nokia-conf/configure/port/ethernet/network/egress/queue-group/description
                    leaf description {
                        type types-sros:description;
                        description "Text description";
                    }

                    ///nokia-conf/configure/port/ethernet/network/egress/queue-group/hs-turbo
                    leaf hs-turbo {
                        type boolean;
                        default "false";
                        description "Enable HS turbo queues for higher throughput";
                    }

                    ///nokia-conf/configure/port/ethernet/network/egress/queue-group/policer-control-policy
                    leaf policer-control-policy {
                        type leafref {
                            path "../../../../../../qos/policer-control-policy/policer-control-policy-name";
                        }
                        description "Policer control policy for the QoS egress queue group";
                    }

                    ///nokia-conf/configure/port/ethernet/network/egress/queue-group/apply-groups
                    leaf-list apply-groups {
                        type leafref {
                            path "../../../../../../groups/group/name";
                        }
                        max-elements 8;
                        ordered-by user;
                        description "Apply a configuration group at this level";
                    }

                    ///nokia-conf/configure/port/ethernet/network/egress/queue-group/apply-groups-exclude
                    leaf-list apply-groups-exclude {
                        type leafref {
                            path "../../../../../../groups/group/name";
                        }
                        max-elements 8;
                        ordered-by user;
                        description "Exclude a configuration group at this level";
                    }

                    ///nokia-conf/configure/port/ethernet/network/egress/queue-group/aggregate-rate
                    container aggregate-rate {
                        description "Enter the aggregate-rate context";

                        ///nokia-conf/configure/port/ethernet/network/egress/queue-group/aggregate-rate/queue-frame-based-accounting
                        leaf queue-frame-based-accounting {
                            type boolean;
                            default "false";
                            description "Enable frame-based accounting on policers and queues";
                        }

                        ///nokia-conf/configure/port/ethernet/network/egress/queue-group/aggregate-rate/limit-unused-bandwidth
                        leaf limit-unused-bandwidth {
                            type boolean;
                            default "false";
                            description "Control unused bandwidth";
                        }

                        ///nokia-conf/configure/port/ethernet/network/egress/queue-group/aggregate-rate/rate
                        leaf rate {
                            type union {
                                type uint32 {
                                    range "1..3200000000";
                                }
                                type enumeration {
                                    enum max                            { value -1; }
                                }
                            }
                            units "kilobps";
                            default "max";
                            description "Aggregate rate for all queues";
                        }

                    } // container aggregate-rate

                    ///nokia-conf/configure/port/ethernet/network/egress/queue-group/queue-overrides
                    container queue-overrides {
                        description "Enter the queue-overrides context";

                        ///nokia-conf/configure/port/ethernet/network/egress/queue-group/queue-overrides/queue
                        list queue {
                            key "queue-id";
                            description "Enter the queue list instance";

                            ///nokia-conf/configure/port/ethernet/network/egress/queue-group/queue-overrides/queue/queue-id
                            leaf queue-id {
                                type leafref {
                                    path "../../../../../../../../qos/queue-group-templates/egress/queue-group[egress-queue-group-name=current()/../../../queue-group-name]/queue/queue-id";
                                }
                                description "Queue ID";
                            }

                            ///nokia-conf/configure/port/ethernet/network/egress/queue-group/queue-overrides/queue/cbs
                            leaf cbs {
                                type types-qos:burst-size-override;
                                units "kilobytes";
                                description "CBS for the template queue";
                            }

                            ///nokia-conf/configure/port/ethernet/network/egress/queue-group/queue-overrides/queue/mbs
                            leaf mbs {
                                type types-qos:queue-burst-size-override;
                                units "bytes";
                                description "MBS for the template queue";
                            }

                            ///nokia-conf/configure/port/ethernet/network/egress/queue-group/queue-overrides/queue/monitor-depth
                            leaf monitor-depth {
                                status obsolete;
                                type boolean;
                                default "false";
                                description "Enable queue depth monitoring";
                            }

                            ///nokia-conf/configure/port/ethernet/network/egress/queue-group/queue-overrides/queue/apply-groups
                            leaf-list apply-groups {
                                type leafref {
                                    path "../../../../../../../../groups/group/name";
                                }
                                max-elements 8;
                                ordered-by user;
                                description "Apply a configuration group at this level";
                            }

                            ///nokia-conf/configure/port/ethernet/network/egress/queue-group/queue-overrides/queue/apply-groups-exclude
                            leaf-list apply-groups-exclude {
                                type leafref {
                                    path "../../../../../../../../groups/group/name";
                                }
                                max-elements 8;
                                ordered-by user;
                                description "Exclude a configuration group at this level";
                            }

                            ///nokia-conf/configure/port/ethernet/network/egress/queue-group/queue-overrides/queue/queue-override-rate
                            choice queue-override-rate {
                                default "rate";
                                ///nokia-conf/configure/port/ethernet/network/egress/queue-group/queue-overrides/queue/queue-override-rate/percent-rate
                                case percent-rate {

                                    ///nokia-conf/configure/port/ethernet/network/egress/queue-group/queue-overrides/queue/queue-override-rate/percent-rate/percent-rate
                                    container percent-rate {
                                        description "Enter the percent-rate context";

                                        ///nokia-conf/configure/port/ethernet/network/egress/queue-group/queue-overrides/queue/queue-override-rate/percent-rate/percent-rate/cir
                                        leaf cir {
                                            type types-qos:cir-percent-override;
                                            units "percent";
                                            description "CIR for the queue";
                                        }

                                        ///nokia-conf/configure/port/ethernet/network/egress/queue-group/queue-overrides/queue/queue-override-rate/percent-rate/percent-rate/pir
                                        leaf pir {
                                            type types-qos:pir-percent-override;
                                            units "percent";
                                            description "PIR for the queue";
                                        }

                                    } // container percent-rate

                                }
                                ///nokia-conf/configure/port/ethernet/network/egress/queue-group/queue-overrides/queue/queue-override-rate/rate
                                case rate {

                                    ///nokia-conf/configure/port/ethernet/network/egress/queue-group/queue-overrides/queue/queue-override-rate/rate/rate
                                    container rate {
                                        description "Enter the rate context";

                                        ///nokia-conf/configure/port/ethernet/network/egress/queue-group/queue-overrides/queue/queue-override-rate/rate/rate/cir
                                        leaf cir {
                                            type types-qos:queue-cir-rate-override;
                                            units "kilobps";
                                            description "CIR for the queue";
                                        }

                                        ///nokia-conf/configure/port/ethernet/network/egress/queue-group/queue-overrides/queue/queue-override-rate/rate/rate/pir
                                        leaf pir {
                                            type types-qos:queue-pir-rate-override;
                                            units "kilobps";
                                            description "PIR for the queue";
                                        }

                                    } // container rate

                                }
                            }
                            ///nokia-conf/configure/port/ethernet/network/egress/queue-group/queue-overrides/queue/adaptation-rule
                            container adaptation-rule {
                                description "Enter the adaptation-rule context";

                                ///nokia-conf/configure/port/ethernet/network/egress/queue-group/queue-overrides/queue/adaptation-rule/cir
                                leaf cir {
                                    type types-qos:adaptation-rule-override;
                                    description "Constraint used when deriving the operational CIR value";
                                }

                                ///nokia-conf/configure/port/ethernet/network/egress/queue-group/queue-overrides/queue/adaptation-rule/pir
                                leaf pir {
                                    type types-qos:adaptation-rule-override;
                                    description "Constraint used when deriving the operational PIR value";
                                }

                            } // container adaptation-rule

                            ///nokia-conf/configure/port/ethernet/network/egress/queue-group/queue-overrides/queue/drop-tail
                            container drop-tail {
                                description "Enter the drop-tail context";

                                ///nokia-conf/configure/port/ethernet/network/egress/queue-group/queue-overrides/queue/drop-tail/low
                                container low {
                                    description "Enter the low context";

                                    ///nokia-conf/configure/port/ethernet/network/egress/queue-group/queue-overrides/queue/drop-tail/low/percent-reduction-from-mbs
                                    leaf percent-reduction-from-mbs {
                                        type types-qos:burst-percent-or-default-override;
                                        description "Percentage reduction from the MBS for a queue drop tail";
                                    }

                                } // container low

                            } // container drop-tail

                            ///nokia-conf/configure/port/ethernet/network/egress/queue-group/queue-overrides/queue/monitor-queue-depth
                            container monitor-queue-depth {
                                presence "Enable the monitor-queue-depth context";
                                description "Enable the monitor-queue-depth context";

                                ///nokia-conf/configure/port/ethernet/network/egress/queue-group/queue-overrides/queue/monitor-queue-depth/fast-polling
                                leaf fast-polling {
                                    type boolean;
                                    default "false";
                                    description "Enable fast polling of the queue depth";
                                }

                                ///nokia-conf/configure/port/ethernet/network/egress/queue-group/queue-overrides/queue/monitor-queue-depth/violation-threshold
                                leaf violation-threshold {
                                    type decimal64 {
                                        range "0.01..99.99";
                                        fraction-digits 2;
                                    }
                                    description "Threshold for queue depth before violation is raised";
                                }

                            } // container monitor-queue-depth

                        } // list queue

                    } // container queue-overrides

                    ///nokia-conf/configure/port/ethernet/network/egress/queue-group/scheduler-policy
                    container scheduler-policy {
                        description "Enter the scheduler-policy context";

                        ///nokia-conf/configure/port/ethernet/network/egress/queue-group/scheduler-policy/policy-name
                        leaf policy-name {
                            type leafref {
                                path "../../../../../../../qos/scheduler-policy/scheduler-policy-name";
                            }
                            description "Scheduler policy for the QoS egress queue group";
                        }

                    } // container scheduler-policy

                } // list queue-group

                ///nokia-conf/configure/port/ethernet/network/egress/port-queues
                container port-queues {
                    description "Enter the port-queues context";

                    ///nokia-conf/configure/port/ethernet/network/egress/port-queues/overrides
                    container overrides {
                        description "Enter the overrides context";

                        ///nokia-conf/configure/port/ethernet/network/egress/port-queues/overrides/queue
                        list queue {
                            key "queue-id";
                            description "Enter the queue list instance";

                            ///nokia-conf/configure/port/ethernet/network/egress/port-queues/overrides/queue/queue-id
                            leaf queue-id {
                                type types-qos:network-queue-queue-id;
                                description "Queue ID";
                            }

                            ///nokia-conf/configure/port/ethernet/network/egress/port-queues/overrides/queue/apply-groups
                            leaf-list apply-groups {
                                type leafref {
                                    path "../../../../../../../../groups/group/name";
                                }
                                max-elements 8;
                                ordered-by user;
                                description "Apply a configuration group at this level";
                            }

                            ///nokia-conf/configure/port/ethernet/network/egress/port-queues/overrides/queue/apply-groups-exclude
                            leaf-list apply-groups-exclude {
                                type leafref {
                                    path "../../../../../../../../groups/group/name";
                                }
                                max-elements 8;
                                ordered-by user;
                                description "Exclude a configuration group at this level";
                            }

                            ///nokia-conf/configure/port/ethernet/network/egress/port-queues/overrides/queue/monitor-queue-depth
                            container monitor-queue-depth {
                                presence "Enable the monitor-queue-depth context";
                                description "Enable the monitor-queue-depth context";

                                ///nokia-conf/configure/port/ethernet/network/egress/port-queues/overrides/queue/monitor-queue-depth/fast-polling
                                leaf fast-polling {
                                    type boolean;
                                    default "false";
                                    description "Enable fast polling of the queue depth";
                                }

                                ///nokia-conf/configure/port/ethernet/network/egress/port-queues/overrides/queue/monitor-queue-depth/violation-threshold
                                leaf violation-threshold {
                                    type decimal64 {
                                        range "0.01..99.99";
                                        fraction-digits 2;
                                    }
                                    description "Threshold for queue depth before violation is raised";
                                }

                            } // container monitor-queue-depth

                        } // list queue

                    } // container overrides

                } // container port-queues

            } // container egress

        } // container network

    } // grouping conf-port-eth-network

}
