submodule nokia-conf-service {

    yang-version "1.1";

    belongs-to nokia-conf { prefix "conf"; }

    import ietf-yang-types                { prefix "yang"; }
    import nokia-sros-yang-extensions     { prefix "sros-ext"; }
    import nokia-types-igmp               { prefix "types-igmp"; }
    import nokia-types-isa                { prefix "types-isa"; }
    import nokia-types-log                { prefix "types-log"; }
    import nokia-types-qos                { prefix "types-qos"; }
    import nokia-types-services           { prefix "types-services"; }
    import nokia-types-sros               { prefix "types-sros"; }

    include nokia-conf-filter;
    include nokia-conf-groups;
    include nokia-conf-lag;
    include nokia-conf-port;
    include nokia-conf-pw-port;
    include nokia-conf-pxc;
    include nokia-conf-qos;
    include nokia-conf-router;
    include nokia-conf-svc-cpipe;
    include nokia-conf-svc-epipe;
    include nokia-conf-svc-ies;
    include nokia-conf-svc-ipfix;
    include nokia-conf-svc-ipipe;
    include nokia-conf-svc-nat;
    include nokia-conf-svc-sdp;
    include nokia-conf-svc-vpls;
    include nokia-conf-svc-vprn;

    sros-ext:sros-major-release "rel23";
    organization "Nokia";
    contact
        "Nokia SR OS Support
         Web: <http://www.nokia.com>";
    description
        "Nokia YANG Data model to configure services on SR OS based routers.

         Copyright 2016 Nokia. All rights reserved. Reproduction of this document
         is authorized on the condition that the foregoing copyright notice is included.

         This nokia-conf-service YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-28";

    grouping conf-service {
        ///nokia-conf/configure/service
        container service {
            description "Enable the service context";

            ///nokia-conf/configure/service/apply-groups
            leaf-list apply-groups {
                type leafref {
                    path "../../groups/group/name";
                }
                max-elements 8;
                ordered-by user;
                description "Apply a configuration group at this level";
            }

            ///nokia-conf/configure/service/apply-groups-exclude
            leaf-list apply-groups-exclude {
                type leafref {
                    path "../../groups/group/name";
                }
                max-elements 8;
                ordered-by user;
                description "Exclude a configuration group at this level";
            }

            ///nokia-conf/configure/service/sdp-group
            container sdp-group {
                description "Enter the sdp-group context";

                ///nokia-conf/configure/service/sdp-group/apply-groups
                leaf-list apply-groups {
                    type leafref {
                        path "../../../groups/group/name";
                    }
                    max-elements 8;
                    ordered-by user;
                    description "Apply a configuration group at this level";
                }

                ///nokia-conf/configure/service/sdp-group/apply-groups-exclude
                leaf-list apply-groups-exclude {
                    type leafref {
                        path "../../../groups/group/name";
                    }
                    max-elements 8;
                    ordered-by user;
                    description "Exclude a configuration group at this level";
                }

                ///nokia-conf/configure/service/sdp-group/group-name
                list group-name {
                    key "group-name";
                    description "Enter the group-name list instance";

                    ///nokia-conf/configure/service/sdp-group/group-name/group-name
                    leaf group-name {
                        type types-sros:named-item;
                        description "SDP administrative group name";
                    }

                    ///nokia-conf/configure/service/sdp-group/group-name/value
                    leaf value {
                        type uint32 {
                            range "0..31";
                        }
                        sros-ext:immutable;
                        mandatory true;
                        description "Unique group value associated with the SDP admin group";
                    }

                    ///nokia-conf/configure/service/sdp-group/group-name/apply-groups
                    leaf-list apply-groups {
                        type leafref {
                            path "../../../../groups/group/name";
                        }
                        max-elements 8;
                        ordered-by user;
                        description "Apply a configuration group at this level";
                    }

                    ///nokia-conf/configure/service/sdp-group/group-name/apply-groups-exclude
                    leaf-list apply-groups-exclude {
                        type leafref {
                            path "../../../../groups/group/name";
                        }
                        max-elements 8;
                        ordered-by user;
                        description "Exclude a configuration group at this level";
                    }

                } // list group-name

            } // container sdp-group

            ///nokia-conf/configure/service/customer
            list customer {
                key "customer-name";
                description "Enter the customer list instance";

                ///nokia-conf/configure/service/customer/customer-name
                leaf customer-name {
                    type types-services:customer-name;
                    description "Customer name for a service";
                }

                ///nokia-conf/configure/service/customer/customer-id
                leaf customer-id {
                    type types-services:customer-id;
                    sros-ext:immutable;
                    description "Customer ID";
                }

                ///nokia-conf/configure/service/customer/description
                leaf description {
                    type types-sros:description;
                    description "Text description";
                }

                ///nokia-conf/configure/service/customer/contact
                leaf contact {
                    type types-sros:description;
                    description "Service customer contact information";
                }

                ///nokia-conf/configure/service/customer/phone
                leaf phone {
                    type types-sros:description;
                    description "Service customer telephone number information";
                }

                ///nokia-conf/configure/service/customer/apply-groups
                leaf-list apply-groups {
                    type leafref {
                        path "../../../groups/group/name";
                    }
                    max-elements 8;
                    ordered-by user;
                    description "Apply a configuration group at this level";
                }

                ///nokia-conf/configure/service/customer/apply-groups-exclude
                leaf-list apply-groups-exclude {
                    type leafref {
                        path "../../../groups/group/name";
                    }
                    max-elements 8;
                    ordered-by user;
                    description "Exclude a configuration group at this level";
                }

                ///nokia-conf/configure/service/customer/multi-service-site
                list multi-service-site {
                    key "multi-service-site-name";
                    description "Enter the multi-service-site list instance";

                    ///nokia-conf/configure/service/customer/multi-service-site/multi-service-site-name
                    leaf multi-service-site-name {
                        type types-sros:named-item;
                        description "Customer site name";
                    }

                    ///nokia-conf/configure/service/customer/multi-service-site/description
                    leaf description {
                        type types-sros:description;
                        description "Text description";
                    }

                    ///nokia-conf/configure/service/customer/multi-service-site/apply-groups
                    leaf-list apply-groups {
                        type leafref {
                            path "../../../../groups/group/name";
                        }
                        max-elements 8;
                        ordered-by user;
                        description "Apply a configuration group at this level";
                    }

                    ///nokia-conf/configure/service/customer/multi-service-site/apply-groups-exclude
                    leaf-list apply-groups-exclude {
                        type leafref {
                            path "../../../../groups/group/name";
                        }
                        max-elements 8;
                        ordered-by user;
                        description "Exclude a configuration group at this level";
                    }

                    ///nokia-conf/configure/service/customer/multi-service-site/assignment
                    container assignment {
                        description "Enter the assignment context";

                        ///nokia-conf/configure/service/customer/multi-service-site/assignment/assignment
                        choice assignment {
                            ///nokia-conf/configure/service/customer/multi-service-site/assignment/assignment/port
                            case port {

                                ///nokia-conf/configure/service/customer/multi-service-site/assignment/assignment/port/port
                                leaf port {
                                    type types-sros:port-named;
                                    description "Multi-service-site assignment to the port";
                                }

                            }
                            ///nokia-conf/configure/service/customer/multi-service-site/assignment/assignment/card
                            case card {

                                ///nokia-conf/configure/service/customer/multi-service-site/assignment/assignment/card/card
                                leaf card {
                                    type uint32 {
                                        range "1..20";
                                    }
                                    description "Multi-service-site assignment to the card slot";
                                }

                            }
                            ///nokia-conf/configure/service/customer/multi-service-site/assignment/assignment/fpe
                            case fpe {

                                ///nokia-conf/configure/service/customer/multi-service-site/assignment/assignment/fpe/fpe
                                leaf fpe {
                                    type leafref {
                                        path "../../../../../fwd-path-ext/fpe/fpe-id";
                                    }
                                    description "Multi-service-site assignment to the FPE object";
                                }

                            }
                        }
                    } // container assignment

                    ///nokia-conf/configure/service/customer/multi-service-site/ingress
                    container ingress {
                        description "Enter the ingress context";

                        ///nokia-conf/configure/service/customer/multi-service-site/ingress/policer-control-policy
                        leaf policer-control-policy {
                            type leafref {
                                path "../../../../../qos/policer-control-policy/policer-control-policy-name";
                            }
                            description "Policer control policy";
                        }

                        ///nokia-conf/configure/service/customer/multi-service-site/ingress/scheduler-policy
                        container scheduler-policy {
                            description "Enter the scheduler-policy context";

                            ///nokia-conf/configure/service/customer/multi-service-site/ingress/scheduler-policy/policy-name
                            leaf policy-name {
                                type leafref {
                                    path "../../../../../../qos/scheduler-policy/scheduler-policy-name";
                                }
                                description "Scheduler policy name";
                            }

                            ///nokia-conf/configure/service/customer/multi-service-site/ingress/scheduler-policy/overrides
                            container overrides {
                                description "Enter the overrides context";

                                ///nokia-conf/configure/service/customer/multi-service-site/ingress/scheduler-policy/overrides/scheduler
                                list scheduler {
                                    key "scheduler-name";
                                    description "Enter the scheduler list instance";

                                    ///nokia-conf/configure/service/customer/multi-service-site/ingress/scheduler-policy/overrides/scheduler/scheduler-name
                                    leaf scheduler-name {
                                        type types-sros:named-item;
                                        description "Scheduler name";
                                    }

                                    ///nokia-conf/configure/service/customer/multi-service-site/ingress/scheduler-policy/overrides/scheduler/apply-groups
                                    leaf-list apply-groups {
                                        type leafref {
                                            path "../../../../../../../../groups/group/name";
                                        }
                                        max-elements 8;
                                        ordered-by user;
                                        description "Apply a configuration group at this level";
                                    }

                                    ///nokia-conf/configure/service/customer/multi-service-site/ingress/scheduler-policy/overrides/scheduler/apply-groups-exclude
                                    leaf-list apply-groups-exclude {
                                        type leafref {
                                            path "../../../../../../../../groups/group/name";
                                        }
                                        max-elements 8;
                                        ordered-by user;
                                        description "Exclude a configuration group at this level";
                                    }

                                    ///nokia-conf/configure/service/customer/multi-service-site/ingress/scheduler-policy/overrides/scheduler/parent
                                    container parent {
                                        description "Enter the parent context";

                                        ///nokia-conf/configure/service/customer/multi-service-site/ingress/scheduler-policy/overrides/scheduler/parent/weight
                                        leaf weight {
                                            type types-qos:weight;
                                            description "Relative weight of the scheduler to feed the queue";
                                        }

                                        ///nokia-conf/configure/service/customer/multi-service-site/ingress/scheduler-policy/overrides/scheduler/parent/cir-weight
                                        leaf cir-weight {
                                            type types-qos:weight;
                                            description "Weight used at the within-CIR port priority level";
                                        }

                                    } // container parent

                                    ///nokia-conf/configure/service/customer/multi-service-site/ingress/scheduler-policy/overrides/scheduler/rate
                                    container rate {
                                        description "Enter the rate context";

                                        ///nokia-conf/configure/service/customer/multi-service-site/ingress/scheduler-policy/overrides/scheduler/rate/pir
                                        leaf pir {
                                            type union {
                                                type int64 {
                                                    range "1..6400000000";
                                                }
                                                type enumeration {
                                                    enum max                            { value -1; }
                                                }
                                            }
                                            units "kilobps";
                                            description "PIR for the scheduler";
                                        }

                                        ///nokia-conf/configure/service/customer/multi-service-site/ingress/scheduler-policy/overrides/scheduler/rate/cir
                                        leaf cir {
                                            type union {
                                                type int64 {
                                                    range "0..6400000000";
                                                }
                                                type enumeration {
                                                    enum sum                            { value -3; }
                                                    enum max                            { value -1; }
                                                }
                                            }
                                            units "kilobps";
                                            description "CIR for the scheduler";
                                        }

                                    } // container rate

                                } // list scheduler

                            } // container overrides

                        } // container scheduler-policy

                    } // container ingress

                    ///nokia-conf/configure/service/customer/multi-service-site/egress
                    container egress {
                        description "Enter the egress context";

                        ///nokia-conf/configure/service/customer/multi-service-site/egress/policer-control-policy
                        leaf policer-control-policy {
                            type leafref {
                                path "../../../../../qos/policer-control-policy/policer-control-policy-name";
                            }
                            description "Policer control policy";
                        }

                        ///nokia-conf/configure/service/customer/multi-service-site/egress/agg-rate
                        container agg-rate {
                            description "Enter the agg-rate context";

                            ///nokia-conf/configure/service/customer/multi-service-site/egress/agg-rate/rate
                            leaf rate {
                                type types-services:agg-rate-rate;
                                units "kilobps";
                                description "Rate limit";
                            }

                            ///nokia-conf/configure/service/customer/multi-service-site/egress/agg-rate/queue-frame-based-accounting
                            leaf queue-frame-based-accounting {
                                type boolean;
                                default "false";
                                description "Enable frame based accounting for policers and queues";
                            }

                            ///nokia-conf/configure/service/customer/multi-service-site/egress/agg-rate/limit-unused-bandwidth
                            leaf limit-unused-bandwidth {
                                type boolean;
                                default "false";
                                description "Enable aggregate rate overrun protection";
                            }

                        } // container agg-rate

                        ///nokia-conf/configure/service/customer/multi-service-site/egress/scheduler-policy
                        container scheduler-policy {
                            description "Enter the scheduler-policy context";

                            ///nokia-conf/configure/service/customer/multi-service-site/egress/scheduler-policy/policy-name
                            leaf policy-name {
                                type leafref {
                                    path "../../../../../../qos/scheduler-policy/scheduler-policy-name";
                                }
                                description "Scheduler policy name";
                            }

                            ///nokia-conf/configure/service/customer/multi-service-site/egress/scheduler-policy/overrides
                            container overrides {
                                description "Enter the overrides context";

                                ///nokia-conf/configure/service/customer/multi-service-site/egress/scheduler-policy/overrides/scheduler
                                list scheduler {
                                    key "scheduler-name";
                                    description "Enter the scheduler list instance";

                                    ///nokia-conf/configure/service/customer/multi-service-site/egress/scheduler-policy/overrides/scheduler/scheduler-name
                                    leaf scheduler-name {
                                        type types-sros:named-item;
                                        description "Scheduler name";
                                    }

                                    ///nokia-conf/configure/service/customer/multi-service-site/egress/scheduler-policy/overrides/scheduler/apply-groups
                                    leaf-list apply-groups {
                                        type leafref {
                                            path "../../../../../../../../groups/group/name";
                                        }
                                        max-elements 8;
                                        ordered-by user;
                                        description "Apply a configuration group at this level";
                                    }

                                    ///nokia-conf/configure/service/customer/multi-service-site/egress/scheduler-policy/overrides/scheduler/apply-groups-exclude
                                    leaf-list apply-groups-exclude {
                                        type leafref {
                                            path "../../../../../../../../groups/group/name";
                                        }
                                        max-elements 8;
                                        ordered-by user;
                                        description "Exclude a configuration group at this level";
                                    }

                                    ///nokia-conf/configure/service/customer/multi-service-site/egress/scheduler-policy/overrides/scheduler/parent
                                    container parent {
                                        description "Enter the parent context";

                                        ///nokia-conf/configure/service/customer/multi-service-site/egress/scheduler-policy/overrides/scheduler/parent/weight
                                        leaf weight {
                                            type types-qos:weight;
                                            description "Relative weight of the scheduler to feed the queue";
                                        }

                                        ///nokia-conf/configure/service/customer/multi-service-site/egress/scheduler-policy/overrides/scheduler/parent/cir-weight
                                        leaf cir-weight {
                                            type types-qos:weight;
                                            description "Weight used at the within-CIR port priority level";
                                        }

                                    } // container parent

                                    ///nokia-conf/configure/service/customer/multi-service-site/egress/scheduler-policy/overrides/scheduler/rate
                                    container rate {
                                        description "Enter the rate context";

                                        ///nokia-conf/configure/service/customer/multi-service-site/egress/scheduler-policy/overrides/scheduler/rate/pir
                                        leaf pir {
                                            type union {
                                                type int64 {
                                                    range "1..6400000000";
                                                }
                                                type enumeration {
                                                    enum max                            { value -1; }
                                                }
                                            }
                                            units "kilobps";
                                            description "PIR for the scheduler";
                                        }

                                        ///nokia-conf/configure/service/customer/multi-service-site/egress/scheduler-policy/overrides/scheduler/rate/cir
                                        leaf cir {
                                            type union {
                                                type int64 {
                                                    range "0..6400000000";
                                                }
                                                type enumeration {
                                                    enum sum                            { value -3; }
                                                    enum max                            { value -1; }
                                                }
                                            }
                                            units "kilobps";
                                            description "CIR for the scheduler";
                                        }

                                    } // container rate

                                } // list scheduler

                            } // container overrides

                        } // container scheduler-policy

                    } // container egress

                } // list multi-service-site

            } // list customer

            ///nokia-conf/configure/service/mrp
            container mrp {
                description "Enter the mrp context";

                ///nokia-conf/configure/service/mrp/policy
                list policy {
                    key "policy-name";
                    description "Enter the policy list instance";

                    ///nokia-conf/configure/service/mrp/policy/policy-name
                    leaf policy-name {
                        type types-sros:named-item;
                        description "Specify the policy name associated with the MRP";
                    }

                    ///nokia-conf/configure/service/mrp/policy/description
                    leaf description {
                        type types-sros:description;
                        description "Text description";
                    }

                    ///nokia-conf/configure/service/mrp/policy/scope
                    leaf scope {
                        type types-services:item-scope;
                        default "template";
                        description "Specify the scope of the mrp-policy definition";
                    }

                    ///nokia-conf/configure/service/mrp/policy/default-action
                    leaf default-action {
                        type types-services:mrp-policy-default-action;
                        default "allow";
                        description "Action for packets not matching any MRP policy entries";
                    }

                    ///nokia-conf/configure/service/mrp/policy/apply-groups
                    leaf-list apply-groups {
                        type leafref {
                            path "../../../../groups/group/name";
                        }
                        max-elements 8;
                        ordered-by user;
                        description "Apply a configuration group at this level";
                    }

                    ///nokia-conf/configure/service/mrp/policy/apply-groups-exclude
                    leaf-list apply-groups-exclude {
                        type leafref {
                            path "../../../../groups/group/name";
                        }
                        max-elements 8;
                        ordered-by user;
                        description "Exclude a configuration group at this level";
                    }

                    ///nokia-conf/configure/service/mrp/policy/entry
                    list entry {
                        key "entry-id";
                        description "Enter the entry list instance";

                        ///nokia-conf/configure/service/mrp/policy/entry/entry-id
                        leaf entry-id {
                            type types-services:entry-id;
                            description "Sepcify an id for the MRP policy entry";
                        }

                        ///nokia-conf/configure/service/mrp/policy/entry/action
                        leaf action {
                            type types-services:mrp-policy-action;
                            description "Action applied for matching packets";
                        }

                        ///nokia-conf/configure/service/mrp/policy/entry/description
                        leaf description {
                            type types-sros:description;
                            description "Text description";
                        }

                        ///nokia-conf/configure/service/mrp/policy/entry/apply-groups
                        leaf-list apply-groups {
                            type leafref {
                                path "../../../../../groups/group/name";
                            }
                            max-elements 8;
                            ordered-by user;
                            description "Apply a configuration group at this level";
                        }

                        ///nokia-conf/configure/service/mrp/policy/entry/apply-groups-exclude
                        leaf-list apply-groups-exclude {
                            type leafref {
                                path "../../../../../groups/group/name";
                            }
                            max-elements 8;
                            ordered-by user;
                            description "Exclude a configuration group at this level";
                        }

                        ///nokia-conf/configure/service/mrp/policy/entry/match
                        container match {
                            description "Enter the match context";

                            ///nokia-conf/configure/service/mrp/policy/entry/match/isid
                            list isid {
                                key "value";
                                description "Enter the isid list instance";

                                ///nokia-conf/configure/service/mrp/policy/entry/match/isid/value
                                leaf value {
                                    type types-sros:svc-isid;
                                    description "Lowest service instance ID to match the entry";
                                }

                                ///nokia-conf/configure/service/mrp/policy/entry/match/isid/higher-value
                                leaf higher-value {
                                    type types-sros:svc-isid;
                                    description "Highest service instance ID to match the entry";
                                }

                                ///nokia-conf/configure/service/mrp/policy/entry/match/isid/apply-groups
                                leaf-list apply-groups {
                                    type leafref {
                                        path "../../../../../../../groups/group/name";
                                    }
                                    max-elements 8;
                                    ordered-by user;
                                    description "Apply a configuration group at this level";
                                }

                                ///nokia-conf/configure/service/mrp/policy/entry/match/isid/apply-groups-exclude
                                leaf-list apply-groups-exclude {
                                    type leafref {
                                        path "../../../../../../../groups/group/name";
                                    }
                                    max-elements 8;
                                    ordered-by user;
                                    description "Exclude a configuration group at this level";
                                }

                            } // list isid

                        } // container match

                    } // list entry

                } // list policy

            } // container mrp

            ///nokia-conf/configure/service/oper-group
            list oper-group {
                key "name";
                max-elements 32768;
                description "Enter the oper-group list instance";

                ///nokia-conf/configure/service/oper-group/name
                leaf name {
                    type types-sros:named-item;
                    description "Operational group name";
                }

                ///nokia-conf/configure/service/oper-group/apply-groups
                leaf-list apply-groups {
                    type leafref {
                        path "../../../groups/group/name";
                    }
                    max-elements 8;
                    ordered-by user;
                    description "Apply a configuration group at this level";
                }

                ///nokia-conf/configure/service/oper-group/apply-groups-exclude
                leaf-list apply-groups-exclude {
                    type leafref {
                        path "../../../groups/group/name";
                    }
                    max-elements 8;
                    ordered-by user;
                    description "Exclude a configuration group at this level";
                }

                ///nokia-conf/configure/service/oper-group/hold-time
                container hold-time {
                    description "Enter the hold-time context";

                    ///nokia-conf/configure/service/oper-group/hold-time/down
                    leaf down {
                        type uint32 {
                            range "1..3600";
                        }
                        units "seconds";
                        description "Oper group hold down time";
                    }

                    ///nokia-conf/configure/service/oper-group/hold-time/up
                    leaf up {
                        type uint32 {
                            range "0..3600";
                        }
                        units "seconds";
                        default "4";
                        description "Oper group hold up time";
                    }

                } // container hold-time

                ///nokia-conf/configure/service/oper-group/bfd-liveness
                container bfd-liveness {
                    presence "Enable the bfd-liveness context";
                    description "Enable the bfd-liveness context";

                    ///nokia-conf/configure/service/oper-group/bfd-liveness/router-instance
                    leaf router-instance {
                        type string;
                        sros-ext:immutable;
                        mandatory true;
                        description "Routing context used for route lookup";
                    }

                    ///nokia-conf/configure/service/oper-group/bfd-liveness/interface-name
                    leaf interface-name {
                        type types-sros:interface-name;
                        sros-ext:immutable;
                        mandatory true;
                        description "Source interface name";
                    }

                    ///nokia-conf/configure/service/oper-group/bfd-liveness/dest-ip
                    leaf dest-ip {
                        type types-sros:ipv4-unicast-address;
                        sros-ext:immutable;
                        mandatory true;
                        description "Destination address for BFD";
                    }

                    ///nokia-conf/configure/service/oper-group/bfd-liveness/apply-groups
                    leaf-list apply-groups {
                        type leafref {
                            path "../../../../groups/group/name";
                        }
                        max-elements 8;
                        ordered-by user;
                        description "Apply a configuration group at this level";
                    }

                    ///nokia-conf/configure/service/oper-group/bfd-liveness/apply-groups-exclude
                    leaf-list apply-groups-exclude {
                        type leafref {
                            path "../../../../groups/group/name";
                        }
                        max-elements 8;
                        ordered-by user;
                        description "Exclude a configuration group at this level";
                    }

                } // container bfd-liveness

            } // list oper-group

            ///nokia-conf/configure/service/pbb
            container pbb {
                description "Enable the pbb context";

                ///nokia-conf/configure/service/pbb/apply-groups
                leaf-list apply-groups {
                    type leafref {
                        path "../../../groups/group/name";
                    }
                    max-elements 8;
                    ordered-by user;
                    description "Apply a configuration group at this level";
                }

                ///nokia-conf/configure/service/pbb/apply-groups-exclude
                leaf-list apply-groups-exclude {
                    type leafref {
                        path "../../../groups/group/name";
                    }
                    max-elements 8;
                    ordered-by user;
                    description "Exclude a configuration group at this level";
                }

                ///nokia-conf/configure/service/pbb/source-bmac
                container source-bmac {
                    description "Enter the source-bmac context";

                    ///nokia-conf/configure/service/pbb/source-bmac/address
                    leaf address {
                        type types-sros:mac-unicast-address-no-zero;
                        description "Source B-VPLS MAC address to use with PBB";
                    }

                    ///nokia-conf/configure/service/pbb/source-bmac/evpn-etree-leaf-address
                    leaf evpn-etree-leaf-address {
                        type types-sros:mac-unicast-address-no-zero;
                        description "Source Backbone VPLS MAC address to use with Provider Backbone Bridging (PBB)";
                    }

                } // container source-bmac

                ///nokia-conf/configure/service/pbb/mac
                list mac {
                    key "name";
                    description "Enter the mac list instance";

                    ///nokia-conf/configure/service/pbb/mac/name
                    leaf name {
                        type types-sros:named-item;
                        description "MAC name for the MAC address";
                    }

                    ///nokia-conf/configure/service/pbb/mac/address
                    leaf address {
                        type types-sros:mac-unicast-address-no-zero;
                        mandatory true;
                        description "IEEE address assigned to the MAC name";
                    }

                    ///nokia-conf/configure/service/pbb/mac/apply-groups
                    leaf-list apply-groups {
                        type leafref {
                            path "../../../../groups/group/name";
                        }
                        max-elements 8;
                        ordered-by user;
                        description "Apply a configuration group at this level";
                    }

                    ///nokia-conf/configure/service/pbb/mac/apply-groups-exclude
                    leaf-list apply-groups-exclude {
                        type leafref {
                            path "../../../../groups/group/name";
                        }
                        max-elements 8;
                        ordered-by user;
                        description "Exclude a configuration group at this level";
                    }

                } // list mac

                ///nokia-conf/configure/service/pbb/mac-notification
                container mac-notification {
                    description "Enter the mac-notification context";

                    ///nokia-conf/configure/service/pbb/mac-notification/interval
                    leaf interval {
                        type uint32 {
                            range "1..100";
                        }
                        units "deciseconds";
                        default "1";
                        description "Interval for MAC-notification messages";
                    }

                    ///nokia-conf/configure/service/pbb/mac-notification/count
                    leaf count {
                        type uint32 {
                            range "1..10";
                        }
                        default "3";
                        description "MAC notification messages count";
                    }

                    ///nokia-conf/configure/service/pbb/mac-notification/apply-groups
                    leaf-list apply-groups {
                        type leafref {
                            path "../../../../groups/group/name";
                        }
                        max-elements 8;
                        ordered-by user;
                        description "Apply a configuration group at this level";
                    }

                    ///nokia-conf/configure/service/pbb/mac-notification/apply-groups-exclude
                    leaf-list apply-groups-exclude {
                        type leafref {
                            path "../../../../groups/group/name";
                        }
                        max-elements 8;
                        ordered-by user;
                        description "Exclude a configuration group at this level";
                    }

                } // container mac-notification

            } // container pbb

            ///nokia-conf/configure/service/upnp
            container upnp {
                description "Enter the upnp context";

                ///nokia-conf/configure/service/upnp/policy
                list policy {
                    key "name";
                    max-elements 255;
                    description "Enter the policy list instance";

                    ///nokia-conf/configure/service/upnp/policy/name
                    leaf name {
                        type types-sros:external-named-item;
                        description "UPnP policy name";
                    }

                    ///nokia-conf/configure/service/upnp/policy/description
                    leaf description {
                        type types-sros:description;
                        description "Text description";
                    }

                    ///nokia-conf/configure/service/upnp/policy/port
                    leaf port {
                        type types-sros:tcp-udp-port-non-zero;
                        default "5000";
                        description "HTTP TCP port to which the UPnP IGD listens";
                    }

                    ///nokia-conf/configure/service/upnp/policy/mapping-limit
                    leaf mapping-limit {
                        type uint32 {
                            range "1..256";
                        }
                        default "256";
                        description "Maximum number of UPnP mappings per subscriber";
                    }

                    ///nokia-conf/configure/service/upnp/policy/strict-mode
                    leaf strict-mode {
                        type boolean;
                        default "false";
                        description "Enable UPnP strict mode";
                    }

                    ///nokia-conf/configure/service/upnp/policy/apply-groups
                    leaf-list apply-groups {
                        type leafref {
                            path "../../../../groups/group/name";
                        }
                        max-elements 8;
                        ordered-by user;
                        description "Apply a configuration group at this level";
                    }

                    ///nokia-conf/configure/service/upnp/policy/apply-groups-exclude
                    leaf-list apply-groups-exclude {
                        type leafref {
                            path "../../../../groups/group/name";
                        }
                        max-elements 8;
                        ordered-by user;
                        description "Exclude a configuration group at this level";
                    }

                } // list policy

            } // container upnp

            ///nokia-conf/configure/service/proxy-arp-nd
            container proxy-arp-nd {
                description "Enter the proxy-arp-nd context";

                ///nokia-conf/configure/service/proxy-arp-nd/mac-list
                container mac-list {
                    description "Enter the mac-list context";

                    ///nokia-conf/configure/service/proxy-arp-nd/mac-list/list
                    list list {
                        key "list-name";
                        description "Enter the list list instance";

                        ///nokia-conf/configure/service/proxy-arp-nd/mac-list/list/list-name
                        leaf list-name {
                            type types-sros:named-item;
                            description "Specify name for mac list";
                        }

                        ///nokia-conf/configure/service/proxy-arp-nd/mac-list/list/apply-groups
                        leaf-list apply-groups {
                            type leafref {
                                path "../../../../../groups/group/name";
                            }
                            max-elements 8;
                            ordered-by user;
                            description "Apply a configuration group at this level";
                        }

                        ///nokia-conf/configure/service/proxy-arp-nd/mac-list/list/apply-groups-exclude
                        leaf-list apply-groups-exclude {
                            type leafref {
                                path "../../../../../groups/group/name";
                            }
                            max-elements 8;
                            ordered-by user;
                            description "Exclude a configuration group at this level";
                        }

                        ///nokia-conf/configure/service/proxy-arp-nd/mac-list/list/mac
                        list mac {
                            key "address";
                            max-elements 10;
                            description "Add a list entry for mac";

                            ///nokia-conf/configure/service/proxy-arp-nd/mac-list/list/mac/address
                            leaf address {
                                type types-sros:mac-unicast-address-no-zero;
                                description "MAC address to be added to the list";
                            }

                        } // list mac

                    } // list list

                } // container mac-list

            } // container proxy-arp-nd

            ///nokia-conf/configure/service/pw-template
            list pw-template {
                key "pw-template-name";
                max-elements 2048;
                description "Enter the pw-template list instance";

                ///nokia-conf/configure/service/pw-template/pw-template-name
                leaf pw-template-name {
                    type types-services:pw-template-name;
                    description "SDP template name";
                }

                ///nokia-conf/configure/service/pw-template/pw-template-id
                leaf pw-template-id {
                    type types-services:pw-template-id;
                    sros-ext:immutable;
                    description "PW Template Id";
                }

                ///nokia-conf/configure/service/pw-template/provisioned-sdp
                leaf provisioned-sdp {
                    type types-services:provisioned-sdp;
                    sros-ext:immutable;
                    description "Provisioned SDP type";
                }

                ///nokia-conf/configure/service/pw-template/allow-fragmentation
                leaf allow-fragmentation {
                    type boolean;
                    default "false";
                    description "Allow packets to be sent without setting DF bit";
                }

                ///nokia-conf/configure/service/pw-template/auto-gre-sdp
                leaf auto-gre-sdp {
                    type boolean;
                    sros-ext:immutable;
                    default "false";
                    description "Use a GRE tunnel to automatically create an SDP";
                }

                ///nokia-conf/configure/service/pw-template/vc-type
                leaf vc-type {
                    type types-services:pw-template-sdp-bind-vc-type;
                    default "ether";
                    description "Virtual circuit type associated with the SDP bind";
                }

                ///nokia-conf/configure/service/pw-template/accounting-policy
                leaf accounting-policy {
                    type types-log:log-policy-id;
                    description "Accounting policy";
                }

                ///nokia-conf/configure/service/pw-template/collect-stats
                leaf collect-stats {
                    type boolean;
                    default "false";
                    description "Collect statistics";
                }

                ///nokia-conf/configure/service/pw-template/vlan-vc-tag
                leaf vlan-vc-tag {
                    type types-services:vlan-vc-tag;
                    description "VLAN VC tag";
                }

                ///nokia-conf/configure/service/pw-template/force-vc-forwarding
                leaf force-vc-forwarding {
                    type enumeration {
                        enum vlan                           { value 1; }
                        enum qinq-c-tag-c-tag               { value 2; }
                        enum qinq-s-tag-c-tag               { value 3; }
                    }
                    description "VC forwarding action";
                }

                ///nokia-conf/configure/service/pw-template/control-word
                leaf control-word {
                    type boolean;
                    default "false";
                    description "Enable/Disable the use of ControlWord";
                }

                ///nokia-conf/configure/service/pw-template/block-on-peer-fault
                leaf block-on-peer-fault {
                    type boolean;
                    default "false";
                    description "Enable block traffic on peer fault";
                }

                ///nokia-conf/configure/service/pw-template/apply-groups
                leaf-list apply-groups {
                    type leafref {
                        path "../../../groups/group/name";
                    }
                    max-elements 8;
                    ordered-by user;
                    description "Apply a configuration group at this level";
                }

                ///nokia-conf/configure/service/pw-template/apply-groups-exclude
                leaf-list apply-groups-exclude {
                    type leafref {
                        path "../../../groups/group/name";
                    }
                    max-elements 8;
                    ordered-by user;
                    description "Exclude a configuration group at this level";
                }

                ///nokia-conf/configure/service/pw-template/label
                choice label {
                    ///nokia-conf/configure/service/pw-template/label/entropy
                    case entropy {

                        ///nokia-conf/configure/service/pw-template/label/entropy/entropy-label
                        leaf entropy-label {
                            type empty;
                            description "Enable the use of an entropy label";
                        }

                    }
                    ///nokia-conf/configure/service/pw-template/label/hash
                    case hash {

                        ///nokia-conf/configure/service/pw-template/label/hash/hash-label
                        container hash-label {
                            presence "Enable the hash-label context";
                            description "Enable the hash-label context";

                            ///nokia-conf/configure/service/pw-template/label/hash/hash-label/signal-capability
                            leaf signal-capability {
                                type empty;
                                description "Signal hash label capability to the remote PE";
                            }

                        } // container hash-label

                    }
                }
                ///nokia-conf/configure/service/pw-template/split-horizon-group
                container split-horizon-group {
                    description "Enter the split-horizon-group context";

                    ///nokia-conf/configure/service/pw-template/split-horizon-group/name
                    leaf name {
                        type types-sros:named-item;
                        description "Split horizon group name to which the SDP belongs";
                    }

                    ///nokia-conf/configure/service/pw-template/split-horizon-group/description
                    leaf description {
                        type types-sros:description;
                        description "Text description";
                    }

                    ///nokia-conf/configure/service/pw-template/split-horizon-group/fdb
                    container fdb {
                        description "Enter the fdb context";

                        ///nokia-conf/configure/service/pw-template/split-horizon-group/fdb/saps
                        container saps {
                            description "Enter the saps context";

                            ///nokia-conf/configure/service/pw-template/split-horizon-group/fdb/saps/auto-learn-mac-protect
                            leaf auto-learn-mac-protect {
                                type boolean;
                                default "false";
                                description "Enable automatic update of MAC protect list";
                            }

                            ///nokia-conf/configure/service/pw-template/split-horizon-group/fdb/saps/protected-src-mac-violation-action
                            leaf protected-src-mac-violation-action {
                                type types-services:sap-protected-src-mac-violation-action;
                                description "Action for protected source MAC restriction";
                            }

                            ///nokia-conf/configure/service/pw-template/split-horizon-group/fdb/saps/discard-unprotected-dest-mac
                            leaf discard-unprotected-dest-mac {
                                type boolean;
                                default "false";
                                description "Enable/disable unprotected dest MAC restriction";
                            }

                        } // container saps

                    } // container fdb

                } // container split-horizon-group

                ///nokia-conf/configure/service/pw-template/ingress
                container ingress {
                    description "Enter the ingress context";

                    ///nokia-conf/configure/service/pw-template/ingress/filter
                    container filter {
                        description "Enter the filter context";

                        ///nokia-conf/configure/service/pw-template/ingress/filter/mac
                        leaf mac {
                            type types-sros:named-item-64;
                            description "MAC filter policy name";
                        }

                        ///nokia-conf/configure/service/pw-template/ingress/filter/ip
                        leaf ip {
                            type types-sros:named-item-64;
                            description "IPv4 filter policy name";
                        }

                        ///nokia-conf/configure/service/pw-template/ingress/filter/ipv6
                        leaf ipv6 {
                            type types-sros:named-item-64;
                            description "IPv6 filter policy name";
                        }

                    } // container filter

                    ///nokia-conf/configure/service/pw-template/ingress/qos
                    container qos {
                        description "Enter the qos context";

                        ///nokia-conf/configure/service/pw-template/ingress/qos/network
                        container network {
                            description "Enter the network context";

                            ///nokia-conf/configure/service/pw-template/ingress/qos/network/policy-name
                            leaf policy-name {
                                type types-sros:named-item-64;
                                description "Network policy ID";
                            }

                            ///nokia-conf/configure/service/pw-template/ingress/qos/network/fp-redirect-group
                            container fp-redirect-group {
                                description "Enter the fp-redirect-group context";

                                ///nokia-conf/configure/service/pw-template/ingress/qos/network/fp-redirect-group/group-name
                                leaf group-name {
                                    type types-sros:named-item;
                                    description "Name of the forwarding plane queue group template";
                                }

                                ///nokia-conf/configure/service/pw-template/ingress/qos/network/fp-redirect-group/instance
                                leaf instance {
                                    type types-services:qos-qgrp-instance-id;
                                    description "Instance for FP ingress queue group";
                                }

                            } // container fp-redirect-group

                        } // container network

                    } // container qos

                } // container ingress

                ///nokia-conf/configure/service/pw-template/igmp-snooping
                container igmp-snooping {
                    description "Enter the igmp-snooping context";

                    ///nokia-conf/configure/service/pw-template/igmp-snooping/fast-leave
                    leaf fast-leave {
                        type boolean;
                        default "false";
                        description "Allow IGMP fast leave processing";
                    }

                    ///nokia-conf/configure/service/pw-template/igmp-snooping/import-policy
                    leaf import-policy {
                        type types-sros:named-item;
                        description "Import policy that filters IGMP packets";
                    }

                    ///nokia-conf/configure/service/pw-template/igmp-snooping/query-last-member-interval
                    leaf query-last-member-interval {
                        type uint32 {
                            range "1..50";
                        }
                        units "deciseconds";
                        default "10";
                        description "Time between group-specific query messages";
                    }

                    ///nokia-conf/configure/service/pw-template/igmp-snooping/maximum-number-groups
                    leaf maximum-number-groups {
                        type uint32 {
                            range "1..1000";
                        }
                        description "Maximum multicast groups";
                    }

                    ///nokia-conf/configure/service/pw-template/igmp-snooping/query-interval
                    leaf query-interval {
                        type uint32 {
                            range "2..1024";
                        }
                        units "seconds";
                        default "125";
                        description "Time between two consecutive host-query messages";
                    }

                    ///nokia-conf/configure/service/pw-template/igmp-snooping/query-response-interval
                    leaf query-response-interval {
                        type uint32 {
                            range "1..1023";
                        }
                        units "seconds";
                        default "10";
                        description "Time to wait for a response to the host-query messages";
                    }

                    ///nokia-conf/configure/service/pw-template/igmp-snooping/robust-count
                    leaf robust-count {
                        type uint32 {
                            range "2..7";
                        }
                        default "2";
                        description "Number of retries after expected message loss";
                    }

                    ///nokia-conf/configure/service/pw-template/igmp-snooping/send-queries
                    leaf send-queries {
                        type boolean;
                        default "false";
                        description "Generate IGMP general queries";
                    }

                    ///nokia-conf/configure/service/pw-template/igmp-snooping/version
                    leaf version {
                        type types-igmp:igmp-version;
                        default "3";
                        description "IGMP version";
                    }

                } // container igmp-snooping

                ///nokia-conf/configure/service/pw-template/stp
                container stp {
                    description "Enter the stp context";

                    ///nokia-conf/configure/service/pw-template/stp/admin-state
                    leaf admin-state {
                        type types-sros:admin-state;
                        description "Administrative state of STP";
                    }

                    ///nokia-conf/configure/service/pw-template/stp/auto-edge
                    leaf auto-edge {
                        type boolean;
                        default "true";
                        description "Enable automatic detection of edge port characteristics";
                    }

                    ///nokia-conf/configure/service/pw-template/stp/edge-port
                    leaf edge-port {
                        type boolean;
                        default "false";
                        description "Designate SAP or SDP as an edge port";
                    }

                    ///nokia-conf/configure/service/pw-template/stp/link-type
                    leaf link-type {
                        type types-services:stp-link-type;
                        default "pt-pt";
                        description "Configure STP link-type";
                    }

                    ///nokia-conf/configure/service/pw-template/stp/path-cost
                    leaf path-cost {
                        type types-services:stp-path-cost;
                        default "10";
                        description "Configure path-cost";
                    }

                    ///nokia-conf/configure/service/pw-template/stp/priority
                    leaf priority {
                        type int32 {
                            range "0..255";
                        }
                        default "128";
                        description "Configure STP priority";
                    }

                    ///nokia-conf/configure/service/pw-template/stp/root-guard
                    leaf root-guard {
                        type boolean;
                        default "false";
                        description "Enable/disable STP root-guard";
                    }

                } // container stp

                ///nokia-conf/configure/service/pw-template/l2pt
                container l2pt {
                    description "Enter the l2pt context";

                    ///nokia-conf/configure/service/pw-template/l2pt/termination
                    container termination {
                        presence "Enable the termination context";
                        description "Enable the termination context";

                        ///nokia-conf/configure/service/pw-template/l2pt/termination/protocols
                        container protocols {
                            description "Enter the protocols context";

                            ///nokia-conf/configure/service/pw-template/l2pt/termination/protocols/stp
                            leaf stp {
                                type boolean;
                                default "true";
                                description "Enable all spanning tree protocols";
                            }

                            ///nokia-conf/configure/service/pw-template/l2pt/termination/protocols/cdp
                            leaf cdp {
                                type boolean;
                                default "false";
                                description "Enable Cisco discovery protocol";
                            }

                            ///nokia-conf/configure/service/pw-template/l2pt/termination/protocols/vtp
                            leaf vtp {
                                type boolean;
                                default "false";
                                description "Enable virtual trunk protocol";
                            }

                            ///nokia-conf/configure/service/pw-template/l2pt/termination/protocols/dtp
                            leaf dtp {
                                type boolean;
                                default "false";
                                description "Enable dynamic trunking protocol";
                            }

                            ///nokia-conf/configure/service/pw-template/l2pt/termination/protocols/pagp
                            leaf pagp {
                                type boolean;
                                default "false";
                                description "Enable port aggregation protocol";
                            }

                            ///nokia-conf/configure/service/pw-template/l2pt/termination/protocols/udld
                            leaf udld {
                                type boolean;
                                default "false";
                                description "Enable unidirectional link detection";
                            }

                        } // container protocols

                    } // container termination

                } // container l2pt

                ///nokia-conf/configure/service/pw-template/encryption-keygroup
                container encryption-keygroup {
                    description "Enter the encryption-keygroup context";

                    ///nokia-conf/configure/service/pw-template/encryption-keygroup/inbound
                    leaf inbound {
                        type types-services:keygroup-id;
                        description "Keygroup identifier in the inbound direction";
                    }

                    ///nokia-conf/configure/service/pw-template/encryption-keygroup/outbound
                    leaf outbound {
                        type types-services:keygroup-id;
                        description "Keygroup identifier in the outbound direction";
                    }

                } // container encryption-keygroup

                ///nokia-conf/configure/service/pw-template/fdb
                container fdb {
                    description "Enter the fdb context";

                    ///nokia-conf/configure/service/pw-template/fdb/discard-unknown-source
                    leaf discard-unknown-source {
                        type boolean;
                        default "false";
                        description "Discard frames with unknown source";
                    }

                    ///nokia-conf/configure/service/pw-template/fdb/limit-mac-move
                    leaf limit-mac-move {
                        type types-services:vpls-limit-mac-move;
                        default "blockable";
                        description "MAC move limit";
                    }

                    ///nokia-conf/configure/service/pw-template/fdb/mac-pinning
                    leaf mac-pinning {
                        type boolean;
                        default "false";
                        description "Enable MAC address pinning on this spoke SDP";
                    }

                    ///nokia-conf/configure/service/pw-template/fdb/maximum-mac-addresses
                    leaf maximum-mac-addresses {
                        type uint32 {
                            range "1..511999";
                        }
                        description "Maximum number of MAC address entries in the FDB";
                    }

                    ///nokia-conf/configure/service/pw-template/fdb/auto-learn-mac-protect
                    leaf auto-learn-mac-protect {
                        type boolean;
                        default "false";
                        description "Enable automatic update of MAC protect list";
                    }

                    ///nokia-conf/configure/service/pw-template/fdb/auto-learn-mac-protect-exclude-list
                    leaf auto-learn-mac-protect-exclude-list {
                        type types-sros:named-item;
                        description "Name of the MAC protect exclusion list";
                    }

                    ///nokia-conf/configure/service/pw-template/fdb/protected-src-mac-violation-action
                    leaf protected-src-mac-violation-action {
                        type types-services:sdp-protected-src-mac-violation-action;
                        description "Action for protected source MAC restriction";
                    }

                    ///nokia-conf/configure/service/pw-template/fdb/mac-learning
                    container mac-learning {
                        description "Enter the mac-learning context";

                        ///nokia-conf/configure/service/pw-template/fdb/mac-learning/learning
                        leaf learning {
                            type boolean;
                            default "true";
                            description "Enable learning of new MAC addresses";
                        }

                        ///nokia-conf/configure/service/pw-template/fdb/mac-learning/aging
                        leaf aging {
                            type boolean;
                            default "true";
                            description "Enable aging of MAC addresses";
                        }

                    } // container mac-learning

                } // container fdb

                ///nokia-conf/configure/service/pw-template/egress
                container egress {
                    description "Enter the egress context";

                    ///nokia-conf/configure/service/pw-template/egress/filter
                    container filter {
                        description "Enter the filter context";

                        ///nokia-conf/configure/service/pw-template/egress/filter/mac
                        leaf mac {
                            type types-sros:named-item-64;
                            description "MAC filter policy name";
                        }

                        ///nokia-conf/configure/service/pw-template/egress/filter/ip
                        leaf ip {
                            type types-sros:named-item-64;
                            description "IPv4 filter policy name";
                        }

                        ///nokia-conf/configure/service/pw-template/egress/filter/ipv6
                        leaf ipv6 {
                            type types-sros:named-item-64;
                            description "IPv6 filter policy name";
                        }

                    } // container filter

                    ///nokia-conf/configure/service/pw-template/egress/qos
                    container qos {
                        description "Enter the qos context";

                        ///nokia-conf/configure/service/pw-template/egress/qos/network
                        container network {
                            description "Enter the network context";

                            ///nokia-conf/configure/service/pw-template/egress/qos/network/policy-name
                            leaf policy-name {
                                type types-sros:named-item-64;
                                description "Network policy ID";
                            }

                            ///nokia-conf/configure/service/pw-template/egress/qos/network/port-redirect-group
                            container port-redirect-group {
                                description "Enter the port-redirect-group context";

                                ///nokia-conf/configure/service/pw-template/egress/qos/network/port-redirect-group/group-name
                                leaf group-name {
                                    type types-sros:named-item;
                                    description "Name of the egress port queue group template";
                                }

                                ///nokia-conf/configure/service/pw-template/egress/qos/network/port-redirect-group/instance
                                leaf instance {
                                    type types-services:qos-qgrp-instance-id;
                                    description "Instance for FP ingress queue group";
                                }

                            } // container port-redirect-group

                        } // container network

                    } // container qos

                    ///nokia-conf/configure/service/pw-template/egress/mfib-allowed-mda-destinations
                    container mfib-allowed-mda-destinations {
                        description "Enter the mfib-allowed-mda-destinations context";

                        ///nokia-conf/configure/service/pw-template/egress/mfib-allowed-mda-destinations/mda
                        list mda {
                            key "mda-id";
                            description "Add a list entry for mda";

                            ///nokia-conf/configure/service/pw-template/egress/mfib-allowed-mda-destinations/mda/mda-id
                            leaf mda-id {
                                type types-isa:slot-mda;
                                description "MFIB allowed MDA destination";
                            }

                        } // list mda

                    } // container mfib-allowed-mda-destinations

                } // container egress

                ///nokia-conf/configure/service/pw-template/sdp-include
                list sdp-include {
                    key "group-name";
                    description "Add a list entry for sdp-include";

                    ///nokia-conf/configure/service/pw-template/sdp-include/group-name
                    leaf group-name {
                        type leafref {
                            path "../../../sdp-group/group-name/group-name";
                        }
                        description "SDP group name";
                    }

                } // list sdp-include

                ///nokia-conf/configure/service/pw-template/sdp-exclude
                list sdp-exclude {
                    key "group-name";
                    description "Add a list entry for sdp-exclude";

                    ///nokia-conf/configure/service/pw-template/sdp-exclude/group-name
                    leaf group-name {
                        type leafref {
                            path "../../../sdp-group/group-name/group-name";
                        }
                        description "SDP group name";
                    }

                } // list sdp-exclude

            } // list pw-template


            ///nokia-conf/configure/service/system
            container system {
                description "Enter the system context";

                ///nokia-conf/configure/service/system/extended-default-qinq-sap-lookup
                leaf extended-default-qinq-sap-lookup {
                    type boolean;
                    description "Control the forwarding of the packets";
                }

                ///nokia-conf/configure/service/system/vpn-gre-source-ip
                leaf vpn-gre-source-ip {
                    type types-sros:ipv4-unicast-address;
                    description "VPN GRE source ip-address";
                }

                ///nokia-conf/configure/service/system/apply-groups
                leaf-list apply-groups {
                    type leafref {
                        path "../../../groups/group/name";
                    }
                    max-elements 8;
                    ordered-by user;
                    description "Apply a configuration group at this level";
                }

                ///nokia-conf/configure/service/system/apply-groups-exclude
                leaf-list apply-groups-exclude {
                    type leafref {
                        path "../../../groups/group/name";
                    }
                    max-elements 8;
                    ordered-by user;
                    description "Exclude a configuration group at this level";
                }

                ///nokia-conf/configure/service/system/pw-port-list
                container pw-port-list {
                    description "Enter the pw-port-list context";

                    ///nokia-conf/configure/service/system/pw-port-list/port
                    list port {
                        key "port-id";
                        description "Add a list entry for port";

                        ///nokia-conf/configure/service/system/pw-port-list/port/port-id
                        leaf port-id {
                            type types-sros:port;
                            description "Port ID";
                        }

                    } // list port

                } // container pw-port-list

                ///nokia-conf/configure/service/system/bgp-auto-rd-range
                container bgp-auto-rd-range {
                    description "Enable the bgp-auto-rd-range context";

                    ///nokia-conf/configure/service/system/bgp-auto-rd-range/ip-address
                    leaf ip-address {
                        type types-sros:ipv4-address;
                        description "IP address used for selecting the route distinguisher";
                    }

                    ///nokia-conf/configure/service/system/bgp-auto-rd-range/apply-groups
                    leaf-list apply-groups {
                        type leafref {
                            path "../../../../groups/group/name";
                        }
                        max-elements 8;
                        ordered-by user;
                        description "Apply a configuration group at this level";
                    }

                    ///nokia-conf/configure/service/system/bgp-auto-rd-range/apply-groups-exclude
                    leaf-list apply-groups-exclude {
                        type leafref {
                            path "../../../../groups/group/name";
                        }
                        max-elements 8;
                        ordered-by user;
                        description "Exclude a configuration group at this level";
                    }

                    ///nokia-conf/configure/service/system/bgp-auto-rd-range/community-value
                    container community-value {
                        description "Enter the community-value context";

                        ///nokia-conf/configure/service/system/bgp-auto-rd-range/community-value/start
                        leaf start {
                            type int32 {
                                range "1..65535";
                            }
                            description "Lower bound of BGP route distinguisher community range";
                        }

                        ///nokia-conf/configure/service/system/bgp-auto-rd-range/community-value/end
                        leaf end {
                            type int32 {
                                range "1..65535";
                            }
                            description "Upper bound of BGP route distinguisher community range";
                        }

                    } // container community-value

                } // container bgp-auto-rd-range

                ///nokia-conf/configure/service/system/fdb
                container fdb {
                    description "Enable the fdb context";

                    ///nokia-conf/configure/service/system/fdb/table-size
                    leaf table-size {
                        type uint32 {
                            range "4095..2047999";
                        }
                        description "Maximum FDB entries in the system";
                    }

                    ///nokia-conf/configure/service/system/fdb/apply-groups
                    leaf-list apply-groups {
                        type leafref {
                            path "../../../../groups/group/name";
                        }
                        max-elements 8;
                        ordered-by user;
                        description "Apply a configuration group at this level";
                    }

                    ///nokia-conf/configure/service/system/fdb/apply-groups-exclude
                    leaf-list apply-groups-exclude {
                        type leafref {
                            path "../../../../groups/group/name";
                        }
                        max-elements 8;
                        ordered-by user;
                        description "Exclude a configuration group at this level";
                    }

                } // container fdb

                ///nokia-conf/configure/service/system/vxlan
                container vxlan {
                    description "Enter the vxlan context";

                    ///nokia-conf/configure/service/system/vxlan/assisted-replication
                    container assisted-replication {
                        description "Enter the assisted-replication context";

                        ///nokia-conf/configure/service/system/vxlan/assisted-replication/ip-address
                        leaf ip-address {
                            type types-sros:ipv4-unicast-address;
                            description "IP address for assisted replication in the router";
                        }

                        ///nokia-conf/configure/service/system/vxlan/assisted-replication/apply-groups
                        leaf-list apply-groups {
                            type leafref {
                                path "../../../../../groups/group/name";
                            }
                            max-elements 8;
                            ordered-by user;
                            description "Apply a configuration group at this level";
                        }

                        ///nokia-conf/configure/service/system/vxlan/assisted-replication/apply-groups-exclude
                        leaf-list apply-groups-exclude {
                            type leafref {
                                path "../../../../../groups/group/name";
                            }
                            max-elements 8;
                            ordered-by user;
                            description "Exclude a configuration group at this level";
                        }

                    } // container assisted-replication

                    ///nokia-conf/configure/service/system/vxlan/tunnel-termination
                    list tunnel-termination {
                        key "ip-address";
                        description "Enter the tunnel-termination list instance";

                        ///nokia-conf/configure/service/system/vxlan/tunnel-termination/ip-address
                        leaf ip-address {
                            type types-sros:ip-unicast-address;
                            description "Non-system IP address that terminates the VXLAN";
                        }

                        ///nokia-conf/configure/service/system/vxlan/tunnel-termination/fpe-id
                        leaf fpe-id {
                            type leafref {
                                path "../../../../../fwd-path-ext/fpe/fpe-id";
                            }
                            sros-ext:immutable;
                            mandatory true;
                            description "FPE id for this entry";
                        }

                        ///nokia-conf/configure/service/system/vxlan/tunnel-termination/apply-groups
                        leaf-list apply-groups {
                            type leafref {
                                path "../../../../../groups/group/name";
                            }
                            max-elements 8;
                            ordered-by user;
                            description "Apply a configuration group at this level";
                        }

                        ///nokia-conf/configure/service/system/vxlan/tunnel-termination/apply-groups-exclude
                        leaf-list apply-groups-exclude {
                            type leafref {
                                path "../../../../../groups/group/name";
                            }
                            max-elements 8;
                            ordered-by user;
                            description "Exclude a configuration group at this level";
                        }

                    } // list tunnel-termination

                } // container vxlan

                ///nokia-conf/configure/service/system/gre-eth-bridged
                container gre-eth-bridged {
                    description "Enter the gre-eth-bridged context";

                    ///nokia-conf/configure/service/system/gre-eth-bridged/tunnel-termination
                    list tunnel-termination {
                        key "ip-address";
                        description "Enter the tunnel-termination list instance";

                        ///nokia-conf/configure/service/system/gre-eth-bridged/tunnel-termination/ip-address
                        leaf ip-address {
                            type types-sros:ip-unicast-address;
                            description "Tunnel end-point IP address in the SR OS node";
                        }

                        ///nokia-conf/configure/service/system/gre-eth-bridged/tunnel-termination/fpe-id
                        leaf fpe-id {
                            type leafref {
                                path "../../../../../fwd-path-ext/fpe/fpe-id";
                            }
                            sros-ext:immutable;
                            mandatory true;
                            description "FPE ID";
                        }

                        ///nokia-conf/configure/service/system/gre-eth-bridged/tunnel-termination/apply-groups
                        leaf-list apply-groups {
                            type leafref {
                                path "../../../../../groups/group/name";
                            }
                            max-elements 8;
                            ordered-by user;
                            description "Apply a configuration group at this level";
                        }

                        ///nokia-conf/configure/service/system/gre-eth-bridged/tunnel-termination/apply-groups-exclude
                        leaf-list apply-groups-exclude {
                            type leafref {
                                path "../../../../../groups/group/name";
                            }
                            max-elements 8;
                            ordered-by user;
                            description "Exclude a configuration group at this level";
                        }

                    } // list tunnel-termination

                } // container gre-eth-bridged

                ///nokia-conf/configure/service/system/bgp
                container bgp {
                    description "Enter the bgp context";

                    ///nokia-conf/configure/service/system/bgp/evpn
                    container evpn {
                        description "Enter the evpn context";

                        ///nokia-conf/configure/service/system/bgp/evpn/etree-leaf-label
                        leaf etree-leaf-label {
                            type boolean;
                            default "false";
                            description "Enable E-Tree leaf label for PE";
                        }

                        ///nokia-conf/configure/service/system/bgp/evpn/etree-leaf-label-value
                        leaf etree-leaf-label-value {
                            type union {
                                type int32 {
                                    range "32..524526";
                                }
                                type enumeration {
                                    enum dynamic                        { value -1; }
                                }
                            }
                            default "dynamic";
                            description "Global E-tree leaf label for PE in EVPN E-Tree services";
                        }

                        ///nokia-conf/configure/service/system/bgp/evpn/route-distinguisher
                        leaf route-distinguisher {
                            type types-services:vpn-route-distinguisher;
                            description "Route distinguisher for ES routes";
                        }

                        ///nokia-conf/configure/service/system/bgp/evpn/ingress-replication-bum-label-block
                        leaf ingress-replication-bum-label-block {
                            type leafref {
                                path "../../../../../router/mpls-labels/reserved-label-block/label-block-name";
                            }
                            description "Reserved label block name for BUM traffic";
                        }

                        ///nokia-conf/configure/service/system/bgp/evpn/multicast-leave-sync-propagation
                        leaf multicast-leave-sync-propagation {
                            type int32 {
                                range "0..300";
                            }
                            units "seconds";
                            default "5";
                            description "Multicast leave group synchronization delay";
                        }

                        ///nokia-conf/configure/service/system/bgp/evpn/ethernet-segment
                        list ethernet-segment {
                            key "ethernet-segment-name";
                            max-elements 4095;
                            description "Enter the ethernet-segment list instance";

                            ///nokia-conf/configure/service/system/bgp/evpn/ethernet-segment/ethernet-segment-name
                            leaf ethernet-segment-name {
                                type types-sros:named-item;
                                description "Specify name for Ethernet segment";
                            }

                            ///nokia-conf/configure/service/system/bgp/evpn/ethernet-segment/admin-state
                            leaf admin-state {
                                type types-sros:admin-state;
                                default "disable";
                                description "Administrative state of the Ethernet segment instance";
                            }

                            ///nokia-conf/configure/service/system/bgp/evpn/ethernet-segment/type
                            leaf type {
                                type enumeration {
                                    enum none                           { value 1; }
                                    enum virtual                        { value 2; }
                                }
                                sros-ext:immutable;
                                default "none";
                                description "Ethernet Segment type";
                            }

                            ///nokia-conf/configure/service/system/bgp/evpn/ethernet-segment/esi
                            leaf esi {
                                type types-services:ethernet-segment-id-mac-based;
                                sros-ext:auto-restart-to-modify;
                                description "Ethernet segment identifier";
                            }

                            ///nokia-conf/configure/service/system/bgp/evpn/ethernet-segment/orig-ip
                            leaf orig-ip {
                                type types-sros:ip-unicast-address;
                                sros-ext:auto-restart-to-modify;
                                description "Originating IP address advertised in the ES route";
                            }

                            ///nokia-conf/configure/service/system/bgp/evpn/ethernet-segment/route-next-hop
                            leaf route-next-hop {
                                type types-sros:ip-unicast-address;
                                sros-ext:auto-restart-to-modify;
                                description "Next-hop IP address for ES and AD per ES routes";
                            }

                            ///nokia-conf/configure/service/system/bgp/evpn/ethernet-segment/multi-homing-mode
                            leaf multi-homing-mode {
                                type enumeration {
                                    enum none                           { value 0; }
                                    enum single-active                  { value 1; }
                                    enum single-active-no-esi-label     { value 2; }
                                    enum all-active                     { value 3; }
                                }
                                sros-ext:auto-restart-to-modify;
                                default "none";
                                description "Multi-homing mode of the Ethernet segment";
                            }

                            ///nokia-conf/configure/service/system/bgp/evpn/ethernet-segment/oper-group
                            leaf oper-group {
                                type leafref {
                                    path "../../../../../oper-group/name";
                                }
                                description "Operational group ID";
                            }

                            ///nokia-conf/configure/service/system/bgp/evpn/ethernet-segment/auto-esi
                            leaf auto-esi {
                                type enumeration {
                                    enum none                           { value 0; }
                                    enum type-1                         { value 1; }
                                }
                                sros-ext:auto-restart-to-modify;
                                default "none";
                                description "EVPN Ethernet segment auto-ESI type";
                            }

                            ///nokia-conf/configure/service/system/bgp/evpn/ethernet-segment/ac-df-capability
                            leaf ac-df-capability {
                                type enumeration {
                                    enum include                        { value 0; }
                                    enum exclude                        { value 1; }
                                }
                                sros-ext:auto-restart-to-modify;
                                default "include";
                                description "AC-influenced DF election capability";
                            }

                            ///nokia-conf/configure/service/system/bgp/evpn/ethernet-segment/apply-groups
                            leaf-list apply-groups {
                                type leafref {
                                    path "../../../../../../groups/group/name";
                                }
                                max-elements 8;
                                ordered-by user;
                                description "Apply a configuration group at this level";
                            }

                            ///nokia-conf/configure/service/system/bgp/evpn/ethernet-segment/apply-groups-exclude
                            leaf-list apply-groups-exclude {
                                type leafref {
                                    path "../../../../../../groups/group/name";
                                }
                                max-elements 8;
                                ordered-by user;
                                description "Exclude a configuration group at this level";
                            }

                            ///nokia-conf/configure/service/system/bgp/evpn/ethernet-segment/df-election
                            container df-election {
                                description "Enter the df-election context";

                                ///nokia-conf/configure/service/system/bgp/evpn/ethernet-segment/df-election/es-activation-timer
                                leaf es-activation-timer {
                                    type int32 {
                                        range "0..100";
                                    }
                                    units "seconds";
                                    description "Activation timer per Ethernet segment";
                                }

                                ///nokia-conf/configure/service/system/bgp/evpn/ethernet-segment/df-election/service-carving-mode
                                leaf service-carving-mode {
                                    type enumeration {
                                        enum auto                           { value 1; }
                                        enum manual                         { value 2; }
                                        enum off                            { value 3; }
                                    }
                                    sros-ext:auto-restart-to-modify;
                                    default "auto";
                                    description "Mode of service carving enabled per EVPN associated with this Ethernet segment entry";
                                }

                                ///nokia-conf/configure/service/system/bgp/evpn/ethernet-segment/df-election/manual
                                container manual {
                                    description "Enter the manual context";

                                    ///nokia-conf/configure/service/system/bgp/evpn/ethernet-segment/df-election/manual/evi
                                    list evi {
                                        key "start";
                                        description "Enter the evi list instance";

                                        ///nokia-conf/configure/service/system/bgp/evpn/ethernet-segment/df-election/manual/evi/start
                                        leaf start {
                                            type uint32 {
                                                range "1..16777215";
                                            }
                                            description "Lower bound of EVI range for which the PE is primary";
                                        }

                                        ///nokia-conf/configure/service/system/bgp/evpn/ethernet-segment/df-election/manual/evi/end
                                        leaf end {
                                            type uint32 {
                                                range "1..16777215";
                                            }
                                            mandatory true;
                                            description "Upper bound of EVI range for which the PE is primary";
                                        }

                                        ///nokia-conf/configure/service/system/bgp/evpn/ethernet-segment/df-election/manual/evi/apply-groups
                                        leaf-list apply-groups {
                                            type leafref {
                                                path "../../../../../../../../../groups/group/name";
                                            }
                                            max-elements 8;
                                            ordered-by user;
                                            description "Apply a configuration group at this level";
                                        }

                                        ///nokia-conf/configure/service/system/bgp/evpn/ethernet-segment/df-election/manual/evi/apply-groups-exclude
                                        leaf-list apply-groups-exclude {
                                            type leafref {
                                                path "../../../../../../../../../groups/group/name";
                                            }
                                            max-elements 8;
                                            ordered-by user;
                                            description "Exclude a configuration group at this level";
                                        }

                                    } // list evi

                                    ///nokia-conf/configure/service/system/bgp/evpn/ethernet-segment/df-election/manual/isid
                                    list isid {
                                        key "start";
                                        description "Enter the isid list instance";

                                        ///nokia-conf/configure/service/system/bgp/evpn/ethernet-segment/df-election/manual/isid/start
                                        leaf start {
                                            type types-sros:svc-isid-non-zero;
                                            description "Lower bound of ISID range for which the PE is primary";
                                        }

                                        ///nokia-conf/configure/service/system/bgp/evpn/ethernet-segment/df-election/manual/isid/end
                                        leaf end {
                                            type types-sros:svc-isid-non-zero;
                                            mandatory true;
                                            description "Upper bound of ISID range for which the PE is primary";
                                        }

                                        ///nokia-conf/configure/service/system/bgp/evpn/ethernet-segment/df-election/manual/isid/apply-groups
                                        leaf-list apply-groups {
                                            type leafref {
                                                path "../../../../../../../../../groups/group/name";
                                            }
                                            max-elements 8;
                                            ordered-by user;
                                            description "Apply a configuration group at this level";
                                        }

                                        ///nokia-conf/configure/service/system/bgp/evpn/ethernet-segment/df-election/manual/isid/apply-groups-exclude
                                        leaf-list apply-groups-exclude {
                                            type leafref {
                                                path "../../../../../../../../../groups/group/name";
                                            }
                                            max-elements 8;
                                            ordered-by user;
                                            description "Exclude a configuration group at this level";
                                        }

                                    } // list isid

                                    ///nokia-conf/configure/service/system/bgp/evpn/ethernet-segment/df-election/manual/preference
                                    container preference {
                                        presence "Enable the preference context";
                                        description "Enable the preference context";

                                        ///nokia-conf/configure/service/system/bgp/evpn/ethernet-segment/df-election/manual/preference/mode
                                        leaf mode {
                                            type enumeration {
                                                enum revertive                      { value 1; }
                                                enum non-revertive                  { value 2; }
                                            }
                                            sros-ext:immutable;
                                            default "revertive";
                                            description "Method used to elect the DF";
                                        }

                                        ///nokia-conf/configure/service/system/bgp/evpn/ethernet-segment/df-election/manual/preference/value
                                        leaf value {
                                            type uint32 {
                                                range "0..65535";
                                            }
                                            default "32767";
                                            description "Preference that is used to elect the designated forwarder";
                                        }

                                        ///nokia-conf/configure/service/system/bgp/evpn/ethernet-segment/df-election/manual/preference/apply-groups
                                        leaf-list apply-groups {
                                            type leafref {
                                                path "../../../../../../../../../groups/group/name";
                                            }
                                            max-elements 8;
                                            ordered-by user;
                                            description "Apply a configuration group at this level";
                                        }

                                        ///nokia-conf/configure/service/system/bgp/evpn/ethernet-segment/df-election/manual/preference/apply-groups-exclude
                                        leaf-list apply-groups-exclude {
                                            type leafref {
                                                path "../../../../../../../../../groups/group/name";
                                            }
                                            max-elements 8;
                                            ordered-by user;
                                            description "Exclude a configuration group at this level";
                                        }

                                    } // container preference

                                } // container manual

                            } // container df-election

                            ///nokia-conf/configure/service/system/bgp/evpn/ethernet-segment/association
                            container association {
                                description "Enter the association context";

                                ///nokia-conf/configure/service/system/bgp/evpn/ethernet-segment/association/object
                                choice object {
                                    description "Object being multi homed with this Ethernet segment";
                                    ///nokia-conf/configure/service/system/bgp/evpn/ethernet-segment/association/object/port
                                    case port {

                                        ///nokia-conf/configure/service/system/bgp/evpn/ethernet-segment/association/object/port/port
                                        list port {
                                            key "port-id";
                                            max-elements 1;
                                            description "Enter the port list instance";

                                            ///nokia-conf/configure/service/system/bgp/evpn/ethernet-segment/association/object/port/port/port-id
                                            leaf port-id {
                                                type leafref {
                                                    path "../../../../../../../../port/port-id";
                                                }
                                                description "Port multi-homed with this Ethernet segment entry";
                                            }

                                            ///nokia-conf/configure/service/system/bgp/evpn/ethernet-segment/association/object/port/port/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/port/port/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/port/port/virtual-ranges
                                            container virtual-ranges {
                                                when "../../../type = 'virtual'" {
                                                    description "virtual-ranges allowed only on virtual ethernet-segments";
                                                }
                                                description "Enter the virtual-ranges context";

                                                ///nokia-conf/configure/service/system/bgp/evpn/ethernet-segment/association/object/port/port/virtual-ranges/dot1q
                                                container dot1q {
                                                    description "Enter the dot1q context";

                                                    ///nokia-conf/configure/service/system/bgp/evpn/ethernet-segment/association/object/port/port/virtual-ranges/dot1q/q-tag
                                                    list q-tag {
                                                        key "start";
                                                        max-elements 8;
                                                        description "Enter the q-tag list instance";

                                                        ///nokia-conf/configure/service/system/bgp/evpn/ethernet-segment/association/object/port/port/virtual-ranges/dot1q/q-tag/start
                                                        leaf start {
                                                            type types-services:ethernet-segment-vlan-range-encap;
                                                            description "Lower bound of the q-tag VLAN ID range";
                                                        }

                                                        ///nokia-conf/configure/service/system/bgp/evpn/ethernet-segment/association/object/port/port/virtual-ranges/dot1q/q-tag/end
                                                        leaf end {
                                                            type types-services:ethernet-segment-vlan-range-encap;
                                                            mandatory true;
                                                            description "Upper bound of the q-tag VLAN ID range";
                                                        }

                                                        ///nokia-conf/configure/service/system/bgp/evpn/ethernet-segment/association/object/port/port/virtual-ranges/dot1q/q-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/port/port/virtual-ranges/dot1q/q-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                ///nokia-conf/configure/service/system/bgp/evpn/ethernet-segment/association/object/port/port/virtual-ranges/qinq
                                                container qinq {
                                                    description "Enter the qinq context";

                                                    ///nokia-conf/configure/service/system/bgp/evpn/ethernet-segment/association/object/port/port/virtual-ranges/qinq/s-tag-c-tag
                                                    list s-tag-c-tag {
                                                        key "s-tag c-tag-start";
                                                        max-elements 8;
                                                        description "Enter the s-tag-c-tag list instance";

                                                        ///nokia-conf/configure/service/system/bgp/evpn/ethernet-segment/association/object/port/port/virtual-ranges/qinq/s-tag-c-tag/s-tag
                                                        leaf s-tag {
                                                            type types-services:ethernet-segment-vlan-range-encap-with-null;
                                                            description "Starting value of the qinq s-tag range associated with a virtual ethernet segment";
                                                        }

                                                        ///nokia-conf/configure/service/system/bgp/evpn/ethernet-segment/association/object/port/port/virtual-ranges/qinq/s-tag-c-tag/c-tag-start
                                                        leaf c-tag-start {
                                                            type types-services:ethernet-segment-vlan-range-encap-with-null;
                                                            description "Starting value of the qinq c-tag range";
                                                        }

                                                        ///nokia-conf/configure/service/system/bgp/evpn/ethernet-segment/association/object/port/port/virtual-ranges/qinq/s-tag-c-tag/c-tag-end
                                                        leaf c-tag-end {
                                                            type types-services:ethernet-segment-vlan-range-encap-with-null;
                                                            mandatory true;
                                                            description "End value of the qinq c-tag range";
                                                        }

                                                        ///nokia-conf/configure/service/system/bgp/evpn/ethernet-segment/association/object/port/port/virtual-ranges/qinq/s-tag-c-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/port/port/virtual-ranges/qinq/s-tag-c-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    ///nokia-conf/configure/service/system/bgp/evpn/ethernet-segment/association/object/port/port/virtual-ranges/qinq/s-tag
                                                    list s-tag {
                                                        key "start";
                                                        max-elements 8;
                                                        description "Enter the s-tag list instance";

                                                        ///nokia-conf/configure/service/system/bgp/evpn/ethernet-segment/association/object/port/port/virtual-ranges/qinq/s-tag/start
                                                        leaf start {
                                                            type types-services:ethernet-segment-vlan-range-encap;
                                                            description "Lower bound of the s-tag VLAN ID range";
                                                        }

                                                        ///nokia-conf/configure/service/system/bgp/evpn/ethernet-segment/association/object/port/port/virtual-ranges/qinq/s-tag/end
                                                        leaf end {
                                                            type types-services:ethernet-segment-vlan-range-encap;
                                                            mandatory true;
                                                            description "Upper bound of the s-tag VLAN ID range";
                                                        }

                                                        ///nokia-conf/configure/service/system/bgp/evpn/ethernet-segment/association/object/port/port/virtual-ranges/qinq/s-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/port/port/virtual-ranges/qinq/s-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list port

                                    }
                                    ///nokia-conf/configure/service/system/bgp/evpn/ethernet-segment/association/object/lag
                                    case lag {

                                        ///nokia-conf/configure/service/system/bgp/evpn/ethernet-segment/association/object/lag/lag
                                        list lag {
                                            key "lag-name";
                                            max-elements 1;
                                            description "Enter the lag list instance";

                                            ///nokia-conf/configure/service/system/bgp/evpn/ethernet-segment/association/object/lag/lag/lag-name
                                            leaf lag-name {
                                                type leafref {
                                                    path "../../../../../../../../lag/lag-name";
                                                }
                                                description "LAG multi-homed with the Ethernet segment entry";
                                            }

                                            ///nokia-conf/configure/service/system/bgp/evpn/ethernet-segment/association/object/lag/lag/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/lag/lag/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/lag/lag/virtual-ranges
                                            container virtual-ranges {
                                                when "../../../type = 'virtual'" {
                                                    description "virtual-ranges allowed only on virtual ethernet-segments";
                                                }
                                                description "Enter the virtual-ranges context";

                                                ///nokia-conf/configure/service/system/bgp/evpn/ethernet-segment/association/object/lag/lag/virtual-ranges/dot1q
                                                container dot1q {
                                                    description "Enter the dot1q context";

                                                    ///nokia-conf/configure/service/system/bgp/evpn/ethernet-segment/association/object/lag/lag/virtual-ranges/dot1q/q-tag
                                                    list q-tag {
                                                        key "start";
                                                        max-elements 8;
                                                        description "Enter the q-tag list instance";

                                                        ///nokia-conf/configure/service/system/bgp/evpn/ethernet-segment/association/object/lag/lag/virtual-ranges/dot1q/q-tag/start
                                                        leaf start {
                                                            type types-services:ethernet-segment-vlan-range-encap;
                                                            description "Lower bound of the q-tag VLAN ID range";
                                                        }

                                                        ///nokia-conf/configure/service/system/bgp/evpn/ethernet-segment/association/object/lag/lag/virtual-ranges/dot1q/q-tag/end
                                                        leaf end {
                                                            type types-services:ethernet-segment-vlan-range-encap;
                                                            mandatory true;
                                                            description "Upper bound of the q-tag VLAN ID range";
                                                        }

                                                        ///nokia-conf/configure/service/system/bgp/evpn/ethernet-segment/association/object/lag/lag/virtual-ranges/dot1q/q-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/lag/lag/virtual-ranges/dot1q/q-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                ///nokia-conf/configure/service/system/bgp/evpn/ethernet-segment/association/object/lag/lag/virtual-ranges/qinq
                                                container qinq {
                                                    description "Enter the qinq context";

                                                    ///nokia-conf/configure/service/system/bgp/evpn/ethernet-segment/association/object/lag/lag/virtual-ranges/qinq/s-tag-c-tag
                                                    list s-tag-c-tag {
                                                        key "s-tag c-tag-start";
                                                        max-elements 8;
                                                        description "Enter the s-tag-c-tag list instance";

                                                        ///nokia-conf/configure/service/system/bgp/evpn/ethernet-segment/association/object/lag/lag/virtual-ranges/qinq/s-tag-c-tag/s-tag
                                                        leaf s-tag {
                                                            type types-services:ethernet-segment-vlan-range-encap-with-null;
                                                            description "Starting value of the qinq s-tag range associated with a virtual ethernet segment";
                                                        }

                                                        ///nokia-conf/configure/service/system/bgp/evpn/ethernet-segment/association/object/lag/lag/virtual-ranges/qinq/s-tag-c-tag/c-tag-start
                                                        leaf c-tag-start {
                                                            type types-services:ethernet-segment-vlan-range-encap-with-null;
                                                            description "Starting value of the qinq c-tag range";
                                                        }

                                                        ///nokia-conf/configure/service/system/bgp/evpn/ethernet-segment/association/object/lag/lag/virtual-ranges/qinq/s-tag-c-tag/c-tag-end
                                                        leaf c-tag-end {
                                                            type types-services:ethernet-segment-vlan-range-encap-with-null;
                                                            mandatory true;
                                                            description "End value of the qinq c-tag range";
                                                        }

                                                        ///nokia-conf/configure/service/system/bgp/evpn/ethernet-segment/association/object/lag/lag/virtual-ranges/qinq/s-tag-c-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/lag/lag/virtual-ranges/qinq/s-tag-c-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    ///nokia-conf/configure/service/system/bgp/evpn/ethernet-segment/association/object/lag/lag/virtual-ranges/qinq/s-tag
                                                    list s-tag {
                                                        key "start";
                                                        max-elements 8;
                                                        description "Enter the s-tag list instance";

                                                        ///nokia-conf/configure/service/system/bgp/evpn/ethernet-segment/association/object/lag/lag/virtual-ranges/qinq/s-tag/start
                                                        leaf start {
                                                            type types-services:ethernet-segment-vlan-range-encap;
                                                            description "Lower bound of the s-tag VLAN ID range";
                                                        }

                                                        ///nokia-conf/configure/service/system/bgp/evpn/ethernet-segment/association/object/lag/lag/virtual-ranges/qinq/s-tag/end
                                                        leaf end {
                                                            type types-services:ethernet-segment-vlan-range-encap;
                                                            mandatory true;
                                                            description "Upper bound of the s-tag VLAN ID range";
                                                        }

                                                        ///nokia-conf/configure/service/system/bgp/evpn/ethernet-segment/association/object/lag/lag/virtual-ranges/qinq/s-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/lag/lag/virtual-ranges/qinq/s-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list lag

                                    }
                                    ///nokia-conf/configure/service/system/bgp/evpn/ethernet-segment/association/object/sdp
                                    case sdp {

                                        ///nokia-conf/configure/service/system/bgp/evpn/ethernet-segment/association/object/sdp/sdp
                                        list sdp {
                                            key "sdp-id";
                                            max-elements 1;
                                            description "Enter the sdp list instance";

                                            ///nokia-conf/configure/service/system/bgp/evpn/ethernet-segment/association/object/sdp/sdp/sdp-id
                                            leaf sdp-id {
                                                type leafref {
                                                    path "../../../../../../../sdp/sdp-id";
                                                }
                                                description "Sdp multi-homed with this Ethernet segment entry";
                                            }

                                            ///nokia-conf/configure/service/system/bgp/evpn/ethernet-segment/association/object/sdp/sdp/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/sdp/sdp/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/sdp/sdp/virtual-ranges
                                            container virtual-ranges {
                                                when "../../../type = 'virtual'" {
                                                    description "virtual-ranges allowed only on virtual ethernet-segments";
                                                }
                                                description "Enter the virtual-ranges context";

                                                ///nokia-conf/configure/service/system/bgp/evpn/ethernet-segment/association/object/sdp/sdp/virtual-ranges/vc-id
                                                list vc-id {
                                                    key "start";
                                                    max-elements 8;
                                                    description "Enter the vc-id list instance";

                                                    ///nokia-conf/configure/service/system/bgp/evpn/ethernet-segment/association/object/sdp/sdp/virtual-ranges/vc-id/start
                                                    leaf start {
                                                        type types-services:vc-id;
                                                        description "Lower bound of the VC-ID range";
                                                    }

                                                    ///nokia-conf/configure/service/system/bgp/evpn/ethernet-segment/association/object/sdp/sdp/virtual-ranges/vc-id/end
                                                    leaf end {
                                                        type types-services:vc-id;
                                                        mandatory true;
                                                        description "Upper bound of the VC-ID range";
                                                    }

                                                    ///nokia-conf/configure/service/system/bgp/evpn/ethernet-segment/association/object/sdp/sdp/virtual-ranges/vc-id/apply-groups
                                                    leaf-list apply-groups {
                                                        type leafref {
                                                            path "../../../../../../../../../../groups/group/name";
                                                        }
                                                        max-elements 8;
                                                        ordered-by user;
                                                        description "Apply a configuration group at this level";
                                                    }

                                                    ///nokia-conf/configure/service/system/bgp/evpn/ethernet-segment/association/object/sdp/sdp/virtual-ranges/vc-id/apply-groups-exclude
                                                    leaf-list apply-groups-exclude {
                                                        type leafref {
                                                            path "../../../../../../../../../../groups/group/name";
                                                        }
                                                        max-elements 8;
                                                        ordered-by user;
                                                        description "Exclude a configuration group at this level";
                                                    }

                                                } // list vc-id

                                            } // container virtual-ranges

                                        } // list sdp

                                    }
                                    ///nokia-conf/configure/service/system/bgp/evpn/ethernet-segment/association/object/network-interconnect-vxlan
                                    case network-interconnect-vxlan {

                                        ///nokia-conf/configure/service/system/bgp/evpn/ethernet-segment/association/object/network-interconnect-vxlan/network-interconnect-vxlan
                                        list network-interconnect-vxlan {
                                            when "../../type = 'virtual'" {
                                                description "network-interconnect-vxlan allowed only on virtual ethernet-segments";
                                            }
                                            key "network-interconnect-vxlan-id";
                                            max-elements 1;
                                            description "Enter the network-interconnect-vxlan list instance";

                                            ///nokia-conf/configure/service/system/bgp/evpn/ethernet-segment/association/object/network-interconnect-vxlan/network-interconnect-vxlan/network-interconnect-vxlan-id
                                            leaf network-interconnect-vxlan-id {
                                                type uint32 {
                                                    range "1";
                                                }
                                                description "VXLAN instance ID associated with the virtual ES";
                                            }

                                            ///nokia-conf/configure/service/system/bgp/evpn/ethernet-segment/association/object/network-interconnect-vxlan/network-interconnect-vxlan/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/network-interconnect-vxlan/network-interconnect-vxlan/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/network-interconnect-vxlan/network-interconnect-vxlan/virtual-ranges
                                            container virtual-ranges {
                                                description "Enter the virtual-ranges context";

                                                ///nokia-conf/configure/service/system/bgp/evpn/ethernet-segment/association/object/network-interconnect-vxlan/network-interconnect-vxlan/virtual-ranges/service-id
                                                list service-id {
                                                    key "start";
                                                    max-elements 8;
                                                    description "Enter the service-id list instance";

                                                    ///nokia-conf/configure/service/system/bgp/evpn/ethernet-segment/association/object/network-interconnect-vxlan/network-interconnect-vxlan/virtual-ranges/service-id/start
                                                    leaf start {
                                                        type types-services:external-service-id;
                                                        description "Lower bound of the service ID range";
                                                    }

                                                    ///nokia-conf/configure/service/system/bgp/evpn/ethernet-segment/association/object/network-interconnect-vxlan/network-interconnect-vxlan/virtual-ranges/service-id/end
                                                    leaf end {
                                                        type types-services:external-service-id;
                                                        mandatory true;
                                                        description "Upper bound of the service ID range";
                                                    }

                                                    ///nokia-conf/configure/service/system/bgp/evpn/ethernet-segment/association/object/network-interconnect-vxlan/network-interconnect-vxlan/virtual-ranges/service-id/apply-groups
                                                    leaf-list apply-groups {
                                                        type leafref {
                                                            path "../../../../../../../../../../groups/group/name";
                                                        }
                                                        max-elements 8;
                                                        ordered-by user;
                                                        description "Apply a configuration group at this level";
                                                    }

                                                    ///nokia-conf/configure/service/system/bgp/evpn/ethernet-segment/association/object/network-interconnect-vxlan/network-interconnect-vxlan/virtual-ranges/service-id/apply-groups-exclude
                                                    leaf-list apply-groups-exclude {
                                                        type leafref {
                                                            path "../../../../../../../../../../groups/group/name";
                                                        }
                                                        max-elements 8;
                                                        ordered-by user;
                                                        description "Exclude a configuration group at this level";
                                                    }

                                                } // list service-id

                                            } // container virtual-ranges

                                        } // list network-interconnect-vxlan

                                    }
                                    ///nokia-conf/configure/service/system/bgp/evpn/ethernet-segment/association/object/pw-port
                                    case pw-port {

                                        ///nokia-conf/configure/service/system/bgp/evpn/ethernet-segment/association/object/pw-port/pw-port
                                        list pw-port {
                                            key "pw-port-id";
                                            max-elements 1;
                                            description "Enter the pw-port list instance";

                                            ///nokia-conf/configure/service/system/bgp/evpn/ethernet-segment/association/object/pw-port/pw-port/pw-port-id
                                            leaf pw-port-id {
                                                type leafref {
                                                    path "../../../../../../../../pw-port/pw-port-id";
                                                }
                                                description "Pw-port multi-homed with this Ethernet segment entry";
                                            }

                                            ///nokia-conf/configure/service/system/bgp/evpn/ethernet-segment/association/object/pw-port/pw-port/pw-port-headend
                                            leaf pw-port-headend {
                                                type boolean;
                                                sros-ext:immutable;
                                                default "false";
                                                description "Control state of PW SAPs on PW port using EVPN";
                                            }

                                            ///nokia-conf/configure/service/system/bgp/evpn/ethernet-segment/association/object/pw-port/pw-port/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/pw-port/pw-port/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/pw-port/pw-port/virtual-ranges
                                            container virtual-ranges {
                                                when "../../../type = 'virtual'" {
                                                    description "virtual-ranges allowed only on virtual ethernet-segments";
                                                }
                                                description "Enter the virtual-ranges context";

                                                ///nokia-conf/configure/service/system/bgp/evpn/ethernet-segment/association/object/pw-port/pw-port/virtual-ranges/dot1q
                                                container dot1q {
                                                    description "Enter the dot1q context";

                                                    ///nokia-conf/configure/service/system/bgp/evpn/ethernet-segment/association/object/pw-port/pw-port/virtual-ranges/dot1q/q-tag
                                                    list q-tag {
                                                        key "start";
                                                        max-elements 8;
                                                        description "Enter the q-tag list instance";

                                                        ///nokia-conf/configure/service/system/bgp/evpn/ethernet-segment/association/object/pw-port/pw-port/virtual-ranges/dot1q/q-tag/start
                                                        leaf start {
                                                            type types-services:ethernet-segment-vlan-range-encap;
                                                            description "Lower bound of the q-tag VLAN ID range";
                                                        }

                                                        ///nokia-conf/configure/service/system/bgp/evpn/ethernet-segment/association/object/pw-port/pw-port/virtual-ranges/dot1q/q-tag/end
                                                        leaf end {
                                                            type types-services:ethernet-segment-vlan-range-encap;
                                                            mandatory true;
                                                            description "Upper bound of the q-tag VLAN ID range";
                                                        }

                                                        ///nokia-conf/configure/service/system/bgp/evpn/ethernet-segment/association/object/pw-port/pw-port/virtual-ranges/dot1q/q-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/pw-port/pw-port/virtual-ranges/dot1q/q-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list q-tag

                                                } // container dot1q

                                                ///nokia-conf/configure/service/system/bgp/evpn/ethernet-segment/association/object/pw-port/pw-port/virtual-ranges/qinq
                                                container qinq {
                                                    description "Enter the qinq context";

                                                    ///nokia-conf/configure/service/system/bgp/evpn/ethernet-segment/association/object/pw-port/pw-port/virtual-ranges/qinq/s-tag-c-tag
                                                    list s-tag-c-tag {
                                                        key "s-tag c-tag-start";
                                                        max-elements 8;
                                                        description "Enter the s-tag-c-tag list instance";

                                                        ///nokia-conf/configure/service/system/bgp/evpn/ethernet-segment/association/object/pw-port/pw-port/virtual-ranges/qinq/s-tag-c-tag/s-tag
                                                        leaf s-tag {
                                                            type types-services:ethernet-segment-vlan-range-encap-with-null;
                                                            description "Starting value of the qinq s-tag range associated with a virtual ethernet segment";
                                                        }

                                                        ///nokia-conf/configure/service/system/bgp/evpn/ethernet-segment/association/object/pw-port/pw-port/virtual-ranges/qinq/s-tag-c-tag/c-tag-start
                                                        leaf c-tag-start {
                                                            type types-services:ethernet-segment-vlan-range-encap-with-null;
                                                            description "Starting value of the qinq c-tag range";
                                                        }

                                                        ///nokia-conf/configure/service/system/bgp/evpn/ethernet-segment/association/object/pw-port/pw-port/virtual-ranges/qinq/s-tag-c-tag/c-tag-end
                                                        leaf c-tag-end {
                                                            type types-services:ethernet-segment-vlan-range-encap-with-null;
                                                            mandatory true;
                                                            description "End value of the qinq c-tag range";
                                                        }

                                                        ///nokia-conf/configure/service/system/bgp/evpn/ethernet-segment/association/object/pw-port/pw-port/virtual-ranges/qinq/s-tag-c-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/pw-port/pw-port/virtual-ranges/qinq/s-tag-c-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag-c-tag

                                                    ///nokia-conf/configure/service/system/bgp/evpn/ethernet-segment/association/object/pw-port/pw-port/virtual-ranges/qinq/s-tag
                                                    list s-tag {
                                                        key "start";
                                                        max-elements 8;
                                                        description "Enter the s-tag list instance";

                                                        ///nokia-conf/configure/service/system/bgp/evpn/ethernet-segment/association/object/pw-port/pw-port/virtual-ranges/qinq/s-tag/start
                                                        leaf start {
                                                            type types-services:ethernet-segment-vlan-range-encap;
                                                            description "Lower bound of the s-tag VLAN ID range";
                                                        }

                                                        ///nokia-conf/configure/service/system/bgp/evpn/ethernet-segment/association/object/pw-port/pw-port/virtual-ranges/qinq/s-tag/end
                                                        leaf end {
                                                            type types-services:ethernet-segment-vlan-range-encap;
                                                            mandatory true;
                                                            description "Upper bound of the s-tag VLAN ID range";
                                                        }

                                                        ///nokia-conf/configure/service/system/bgp/evpn/ethernet-segment/association/object/pw-port/pw-port/virtual-ranges/qinq/s-tag/apply-groups
                                                        leaf-list apply-groups {
                                                            type leafref {
                                                                path "../../../../../../../../../../../groups/group/name";
                                                            }
                                                            max-elements 8;
                                                            ordered-by user;
                                                            description "Apply a configuration group at this level";
                                                        }

                                                        ///nokia-conf/configure/service/system/bgp/evpn/ethernet-segment/association/object/pw-port/pw-port/virtual-ranges/qinq/s-tag/apply-groups-exclude
                                                        leaf-list apply-groups-exclude {
                                                            type leafref {
                                                                path "../../../../../../../../../../../groups/group/name";
                                                            }
                                                            max-elements 8;
                                                            ordered-by user;
                                                            description "Exclude a configuration group at this level";
                                                        }

                                                    } // list s-tag

                                                } // container qinq

                                            } // container virtual-ranges

                                        } // list pw-port

                                    }
                                    ///nokia-conf/configure/service/system/bgp/evpn/ethernet-segment/association/object/vprn-next-hop
                                    case vprn-next-hop {

                                        ///nokia-conf/configure/service/system/bgp/evpn/ethernet-segment/association/object/vprn-next-hop/vprn-next-hop
                                        list vprn-next-hop {
                                            when "../../type = 'virtual'" {
                                                description "vprn-next-hop allowed only on virtual ethernet-segments";
                                            }
                                            key "ip-address";
                                            max-elements 1;
                                            description "Enter the vprn-next-hop list instance";

                                            ///nokia-conf/configure/service/system/bgp/evpn/ethernet-segment/association/object/vprn-next-hop/vprn-next-hop/ip-address
                                            leaf ip-address {
                                                type types-sros:ip-address;
                                                description "VPRN next-hop address";
                                            }

                                            ///nokia-conf/configure/service/system/bgp/evpn/ethernet-segment/association/object/vprn-next-hop/vprn-next-hop/apply-groups
                                            leaf-list apply-groups {
                                                type leafref {
                                                    path "../../../../../../../../groups/group/name";
                                                }
                                                max-elements 8;
                                                ordered-by user;
                                                description "Apply a configuration group at this level";
                                            }

                                            ///nokia-conf/configure/service/system/bgp/evpn/ethernet-segment/association/object/vprn-next-hop/vprn-next-hop/apply-groups-exclude
                                            leaf-list apply-groups-exclude {
                                                type leafref {
                                                    path "../../../../../../../../groups/group/name";
                                                }
                                                max-elements 8;
                                                ordered-by user;
                                                description "Exclude a configuration group at this level";
                                            }

                                            ///nokia-conf/configure/service/system/bgp/evpn/ethernet-segment/association/object/vprn-next-hop/vprn-next-hop/virtual-ranges
                                            container virtual-ranges {
                                                description "Enter the virtual-ranges context";

                                                ///nokia-conf/configure/service/system/bgp/evpn/ethernet-segment/association/object/vprn-next-hop/vprn-next-hop/virtual-ranges/evi
                                                list evi {
                                                    key "start";
                                                    max-elements 1;
                                                    description "Add a list entry for evi";

                                                    ///nokia-conf/configure/service/system/bgp/evpn/ethernet-segment/association/object/vprn-next-hop/vprn-next-hop/virtual-ranges/evi/start
                                                    leaf start {
                                                        type uint32 {
                                                            range "1..16777215";
                                                        }
                                                        description "EVI range start information";
                                                    }

                                                } // list evi

                                            } // container virtual-ranges

                                        } // list vprn-next-hop

                                    }
                                }
                            } // container association

                            ///nokia-conf/configure/service/system/bgp/evpn/ethernet-segment/pbb
                            container pbb {
                                description "Enter the pbb context";

                                ///nokia-conf/configure/service/system/bgp/evpn/ethernet-segment/pbb/source-bmac-lsb
                                leaf source-bmac-lsb {
                                    type types-services:bmac-lsb-no-zero;
                                    sros-ext:auto-restart-to-modify;
                                    description "Least significant bytes of the B-MAC for packet source";
                                }

                                ///nokia-conf/configure/service/system/bgp/evpn/ethernet-segment/pbb/es-bmac-table-size
                                leaf es-bmac-table-size {
                                    type uint32 {
                                        range "1..511999";
                                    }
                                    default "8";
                                    description "Size of virtual backbone mac table for this ethernet segment";
                                }

                            } // container pbb

                        } // list ethernet-segment

                        ///nokia-conf/configure/service/system/bgp/evpn/ad-per-es-route
                        container ad-per-es-route {
                            description "Enter the ad-per-es-route context";

                            ///nokia-conf/configure/service/system/bgp/evpn/ad-per-es-route/route-target-type
                            leaf route-target-type {
                                type enumeration {
                                    enum evi-route-target               { value 1; }
                                    enum evi-route-target-set           { value 2; }
                                }
                                default "evi-route-target";
                                description "Method for the AD per-ES routes advertisement";
                            }

                            ///nokia-conf/configure/service/system/bgp/evpn/ad-per-es-route/route-distinguisher-ip-address
                            leaf route-distinguisher-ip-address {
                                type types-sros:ipv4-address;
                                description "IP address for route distinguisher for EVPN AD-ES routes";
                            }

                            ///nokia-conf/configure/service/system/bgp/evpn/ad-per-es-route/extended-evi-range
                            leaf extended-evi-range {
                                type boolean;
                                default "false";
                                description "Reserve extended RD comm-values for AD per-ES routes";
                            }

                        } // container ad-per-es-route

                        ///nokia-conf/configure/service/system/bgp/evpn/ip-prefix-routes
                        container ip-prefix-routes {
                            description "Enter the ip-prefix-routes context";

                            ///nokia-conf/configure/service/system/bgp/evpn/ip-prefix-routes/iff-attribute-uniform-propagation
                            leaf iff-attribute-uniform-propagation {
                                type boolean;
                                default "false";
                                description "Enable uniform propagation of BGP attributes";
                            }

                            ///nokia-conf/configure/service/system/bgp/evpn/ip-prefix-routes/iff-bgp-path-selection
                            leaf iff-bgp-path-selection {
                                type boolean;
                                default "false";
                                description "Enable BGP path selection for EVPN-IFF routes";
                            }

                            ///nokia-conf/configure/service/system/bgp/evpn/ip-prefix-routes/d-path-length-ignore
                            leaf d-path-length-ignore {
                                type boolean;
                                default "false";
                                description "Ignore D-PATH length for BGP path selection of EVPN-IFF";
                            }

                        } // container ip-prefix-routes

                        ///nokia-conf/configure/service/system/bgp/evpn/mpls
                        container mpls {
                            description "Enter the mpls context";

                            ///nokia-conf/configure/service/system/bgp/evpn/mpls/vpls-control-word
                            leaf vpls-control-word {
                                type boolean;
                                default "false";
                                description "VPLS control word";
                            }

                        } // container mpls

                    } // container evpn

                } // container bgp

                ///nokia-conf/configure/service/system/ldp
                container ldp {
                    description "Enter the ldp context";

                    ///nokia-conf/configure/service/system/ldp/hash-label-block
                    leaf hash-label-block {
                        type leafref {
                            path "../../../../router/mpls-labels/reserved-label-block/label-block-name";
                        }
                        description "Reserved label block from which to select hash labels";
                    }

                    ///nokia-conf/configure/service/system/ldp/apply-groups
                    leaf-list apply-groups {
                        type leafref {
                            path "../../../../groups/group/name";
                        }
                        max-elements 8;
                        ordered-by user;
                        description "Apply a configuration group at this level";
                    }

                    ///nokia-conf/configure/service/system/ldp/apply-groups-exclude
                    leaf-list apply-groups-exclude {
                        type leafref {
                            path "../../../../groups/group/name";
                        }
                        max-elements 8;
                        ordered-by user;
                        description "Exclude a configuration group at this level";
                    }

                } // container ldp

            } // container system

            ///nokia-conf/configure/service/mac-list
            list mac-list {
                key "name";
                description "Enter the mac-list list instance";

                ///nokia-conf/configure/service/mac-list/name
                leaf name {
                    type types-sros:named-item;
                    description "MAC list name";
                }

                ///nokia-conf/configure/service/mac-list/description
                leaf description {
                    type types-sros:description;
                    description "Text description";
                }

                ///nokia-conf/configure/service/mac-list/apply-groups
                leaf-list apply-groups {
                    type leafref {
                        path "../../../groups/group/name";
                    }
                    max-elements 8;
                    ordered-by user;
                    description "Apply a configuration group at this level";
                }

                ///nokia-conf/configure/service/mac-list/apply-groups-exclude
                leaf-list apply-groups-exclude {
                    type leafref {
                        path "../../../groups/group/name";
                    }
                    max-elements 8;
                    ordered-by user;
                    description "Exclude a configuration group at this level";
                }

                ///nokia-conf/configure/service/mac-list/mac
                list mac {
                    key "address";
                    description "Enter the mac list instance";

                    ///nokia-conf/configure/service/mac-list/mac/address
                    leaf address {
                        type yang:mac-address;
                        description "MAC address";
                    }

                    ///nokia-conf/configure/service/mac-list/mac/mask
                    leaf mask {
                        type yang:mac-address;
                        default "ff:ff:ff:ff:ff:ff";
                        description "Mask for the MAC address";
                    }

                    ///nokia-conf/configure/service/mac-list/mac/apply-groups
                    leaf-list apply-groups {
                        type leafref {
                            path "../../../../groups/group/name";
                        }
                        max-elements 8;
                        ordered-by user;
                        description "Apply a configuration group at this level";
                    }

                    ///nokia-conf/configure/service/mac-list/mac/apply-groups-exclude
                    leaf-list apply-groups-exclude {
                        type leafref {
                            path "../../../../groups/group/name";
                        }
                        max-elements 8;
                        ordered-by user;
                        description "Exclude a configuration group at this level";
                    }

                } // list mac

            } // list mac-list

            ///nokia-conf/configure/service/md-auto-id
            container md-auto-id {
                description "Enter the md-auto-id context";

                ///nokia-conf/configure/service/md-auto-id/service-id-range
                container service-id-range {
                    presence "Enable the service-id-range context";
                    description "Enable the service-id-range context";

                    ///nokia-conf/configure/service/md-auto-id/service-id-range/start
                    leaf start {
                        type types-services:external-service-id;
                        sros-ext:immutable;
                        mandatory true;
                        description "Lower bound of the service ID range";
                    }

                    ///nokia-conf/configure/service/md-auto-id/service-id-range/end
                    leaf end {
                        type types-services:external-service-id;
                        sros-ext:immutable;
                        mandatory true;
                        description "Upper bound of the service ID range";
                    }

                    ///nokia-conf/configure/service/md-auto-id/service-id-range/apply-groups
                    leaf-list apply-groups {
                        type leafref {
                            path "../../../../groups/group/name";
                        }
                        max-elements 8;
                        ordered-by user;
                        description "Apply a configuration group at this level";
                    }

                    ///nokia-conf/configure/service/md-auto-id/service-id-range/apply-groups-exclude
                    leaf-list apply-groups-exclude {
                        type leafref {
                            path "../../../../groups/group/name";
                        }
                        max-elements 8;
                        ordered-by user;
                        description "Exclude a configuration group at this level";
                    }

                } // container service-id-range

                ///nokia-conf/configure/service/md-auto-id/customer-id-range
                container customer-id-range {
                    presence "Enable the customer-id-range context";
                    description "Enable the customer-id-range context";

                    ///nokia-conf/configure/service/md-auto-id/customer-id-range/start
                    leaf start {
                        type types-services:customer-id {
                            range "2..2147483647";
                        }
                        sros-ext:immutable;
                        mandatory true;
                        description "Lower bound of the ID range";
                    }

                    ///nokia-conf/configure/service/md-auto-id/customer-id-range/end
                    leaf end {
                        type types-services:customer-id {
                            range "2..2147483647";
                        }
                        sros-ext:immutable;
                        mandatory true;
                        description "Upper bound of the ID range";
                    }

                    ///nokia-conf/configure/service/md-auto-id/customer-id-range/apply-groups
                    leaf-list apply-groups {
                        type leafref {
                            path "../../../../groups/group/name";
                        }
                        max-elements 8;
                        ordered-by user;
                        description "Apply a configuration group at this level";
                    }

                    ///nokia-conf/configure/service/md-auto-id/customer-id-range/apply-groups-exclude
                    leaf-list apply-groups-exclude {
                        type leafref {
                            path "../../../../groups/group/name";
                        }
                        max-elements 8;
                        ordered-by user;
                        description "Exclude a configuration group at this level";
                    }

                } // container customer-id-range

                ///nokia-conf/configure/service/md-auto-id/pw-template-id-range
                container pw-template-id-range {
                    presence "Enable the pw-template-id-range context";
                    description "Enable the pw-template-id-range context";

                    ///nokia-conf/configure/service/md-auto-id/pw-template-id-range/start
                    leaf start {
                        type types-services:pw-template-id {
                            range "1..2147483647";
                        }
                        sros-ext:immutable;
                        mandatory true;
                        description "Lower bound of the PW template ID range";
                    }

                    ///nokia-conf/configure/service/md-auto-id/pw-template-id-range/end
                    leaf end {
                        type types-services:pw-template-id {
                            range "1..2147483647";
                        }
                        sros-ext:immutable;
                        mandatory true;
                        description "Upper bound of the PW template ID range";
                    }

                    ///nokia-conf/configure/service/md-auto-id/pw-template-id-range/apply-groups
                    leaf-list apply-groups {
                        type leafref {
                            path "../../../../groups/group/name";
                        }
                        max-elements 8;
                        ordered-by user;
                        description "Apply a configuration group at this level";
                    }

                    ///nokia-conf/configure/service/md-auto-id/pw-template-id-range/apply-groups-exclude
                    leaf-list apply-groups-exclude {
                        type leafref {
                            path "../../../../groups/group/name";
                        }
                        max-elements 8;
                        ordered-by user;
                        description "Exclude a configuration group at this level";
                    }

                } // container pw-template-id-range

            } // container md-auto-id

            ///nokia-conf/configure/service/template
            container template {
                description "Enter the template context";

                ///nokia-conf/configure/service/template/epipe-sap-template
                list epipe-sap-template {
                    key "name";
                    description "Enter the epipe-sap-template list instance";

                    ///nokia-conf/configure/service/template/epipe-sap-template/name
                    leaf name {
                        type types-sros:named-item;
                        description "SAP template name";
                    }

                    ///nokia-conf/configure/service/template/epipe-sap-template/apply-groups
                    leaf-list apply-groups {
                        type leafref {
                            path "../../../../groups/group/name";
                        }
                        max-elements 8;
                        ordered-by user;
                        description "Apply a configuration group at this level";
                    }

                    ///nokia-conf/configure/service/template/epipe-sap-template/apply-groups-exclude
                    leaf-list apply-groups-exclude {
                        type leafref {
                            path "../../../../groups/group/name";
                        }
                        max-elements 8;
                        ordered-by user;
                        description "Exclude a configuration group at this level";
                    }

                    ///nokia-conf/configure/service/template/epipe-sap-template/egress
                    container egress {
                        description "Enter the egress context";

                        ///nokia-conf/configure/service/template/epipe-sap-template/egress/filter
                        container filter {
                            description "Enter the filter context";

                            ///nokia-conf/configure/service/template/epipe-sap-template/egress/filter/mac
                            leaf mac {
                                type leafref {
                                    path "../../../../../../filter/mac-filter/filter-name";
                                }
                                description "MAC filter policy name";
                            }

                            ///nokia-conf/configure/service/template/epipe-sap-template/egress/filter/ip
                            leaf ip {
                                type leafref {
                                    path "../../../../../../filter/ip-filter/filter-name";
                                }
                                description "IPv4 filter policy name";
                            }

                            ///nokia-conf/configure/service/template/epipe-sap-template/egress/filter/ipv6
                            leaf ipv6 {
                                type leafref {
                                    path "../../../../../../filter/ipv6-filter/filter-name";
                                }
                                description "IPv6 filter policy name";
                            }

                        } // container filter

                        ///nokia-conf/configure/service/template/epipe-sap-template/egress/qos
                        container qos {
                            description "Enter the qos context";

                            ///nokia-conf/configure/service/template/epipe-sap-template/egress/qos/policy-name
                            leaf policy-name {
                                type leafref {
                                    path "../../../../../../qos/sap-egress/sap-egress-policy-name";
                                }
                                description "SAP egress QoS policy name to apply to the SAP";
                            }

                        } // container qos

                    } // container egress

                    ///nokia-conf/configure/service/template/epipe-sap-template/ingress
                    container ingress {
                        description "Enter the ingress context";

                        ///nokia-conf/configure/service/template/epipe-sap-template/ingress/filter
                        container filter {
                            description "Enter the filter context";

                            ///nokia-conf/configure/service/template/epipe-sap-template/ingress/filter/mac
                            leaf mac {
                                type leafref {
                                    path "../../../../../../filter/mac-filter/filter-name";
                                }
                                description "MAC filter policy name";
                            }

                            ///nokia-conf/configure/service/template/epipe-sap-template/ingress/filter/ip
                            leaf ip {
                                type leafref {
                                    path "../../../../../../filter/ip-filter/filter-name";
                                }
                                description "IPv4 filter policy name";
                            }

                            ///nokia-conf/configure/service/template/epipe-sap-template/ingress/filter/ipv6
                            leaf ipv6 {
                                type leafref {
                                    path "../../../../../../filter/ipv6-filter/filter-name";
                                }
                                description "IPv6 filter policy name";
                            }

                        } // container filter

                        ///nokia-conf/configure/service/template/epipe-sap-template/ingress/qos
                        container qos {
                            description "Enter the qos context";

                            ///nokia-conf/configure/service/template/epipe-sap-template/ingress/qos/policy-name
                            leaf policy-name {
                                type leafref {
                                    path "../../../../../../qos/sap-ingress/sap-ingress-policy-name";
                                }
                                description "SAP ingress QoS policy name to apply to the SAP";
                            }

                            ///nokia-conf/configure/service/template/epipe-sap-template/ingress/qos/queuing-type
                            leaf queuing-type {
                                type types-services:services-sap-queuing-type;
                                description "Queuing type";
                            }

                        } // container qos

                    } // container ingress

                } // list epipe-sap-template


            } // container template

            uses conf-svc-cpipe;
            uses conf-svc-epipe;
            uses conf-svc-ies;
            uses conf-svc-ipfix;
            uses conf-svc-ipipe;
            uses conf-svc-nat;
            uses conf-svc-sdp;
            uses conf-svc-vpls;
            uses conf-svc-vprn;
        } // container service

    } // grouping conf-service

}
