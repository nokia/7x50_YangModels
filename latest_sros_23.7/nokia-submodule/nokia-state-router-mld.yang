submodule nokia-state-router-mld {

    yang-version "1.1";

    belongs-to nokia-state { prefix "state"; }

    import ietf-yang-types                { prefix "yang"; }
    import nokia-sros-yang-extensions     { prefix "sros-ext"; }
    import nokia-types-igmp               { prefix "types-igmp"; }
    import nokia-types-services           { prefix "types-services"; }
    import nokia-types-sros               { prefix "types-sros"; }
    import nokia-types-subscriber-mgmt    { prefix "types-submgt"; }

    include nokia-state-service;
    include nokia-state-svc-ies;
    include nokia-state-svc-ies-sub-if;
    include nokia-state-svc-vprn;
    include nokia-state-svc-vprn-sub-if;

    sros-ext:sros-major-release "rel23";
    organization "Nokia";
    contact
        "Nokia SR OS Support
         Web: <http://www.nokia.com>";
    description
        "Nokia YANG Data model with operational state for mld protocol on SR OS based routers.

         Copyright 2016 Nokia. All rights reserved. Reproduction of this document
         is authorized on the condition that the foregoing copyright notice is included.

         This nokia-state-router-mld YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-router-mld {
        ///nokia-state/state/router/mld
        container mld {
            description "Enable the mld context";

            ///nokia-state/state/router/mld/oper-state
            leaf oper-state {
                type types-sros:oper-state;
                description "The current operating state of this MLD protocol instance on this router.";
            }

            ///nokia-state/state/router/mld/interface
            list interface {
                key "ip-interface-name";
                description "Enter the interface list instance";

                ///nokia-state/state/router/mld/interface/ip-interface-name
                leaf ip-interface-name {
                    type types-sros:interface-name;
                    description "IP interface name";
                }

                ///nokia-state/state/router/mld/interface/oper-state
                leaf oper-state {
                    type types-sros:oper-state;
                    description "The current operating state of the MLD protocol on this interface.";
                }

                ///nokia-state/state/router/mld/interface/oper-version
                leaf oper-version {
                    type types-igmp:mld-version;
                    description "The operational version of the MLD which is running on this interface.";
                }

                ///nokia-state/state/router/mld/interface/group-count
                leaf group-count {
                    type int32;
                    description "The number of multicast groups which have been learned on this interface.";
                }

                ///nokia-state/state/router/mld/interface/next-general-query-time
                leaf next-general-query-time {
                    type uint32;
                    units "seconds";
                    description
                        "The time remaining before the general query is sent on this interface
                         if this router is the querier.";
                }

                ///nokia-state/state/router/mld/interface/maximum-groups-until-now
                leaf maximum-groups-until-now {
                    type int32;
                    description "The highest value that 'group-count' had till now.";
                }

                ///nokia-state/state/router/mld/interface/querier
                leaf querier {
                    type types-sros:ipv6-address;
                    description "The address of the MLD Querier on the IP subnet to which this interface is attached.";
                }

                ///nokia-state/state/router/mld/interface/querier-up-time
                leaf querier-up-time {
                    type uint32;
                    units "seconds";
                    description "The time since 'querier' was last elected as querier.";
                }

                ///nokia-state/state/router/mld/interface/querier-expiry-time
                leaf querier-expiry-time {
                    type uint32;
                    units "seconds";
                    description "The time remaining before querier is aged out.";
                }

                ///nokia-state/state/router/mld/interface/mcac
                container mcac {
                    description "Enter the mcac context";

                    ///nokia-state/state/router/mld/interface/mcac/in-use-mandatory-bandwidth
                    leaf in-use-mandatory-bandwidth {
                        type uint32;
                        units "kilobps";
                        description
                            "The in-use bandwidth for the mandatory channels for this
                             protocol interface instance.";
                    }

                    ///nokia-state/state/router/mld/interface/mcac/in-use-optional-bandwidth
                    leaf in-use-optional-bandwidth {
                        type uint32;
                        units "kilobps";
                        description
                            "The in-use bandwidth for the optional channels for this
                             protocol interface instance.";
                    }

                    ///nokia-state/state/router/mld/interface/mcac/available-mandatory-bandwidth
                    leaf available-mandatory-bandwidth {
                        type uint32;
                        units "kilobps";
                        description
                            "The pre-reserved bandwidth for the mandatory channels for
                             this interface instance.";
                    }

                    ///nokia-state/state/router/mld/interface/mcac/available-optional-bandwidth
                    leaf available-optional-bandwidth {
                        type uint32;
                        units "kilobps";
                        description "The available bandwidth for this interface instance.";
                    }

                    ///nokia-state/state/router/mld/interface/mcac/values-in-transit
                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

                ///nokia-state/state/router/mld/interface/static
                container static {
                    description "Enter the static context";

                    ///nokia-state/state/router/mld/interface/static/group-range
                    list group-range {
                        key "start end step";
                        description "Enter the group-range list instance";

                        ///nokia-state/state/router/mld/interface/static/group-range/start
                        leaf start {
                            type types-sros:ipv6-multicast-address;
                            description "Lower bound of the static multicast group";
                        }

                        ///nokia-state/state/router/mld/interface/static/group-range/end
                        leaf end {
                            type types-sros:ipv6-multicast-address;
                            description "Upper bound of the static multicast group";
                        }

                        ///nokia-state/state/router/mld/interface/static/group-range/step
                        leaf step {
                            type types-sros:ipv6-address;
                            description "Step interval for the group-range addresses";
                        }

                        ///nokia-state/state/router/mld/interface/static/group-range/group-count
                        leaf group-count {
                            type uint32;
                            description "The number of groups in the group-range.";
                        }

                    } // list group-range

                } // container static

                ///nokia-state/state/router/mld/interface/statistics
                container statistics {
                    description "Enter the statistics context";

                    ///nokia-state/state/router/mld/interface/statistics/received
                    container received {
                        description "Enter the received context";

                        ///nokia-state/state/router/mld/interface/statistics/received/general-queries
                        leaf general-queries {
                            type yang:counter32;
                            description "General Queries.";
                        }

                        ///nokia-state/state/router/mld/interface/statistics/received/group-queries
                        leaf group-queries {
                            type yang:counter32;
                            description "Group Specific Queries.";
                        }

                        ///nokia-state/state/router/mld/interface/statistics/received/group-source-queries
                        leaf group-source-queries {
                            type yang:counter32;
                            description "Group and Source Specific Queries.";
                        }

                        ///nokia-state/state/router/mld/interface/statistics/received/v1-reports
                        leaf v1-reports {
                            type yang:counter32;
                            description "V1 Reports.";
                        }

                        ///nokia-state/state/router/mld/interface/statistics/received/v2-reports
                        leaf v2-reports {
                            type yang:counter32;
                            description "V2 Reports.";
                        }

                        ///nokia-state/state/router/mld/interface/statistics/received/leaves
                        leaf leaves {
                            type yang:counter32;
                            description "Leaves.";
                        }

                        ///nokia-state/state/router/mld/interface/statistics/received/drops
                        leaf drops {
                            type yang:counter32;
                            description "Total number of dropped packets.";
                        }

                    } // container received

                    ///nokia-state/state/router/mld/interface/statistics/transmitted
                    container transmitted {
                        description "Enter the transmitted context";

                        ///nokia-state/state/router/mld/interface/statistics/transmitted/general-queries
                        leaf general-queries {
                            type yang:counter32;
                            description "General Queries.";
                        }

                        ///nokia-state/state/router/mld/interface/statistics/transmitted/group-queries
                        leaf group-queries {
                            type yang:counter32;
                            description "Group Specific Queries.";
                        }

                        ///nokia-state/state/router/mld/interface/statistics/transmitted/group-source-queries
                        leaf group-source-queries {
                            type yang:counter32;
                            description "Group and Source Specific Queries.";
                        }

                        ///nokia-state/state/router/mld/interface/statistics/transmitted/v1-reports
                        leaf v1-reports {
                            type yang:counter32;
                            description "V1 Reports.";
                        }

                        ///nokia-state/state/router/mld/interface/statistics/transmitted/v2-reports
                        leaf v2-reports {
                            type yang:counter32;
                            description "V2 Reports.";
                        }

                        ///nokia-state/state/router/mld/interface/statistics/transmitted/leaves
                        leaf leaves {
                            type yang:counter32;
                            description "Leaves.";
                        }

                        ///nokia-state/state/router/mld/interface/statistics/transmitted/drops
                        leaf drops {
                            type yang:counter32;
                            description "Total number of dropped packets.";
                        }

                        ///nokia-state/state/router/mld/interface/statistics/transmitted/errors
                        leaf errors {
                            type yang:counter32;
                            description "Transmission Errors.";
                        }

                    } // container transmitted

                    ///nokia-state/state/router/mld/interface/statistics/error
                    container error {
                        description "Enter the error context";

                        ///nokia-state/state/router/mld/interface/statistics/error/bad-length
                        leaf bad-length {
                            type yang:counter32;
                            description "Bad length.";
                        }

                        ///nokia-state/state/router/mld/interface/statistics/error/bad-ip-checksum
                        leaf bad-ip-checksum {
                            type yang:counter32;
                            description "Bad Ip checksum.";
                        }

                        ///nokia-state/state/router/mld/interface/statistics/error/unknown-type
                        leaf unknown-type {
                            type yang:counter32;
                            description "Unknown type.";
                        }

                        ///nokia-state/state/router/mld/interface/statistics/error/wrong-version
                        leaf wrong-version {
                            type yang:counter32;
                            description "Wrong version.";
                        }

                        ///nokia-state/state/router/mld/interface/statistics/error/import-policy-drops
                        leaf import-policy-drops {
                            type yang:counter32;
                            description
                                "Number of times we matched the host IP address or group or
                                 source addresses specified in the import policy.";
                        }

                        ///nokia-state/state/router/mld/interface/statistics/error/missing-router-alert
                        leaf missing-router-alert {
                            type yang:counter32;
                            description "Router alert flag is not set.";
                        }

                        ///nokia-state/state/router/mld/interface/statistics/error/bad-encoding
                        leaf bad-encoding {
                            type yang:counter32;
                            description "Badly encoded.";
                        }

                        ///nokia-state/state/router/mld/interface/statistics/error/local-scope
                        leaf local-scope {
                            type yang:counter32;
                            description "Link-local scope multicast group address.";
                        }

                        ///nokia-state/state/router/mld/interface/statistics/error/reserved-scope
                        leaf reserved-scope {
                            type yang:counter32;
                            description "Reserved scope multicast group address.";
                        }

                        ///nokia-state/state/router/mld/interface/statistics/error/mcac-policy-drops
                        leaf mcac-policy-drops {
                            type yang:counter32;
                            description
                                "Number of times a join is dropped because of applying a
                                 multicast CAC policy.";
                        }

                        ///nokia-state/state/router/mld/interface/statistics/error/reached-maximum-number-groups
                        leaf reached-maximum-number-groups {
                            type yang:counter32;
                            description
                                "Number of times a join is dropped because we reached the maximum
                                 number of groups.";
                        }

                        ///nokia-state/state/router/mld/interface/statistics/error/reached-maximum-number-group-sources
                        leaf reached-maximum-number-group-sources {
                            type yang:counter32;
                            description
                                "Number of times a join is dropped because we reached the maximum
                                 number group-source combinations.";
                        }

                        ///nokia-state/state/router/mld/interface/statistics/error/reached-maximum-number-sources
                        leaf reached-maximum-number-sources {
                            type yang:counter32;
                            description
                                "Number of times a join is dropped because we reached the maximum
                                 number of sources per group.";
                        }

                        ///nokia-state/state/router/mld/interface/statistics/error/out-of-memory-drops
                        leaf out-of-memory-drops {
                            type yang:counter32;
                            description "Number of times a join is dropped because we ran out of memory.";
                        }

                        ///nokia-state/state/router/mld/interface/statistics/error/mcs-failures
                        leaf mcs-failures {
                            type yang:counter32;
                            description "Number of times a group could not be synced through multi chassis synchronisation (MCS).";
                        }

                        ///nokia-state/state/router/mld/interface/statistics/error/non-local
                        leaf non-local {
                            type yang:counter32;
                            description "Non-local sender source IP address.";
                        }

                    } // container error

                } // container statistics

                ///nokia-state/state/router/mld/interface/group
                list group {
                    key "group-address";
                    description "Enter the group list instance";

                    ///nokia-state/state/router/mld/interface/group/group-address
                    leaf group-address {
                        type types-sros:ipv6-multicast-address;
                        description "Group address of multicast channel";
                    }

                    ///nokia-state/state/router/mld/interface/group/group-type
                    leaf group-type {
                        type types-igmp:learn-type;
                    }

                    ///nokia-state/state/router/mld/interface/group/filter-mode
                    leaf filter-mode {
                        type types-igmp:filter-mode;
                    }

                    ///nokia-state/state/router/mld/interface/group/expiry-time
                    leaf expiry-time {
                        type uint32;
                        units "seconds";
                        description "The time left before multicast group timeout.";
                    }

                    ///nokia-state/state/router/mld/interface/group/up-time
                    leaf up-time {
                        type uint32;
                        units "seconds";
                        description "The time elapsed since this entry was created.";
                    }

                    ///nokia-state/state/router/mld/interface/group/v1-host-timer
                    leaf v1-host-timer {
                        type uint32;
                        units "seconds";
                        description
                            "The time remaining until the local router will assume that
                             there are no longer any version 1 members.";
                    }

                    ///nokia-state/state/router/mld/interface/group/mld-compatibility-mode
                    leaf mld-compatibility-mode {
                        type types-igmp:mld-version;
                        description "Compatibility with older version routers.";
                    }

                    ///nokia-state/state/router/mld/interface/group/last-reporter
                    leaf last-reporter {
                        type types-sros:ip-address;
                        description
                            "The last host address which has sent the report to join
                             the multicast group.";
                    }

                    ///nokia-state/state/router/mld/interface/group/source
                    list source {
                        key "source-address";
                        description "Enter the source list instance";

                        ///nokia-state/state/router/mld/interface/group/source/source-address
                        leaf source-address {
                            type types-sros:ipv6-address;
                            description "Source address of multicast channel.";
                        }

                        ///nokia-state/state/router/mld/interface/group/source/source-type
                        leaf source-type {
                            type types-igmp:learn-type;
                        }

                        ///nokia-state/state/router/mld/interface/group/source/forwarding-state
                        leaf forwarding-state {
                            type types-igmp:forwarding-state;
                            description "Traffic forwardeding state on this port.";
                        }

                        ///nokia-state/state/router/mld/interface/group/source/expiry-time
                        leaf expiry-time {
                            type uint32;
                            units "seconds";
                            description "The time left before multicast group timeout.";
                        }

                        ///nokia-state/state/router/mld/interface/group/source/up-time
                        leaf up-time {
                            type uint32;
                            units "seconds";
                            description "The time elapsed since this entry was created.";
                        }

                    } // list source

                } // list group

            } // list interface

            ///nokia-state/state/router/mld/group-interface
            list group-interface {
                key "group-interface-name";
                description "Enter the group-interface list instance";

                ///nokia-state/state/router/mld/group-interface/group-interface-name
                leaf group-interface-name {
                    type leafref {
                        path "../../../../service/ies/subscriber-interface/group-interface/group-interface-name";
                    }
                    description "Group interface name";
                }

                ///nokia-state/state/router/mld/group-interface/oper-state
                leaf oper-state {
                    type types-sros:oper-state;
                    description "The current operating state of the MLD protocol on this group interface.";
                }

                ///nokia-state/state/router/mld/group-interface/mcac
                container mcac {
                    description "Enter the mcac context";

                    ///nokia-state/state/router/mld/group-interface/mcac/in-use-mandatory-bandwidth
                    leaf in-use-mandatory-bandwidth {
                        type uint32;
                        units "kilobps";
                        description
                            "The in-use bandwidth for the mandatory channels for this
                             protocol interface instance.";
                    }

                    ///nokia-state/state/router/mld/group-interface/mcac/in-use-optional-bandwidth
                    leaf in-use-optional-bandwidth {
                        type uint32;
                        units "kilobps";
                        description
                            "The in-use bandwidth for the optional channels for this
                             protocol interface instance.";
                    }

                    ///nokia-state/state/router/mld/group-interface/mcac/available-mandatory-bandwidth
                    leaf available-mandatory-bandwidth {
                        type uint32;
                        units "kilobps";
                        description
                            "The pre-reserved bandwidth for the mandatory channels for
                             this interface instance.";
                    }

                    ///nokia-state/state/router/mld/group-interface/mcac/available-optional-bandwidth
                    leaf available-optional-bandwidth {
                        type uint32;
                        units "kilobps";
                        description "The available bandwidth for this interface instance.";
                    }

                    ///nokia-state/state/router/mld/group-interface/mcac/values-in-transit
                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

                ///nokia-state/state/router/mld/group-interface/sap
                list sap {
                    key "sap-id";
                    description "Enter the sap list instance";

                    ///nokia-state/state/router/mld/group-interface/sap/sap-id
                    leaf sap-id {
                        type types-sros:sap;
                        description "SAP identifier.";
                    }

                    ///nokia-state/state/router/mld/group-interface/sap/oper-state
                    leaf oper-state {
                        type types-sros:oper-state;
                        description "The current operating state of the MLD protocol on this interface.";
                    }

                    ///nokia-state/state/router/mld/group-interface/sap/oper-version
                    leaf oper-version {
                        type types-igmp:mld-version;
                        description "The operational version of the MLD which is running on this interface.";
                    }

                    ///nokia-state/state/router/mld/group-interface/sap/group-count
                    leaf group-count {
                        type int32;
                        description "The number of multicast groups which have been learned on this interface.";
                    }

                    ///nokia-state/state/router/mld/group-interface/sap/next-general-query-time
                    leaf next-general-query-time {
                        type uint32;
                        units "seconds";
                        description
                            "The time remaining before the general query is sent on this interface
                             if this router is the querier.";
                    }

                    ///nokia-state/state/router/mld/group-interface/sap/maximum-groups-until-now
                    leaf maximum-groups-until-now {
                        type int32;
                        description "The highest value that 'group-count' had till now.";
                    }

                    ///nokia-state/state/router/mld/group-interface/sap/statistics
                    container statistics {
                        description "Enter the statistics context";

                        ///nokia-state/state/router/mld/group-interface/sap/statistics/received
                        container received {
                            description "Enter the received context";

                            ///nokia-state/state/router/mld/group-interface/sap/statistics/received/general-queries
                            leaf general-queries {
                                type yang:counter32;
                                description "General Queries.";
                            }

                            ///nokia-state/state/router/mld/group-interface/sap/statistics/received/group-queries
                            leaf group-queries {
                                type yang:counter32;
                                description "Group Specific Queries.";
                            }

                            ///nokia-state/state/router/mld/group-interface/sap/statistics/received/group-source-queries
                            leaf group-source-queries {
                                type yang:counter32;
                                description "Group and Source Specific Queries.";
                            }

                            ///nokia-state/state/router/mld/group-interface/sap/statistics/received/v1-reports
                            leaf v1-reports {
                                type yang:counter32;
                                description "V1 Reports.";
                            }

                            ///nokia-state/state/router/mld/group-interface/sap/statistics/received/v2-reports
                            leaf v2-reports {
                                type yang:counter32;
                                description "V2 Reports.";
                            }

                            ///nokia-state/state/router/mld/group-interface/sap/statistics/received/leaves
                            leaf leaves {
                                type yang:counter32;
                                description "Leaves.";
                            }

                            ///nokia-state/state/router/mld/group-interface/sap/statistics/received/drops
                            leaf drops {
                                type yang:counter32;
                                description "Total number of dropped packets.";
                            }

                        } // container received

                        ///nokia-state/state/router/mld/group-interface/sap/statistics/transmitted
                        container transmitted {
                            description "Enter the transmitted context";

                            ///nokia-state/state/router/mld/group-interface/sap/statistics/transmitted/general-queries
                            leaf general-queries {
                                type yang:counter32;
                                description "General Queries.";
                            }

                            ///nokia-state/state/router/mld/group-interface/sap/statistics/transmitted/group-queries
                            leaf group-queries {
                                type yang:counter32;
                                description "Group Specific Queries.";
                            }

                            ///nokia-state/state/router/mld/group-interface/sap/statistics/transmitted/group-source-queries
                            leaf group-source-queries {
                                type yang:counter32;
                                description "Group and Source Specific Queries.";
                            }

                            ///nokia-state/state/router/mld/group-interface/sap/statistics/transmitted/v1-reports
                            leaf v1-reports {
                                type yang:counter32;
                                description "V1 Reports.";
                            }

                            ///nokia-state/state/router/mld/group-interface/sap/statistics/transmitted/v2-reports
                            leaf v2-reports {
                                type yang:counter32;
                                description "V2 Reports.";
                            }

                            ///nokia-state/state/router/mld/group-interface/sap/statistics/transmitted/leaves
                            leaf leaves {
                                type yang:counter32;
                                description "Leaves.";
                            }

                            ///nokia-state/state/router/mld/group-interface/sap/statistics/transmitted/drops
                            leaf drops {
                                type yang:counter32;
                                description "Total number of dropped packets.";
                            }

                            ///nokia-state/state/router/mld/group-interface/sap/statistics/transmitted/errors
                            leaf errors {
                                type yang:counter32;
                                description "Transmission Errors.";
                            }

                        } // container transmitted

                        ///nokia-state/state/router/mld/group-interface/sap/statistics/error
                        container error {
                            description "Enter the error context";

                            ///nokia-state/state/router/mld/group-interface/sap/statistics/error/bad-length
                            leaf bad-length {
                                type yang:counter32;
                                description "Bad length.";
                            }

                            ///nokia-state/state/router/mld/group-interface/sap/statistics/error/bad-ip-checksum
                            leaf bad-ip-checksum {
                                type yang:counter32;
                                description "Bad Ip checksum.";
                            }

                            ///nokia-state/state/router/mld/group-interface/sap/statistics/error/unknown-type
                            leaf unknown-type {
                                type yang:counter32;
                                description "Unknown type.";
                            }

                            ///nokia-state/state/router/mld/group-interface/sap/statistics/error/wrong-version
                            leaf wrong-version {
                                type yang:counter32;
                                description "Wrong version.";
                            }

                            ///nokia-state/state/router/mld/group-interface/sap/statistics/error/import-policy-drops
                            leaf import-policy-drops {
                                type yang:counter32;
                                description
                                    "Number of times we matched the host IP address or group or
                                     source addresses specified in the import policy.";
                            }

                            ///nokia-state/state/router/mld/group-interface/sap/statistics/error/missing-router-alert
                            leaf missing-router-alert {
                                type yang:counter32;
                                description "Router alert flag is not set.";
                            }

                            ///nokia-state/state/router/mld/group-interface/sap/statistics/error/bad-encoding
                            leaf bad-encoding {
                                type yang:counter32;
                                description "Badly encoded.";
                            }

                            ///nokia-state/state/router/mld/group-interface/sap/statistics/error/local-scope
                            leaf local-scope {
                                type yang:counter32;
                                description "Link-local scope multicast group address.";
                            }

                            ///nokia-state/state/router/mld/group-interface/sap/statistics/error/reserved-scope
                            leaf reserved-scope {
                                type yang:counter32;
                                description "Reserved scope multicast group address.";
                            }

                            ///nokia-state/state/router/mld/group-interface/sap/statistics/error/mcac-policy-drops
                            leaf mcac-policy-drops {
                                type yang:counter32;
                                description
                                    "Number of times a join is dropped because of applying a
                                     multicast CAC policy.";
                            }

                            ///nokia-state/state/router/mld/group-interface/sap/statistics/error/reached-maximum-number-groups
                            leaf reached-maximum-number-groups {
                                type yang:counter32;
                                description
                                    "Number of times a join is dropped because we reached the maximum
                                     number of groups.";
                            }

                            ///nokia-state/state/router/mld/group-interface/sap/statistics/error/reached-maximum-number-group-sources
                            leaf reached-maximum-number-group-sources {
                                type yang:counter32;
                                description
                                    "Number of times a join is dropped because we reached the maximum
                                     number group-source combinations.";
                            }

                            ///nokia-state/state/router/mld/group-interface/sap/statistics/error/reached-maximum-number-sources
                            leaf reached-maximum-number-sources {
                                type yang:counter32;
                                description
                                    "Number of times a join is dropped because we reached the maximum
                                     number of sources per group.";
                            }

                            ///nokia-state/state/router/mld/group-interface/sap/statistics/error/out-of-memory-drops
                            leaf out-of-memory-drops {
                                type yang:counter32;
                                description "Number of times a join is dropped because we ran out of memory.";
                            }

                            ///nokia-state/state/router/mld/group-interface/sap/statistics/error/mcs-failures
                            leaf mcs-failures {
                                type yang:counter32;
                                description "Number of times a group could not be synced through multi chassis synchronisation (MCS).";
                            }

                            ///nokia-state/state/router/mld/group-interface/sap/statistics/error/non-local
                            leaf non-local {
                                type yang:counter32;
                                description "Non-local sender source IP address.";
                            }

                        } // container error

                    } // container statistics

                    ///nokia-state/state/router/mld/group-interface/sap/group
                    list group {
                        key "group-address";
                        description "Enter the group list instance";

                        ///nokia-state/state/router/mld/group-interface/sap/group/group-address
                        leaf group-address {
                            type types-sros:ipv6-multicast-address;
                            description "Group address of multicast channel";
                        }

                        ///nokia-state/state/router/mld/group-interface/sap/group/group-type
                        leaf group-type {
                            type types-igmp:learn-type;
                        }

                        ///nokia-state/state/router/mld/group-interface/sap/group/filter-mode
                        leaf filter-mode {
                            type types-igmp:filter-mode;
                        }

                        ///nokia-state/state/router/mld/group-interface/sap/group/expiry-time
                        leaf expiry-time {
                            type uint32;
                            units "seconds";
                            description "The time left before multicast group timeout.";
                        }

                        ///nokia-state/state/router/mld/group-interface/sap/group/up-time
                        leaf up-time {
                            type uint32;
                            units "seconds";
                            description "The time elapsed since this entry was created.";
                        }

                        ///nokia-state/state/router/mld/group-interface/sap/group/v1-host-timer
                        leaf v1-host-timer {
                            type uint32;
                            units "seconds";
                            description
                                "The time remaining until the local router will assume that
                                 there are no longer any version 1 members.";
                        }

                        ///nokia-state/state/router/mld/group-interface/sap/group/mld-compatibility-mode
                        leaf mld-compatibility-mode {
                            type types-igmp:mld-version;
                            description "Compatibility with older version routers.";
                        }

                        ///nokia-state/state/router/mld/group-interface/sap/group/last-reporter
                        leaf last-reporter {
                            type types-sros:ip-address;
                            description
                                "The last host address which has sent the report to join
                                 the multicast group.";
                        }

                        ///nokia-state/state/router/mld/group-interface/sap/group/source
                        list source {
                            key "source-address";
                            description "Enter the source list instance";

                            ///nokia-state/state/router/mld/group-interface/sap/group/source/source-address
                            leaf source-address {
                                type types-sros:ipv6-address;
                                description "Source address of multicast channel.";
                            }

                            ///nokia-state/state/router/mld/group-interface/sap/group/source/source-type
                            leaf source-type {
                                type types-igmp:learn-type;
                            }

                            ///nokia-state/state/router/mld/group-interface/sap/group/source/forwarding-state
                            leaf forwarding-state {
                                type types-igmp:forwarding-state;
                                description "Traffic forwardeding state on this port.";
                            }

                            ///nokia-state/state/router/mld/group-interface/sap/group/source/expiry-time
                            leaf expiry-time {
                                type uint32;
                                units "seconds";
                                description "The time left before multicast group timeout.";
                            }

                            ///nokia-state/state/router/mld/group-interface/sap/group/source/up-time
                            leaf up-time {
                                type uint32;
                                units "seconds";
                                description "The time elapsed since this entry was created.";
                            }

                        } // list source

                    } // list group

                } // list sap

                ///nokia-state/state/router/mld/group-interface/host
                list host {
                    key "ip-address mac-address pppoe-session-id";
                    description "Enter the host list instance";

                    ///nokia-state/state/router/mld/group-interface/host/ip-address
                    leaf ip-address {
                        type types-sros:ipv6-address;
                        description "The IP address of this host.";
                    }

                    ///nokia-state/state/router/mld/group-interface/host/mac-address
                    leaf mac-address {
                        type yang:mac-address;
                        description "The MAC address of this host.";
                    }

                    ///nokia-state/state/router/mld/group-interface/host/pppoe-session-id
                    leaf pppoe-session-id {
                        type uint32;
                        description "The PPPoE session id of this host.";
                    }

                    ///nokia-state/state/router/mld/group-interface/host/oper-state
                    leaf oper-state {
                        type types-sros:oper-state;
                        description "The current operating state of the MLD protocol on this interface.";
                    }

                    ///nokia-state/state/router/mld/group-interface/host/oper-version
                    leaf oper-version {
                        type types-igmp:mld-version;
                        description "The operational version of the MLD which is running on this interface.";
                    }

                    ///nokia-state/state/router/mld/group-interface/host/group-count
                    leaf group-count {
                        type int32;
                        description "The number of multicast groups which have been learned on this interface.";
                    }

                    ///nokia-state/state/router/mld/group-interface/host/next-general-query-time
                    leaf next-general-query-time {
                        type uint32;
                        units "seconds";
                        description
                            "The time remaining before the general query is sent on this interface
                             if this router is the querier.";
                    }

                    ///nokia-state/state/router/mld/group-interface/host/maximum-groups-until-now
                    leaf maximum-groups-until-now {
                        type int32;
                        description "The highest value that 'group-count' had till now.";
                    }

                    ///nokia-state/state/router/mld/group-interface/host/subscriber-id
                    leaf subscriber-id {
                        type types-submgt:subscriber-id;
                        description "The subscriber identification of this subscriber host.";
                    }

                    ///nokia-state/state/router/mld/group-interface/host/bonding-context-id
                    leaf bonding-context-id {
                        type types-submgt:bonding-context-id;
                        description "The bonding context identifier of the session of this host.";
                    }

                    ///nokia-state/state/router/mld/group-interface/host/bonding-connection-index
                    leaf bonding-connection-index {
                        type types-submgt:bonding-connection-index;
                        description "The bonding connection index of the session of this host.";
                    }

                    ///nokia-state/state/router/mld/group-interface/host/mld-policy
                    leaf mld-policy {
                        type types-sros:named-item;
                        description "The mld-policy in use.";
                    }

                    ///nokia-state/state/router/mld/group-interface/host/statistics
                    container statistics {
                        description "Enter the statistics context";

                        ///nokia-state/state/router/mld/group-interface/host/statistics/received
                        container received {
                            description "Enter the received context";

                            ///nokia-state/state/router/mld/group-interface/host/statistics/received/general-queries
                            leaf general-queries {
                                type yang:counter32;
                                description "General Queries.";
                            }

                            ///nokia-state/state/router/mld/group-interface/host/statistics/received/group-queries
                            leaf group-queries {
                                type yang:counter32;
                                description "Group Specific Queries.";
                            }

                            ///nokia-state/state/router/mld/group-interface/host/statistics/received/group-source-queries
                            leaf group-source-queries {
                                type yang:counter32;
                                description "Group and Source Specific Queries.";
                            }

                            ///nokia-state/state/router/mld/group-interface/host/statistics/received/v1-reports
                            leaf v1-reports {
                                type yang:counter32;
                                description "V1 Reports.";
                            }

                            ///nokia-state/state/router/mld/group-interface/host/statistics/received/v2-reports
                            leaf v2-reports {
                                type yang:counter32;
                                description "V2 Reports.";
                            }

                            ///nokia-state/state/router/mld/group-interface/host/statistics/received/leaves
                            leaf leaves {
                                type yang:counter32;
                                description "Leaves.";
                            }

                            ///nokia-state/state/router/mld/group-interface/host/statistics/received/drops
                            leaf drops {
                                type yang:counter32;
                                description "Total number of dropped packets.";
                            }

                        } // container received

                        ///nokia-state/state/router/mld/group-interface/host/statistics/transmitted
                        container transmitted {
                            description "Enter the transmitted context";

                            ///nokia-state/state/router/mld/group-interface/host/statistics/transmitted/general-queries
                            leaf general-queries {
                                type yang:counter32;
                                description "General Queries.";
                            }

                            ///nokia-state/state/router/mld/group-interface/host/statistics/transmitted/group-queries
                            leaf group-queries {
                                type yang:counter32;
                                description "Group Specific Queries.";
                            }

                            ///nokia-state/state/router/mld/group-interface/host/statistics/transmitted/group-source-queries
                            leaf group-source-queries {
                                type yang:counter32;
                                description "Group and Source Specific Queries.";
                            }

                            ///nokia-state/state/router/mld/group-interface/host/statistics/transmitted/v1-reports
                            leaf v1-reports {
                                type yang:counter32;
                                description "V1 Reports.";
                            }

                            ///nokia-state/state/router/mld/group-interface/host/statistics/transmitted/v2-reports
                            leaf v2-reports {
                                type yang:counter32;
                                description "V2 Reports.";
                            }

                            ///nokia-state/state/router/mld/group-interface/host/statistics/transmitted/leaves
                            leaf leaves {
                                type yang:counter32;
                                description "Leaves.";
                            }

                            ///nokia-state/state/router/mld/group-interface/host/statistics/transmitted/drops
                            leaf drops {
                                type yang:counter32;
                                description "Total number of dropped packets.";
                            }

                            ///nokia-state/state/router/mld/group-interface/host/statistics/transmitted/errors
                            leaf errors {
                                type yang:counter32;
                                description "Transmission Errors.";
                            }

                        } // container transmitted

                        ///nokia-state/state/router/mld/group-interface/host/statistics/error
                        container error {
                            description "Enter the error context";

                            ///nokia-state/state/router/mld/group-interface/host/statistics/error/bad-length
                            leaf bad-length {
                                type yang:counter32;
                                description "Bad length.";
                            }

                            ///nokia-state/state/router/mld/group-interface/host/statistics/error/bad-ip-checksum
                            leaf bad-ip-checksum {
                                type yang:counter32;
                                description "Bad Ip checksum.";
                            }

                            ///nokia-state/state/router/mld/group-interface/host/statistics/error/unknown-type
                            leaf unknown-type {
                                type yang:counter32;
                                description "Unknown type.";
                            }

                            ///nokia-state/state/router/mld/group-interface/host/statistics/error/wrong-version
                            leaf wrong-version {
                                type yang:counter32;
                                description "Wrong version.";
                            }

                            ///nokia-state/state/router/mld/group-interface/host/statistics/error/import-policy-drops
                            leaf import-policy-drops {
                                type yang:counter32;
                                description
                                    "Number of times we matched the host IP address or group or
                                     source addresses specified in the import policy.";
                            }

                            ///nokia-state/state/router/mld/group-interface/host/statistics/error/missing-router-alert
                            leaf missing-router-alert {
                                type yang:counter32;
                                description "Router alert flag is not set.";
                            }

                            ///nokia-state/state/router/mld/group-interface/host/statistics/error/bad-encoding
                            leaf bad-encoding {
                                type yang:counter32;
                                description "Badly encoded.";
                            }

                            ///nokia-state/state/router/mld/group-interface/host/statistics/error/local-scope
                            leaf local-scope {
                                type yang:counter32;
                                description "Link-local scope multicast group address.";
                            }

                            ///nokia-state/state/router/mld/group-interface/host/statistics/error/reserved-scope
                            leaf reserved-scope {
                                type yang:counter32;
                                description "Reserved scope multicast group address.";
                            }

                            ///nokia-state/state/router/mld/group-interface/host/statistics/error/mcac-policy-drops
                            leaf mcac-policy-drops {
                                type yang:counter32;
                                description
                                    "Number of times a join is dropped because of applying a
                                     multicast CAC policy.";
                            }

                            ///nokia-state/state/router/mld/group-interface/host/statistics/error/reached-maximum-number-groups
                            leaf reached-maximum-number-groups {
                                type yang:counter32;
                                description
                                    "Number of times a join is dropped because we reached the maximum
                                     number of groups.";
                            }

                            ///nokia-state/state/router/mld/group-interface/host/statistics/error/reached-maximum-number-group-sources
                            leaf reached-maximum-number-group-sources {
                                type yang:counter32;
                                description
                                    "Number of times a join is dropped because we reached the maximum
                                     number group-source combinations.";
                            }

                            ///nokia-state/state/router/mld/group-interface/host/statistics/error/reached-maximum-number-sources
                            leaf reached-maximum-number-sources {
                                type yang:counter32;
                                description
                                    "Number of times a join is dropped because we reached the maximum
                                     number of sources per group.";
                            }

                            ///nokia-state/state/router/mld/group-interface/host/statistics/error/out-of-memory-drops
                            leaf out-of-memory-drops {
                                type yang:counter32;
                                description "Number of times a join is dropped because we ran out of memory.";
                            }

                            ///nokia-state/state/router/mld/group-interface/host/statistics/error/mcs-failures
                            leaf mcs-failures {
                                type yang:counter32;
                                description "Number of times a group could not be synced through multi chassis synchronisation (MCS).";
                            }

                            ///nokia-state/state/router/mld/group-interface/host/statistics/error/non-local
                            leaf non-local {
                                type yang:counter32;
                                description "Non-local sender source IP address.";
                            }

                            ///nokia-state/state/router/mld/group-interface/host/statistics/error/redirection-drops
                            leaf redirection-drops {
                                type yang:counter32;
                                description
                                    "Number of times a Group is dropped because of a failure
                                     while applying a redirection policy for this host.";
                            }

                        } // container error

                    } // container statistics

                    ///nokia-state/state/router/mld/group-interface/host/group
                    list group {
                        key "group-address";
                        description "Enter the group list instance";

                        ///nokia-state/state/router/mld/group-interface/host/group/group-address
                        leaf group-address {
                            type types-sros:ipv6-multicast-address;
                            description "Group address of multicast channel";
                        }

                        ///nokia-state/state/router/mld/group-interface/host/group/group-type
                        leaf group-type {
                            type types-igmp:learn-type;
                        }

                        ///nokia-state/state/router/mld/group-interface/host/group/filter-mode
                        leaf filter-mode {
                            type types-igmp:filter-mode;
                        }

                        ///nokia-state/state/router/mld/group-interface/host/group/expiry-time
                        leaf expiry-time {
                            type uint32;
                            units "seconds";
                            description "The time left before multicast group timeout.";
                        }

                        ///nokia-state/state/router/mld/group-interface/host/group/up-time
                        leaf up-time {
                            type uint32;
                            units "seconds";
                            description "The time elapsed since this entry was created.";
                        }

                        ///nokia-state/state/router/mld/group-interface/host/group/v1-host-timer
                        leaf v1-host-timer {
                            type uint32;
                            units "seconds";
                            description
                                "The time remaining until the local router will assume that
                                 there are no longer any version 1 members.";
                        }

                        ///nokia-state/state/router/mld/group-interface/host/group/mld-compatibility-mode
                        leaf mld-compatibility-mode {
                            type types-igmp:mld-version;
                            description "Compatibility with older version routers.";
                        }

                        ///nokia-state/state/router/mld/group-interface/host/group/last-reporter
                        leaf last-reporter {
                            type types-sros:ip-address;
                            description
                                "The last host address which has sent the report to join
                                 the multicast group.";
                        }

                        ///nokia-state/state/router/mld/group-interface/host/group/source
                        list source {
                            key "source-address";
                            description "Enter the source list instance";

                            ///nokia-state/state/router/mld/group-interface/host/group/source/source-address
                            leaf source-address {
                                type types-sros:ipv6-address;
                                description "Source address of multicast channel.";
                            }

                            ///nokia-state/state/router/mld/group-interface/host/group/source/source-type
                            leaf source-type {
                                type types-igmp:learn-type;
                            }

                            ///nokia-state/state/router/mld/group-interface/host/group/source/forwarding-state
                            leaf forwarding-state {
                                type types-igmp:forwarding-state;
                                description "Traffic forwardeding state on this port.";
                            }

                            ///nokia-state/state/router/mld/group-interface/host/group/source/expiry-time
                            leaf expiry-time {
                                type uint32;
                                units "seconds";
                                description "The time left before multicast group timeout.";
                            }

                            ///nokia-state/state/router/mld/group-interface/host/group/source/up-time
                            leaf up-time {
                                type uint32;
                                units "seconds";
                                description "The time elapsed since this entry was created.";
                            }

                        } // list source

                    } // list group

                } // list host

            } // list group-interface

            ///nokia-state/state/router/mld/forwarding-group-interface
            list forwarding-group-interface {
                key "forwarding-service group-interface-name";
                description "Enter the forwarding-group-interface list instance";

                ///nokia-state/state/router/mld/forwarding-group-interface/forwarding-service
                leaf forwarding-service {
                    type types-services:service-name;
                    description "Forwarding service for the subscriber interface";
                }

                ///nokia-state/state/router/mld/forwarding-group-interface/group-interface-name
                leaf group-interface-name {
                    type leafref {
                        path "../../../../service/vprn[service-name=current()/../forwarding-service]/subscriber-interface/group-interface/group-interface-name";
                    }
                    description "Group interface name";
                }

                ///nokia-state/state/router/mld/forwarding-group-interface/oper-state
                leaf oper-state {
                    type types-sros:oper-state;
                    description "The current operating state of the MLD protocol on this group interface.";
                }

                ///nokia-state/state/router/mld/forwarding-group-interface/mcac
                container mcac {
                    description "Enter the mcac context";

                    ///nokia-state/state/router/mld/forwarding-group-interface/mcac/in-use-mandatory-bandwidth
                    leaf in-use-mandatory-bandwidth {
                        type uint32;
                        units "kilobps";
                        description
                            "The in-use bandwidth for the mandatory channels for this
                             protocol interface instance.";
                    }

                    ///nokia-state/state/router/mld/forwarding-group-interface/mcac/in-use-optional-bandwidth
                    leaf in-use-optional-bandwidth {
                        type uint32;
                        units "kilobps";
                        description
                            "The in-use bandwidth for the optional channels for this
                             protocol interface instance.";
                    }

                    ///nokia-state/state/router/mld/forwarding-group-interface/mcac/available-mandatory-bandwidth
                    leaf available-mandatory-bandwidth {
                        type uint32;
                        units "kilobps";
                        description
                            "The pre-reserved bandwidth for the mandatory channels for
                             this interface instance.";
                    }

                    ///nokia-state/state/router/mld/forwarding-group-interface/mcac/available-optional-bandwidth
                    leaf available-optional-bandwidth {
                        type uint32;
                        units "kilobps";
                        description "The available bandwidth for this interface instance.";
                    }

                    ///nokia-state/state/router/mld/forwarding-group-interface/mcac/values-in-transit
                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

                ///nokia-state/state/router/mld/forwarding-group-interface/sap
                list sap {
                    key "sap-id";
                    description "Enter the sap list instance";

                    ///nokia-state/state/router/mld/forwarding-group-interface/sap/sap-id
                    leaf sap-id {
                        type types-sros:sap;
                        description "SAP identifier.";
                    }

                    ///nokia-state/state/router/mld/forwarding-group-interface/sap/oper-state
                    leaf oper-state {
                        type types-sros:oper-state;
                        description "The current operating state of the MLD protocol on this interface.";
                    }

                    ///nokia-state/state/router/mld/forwarding-group-interface/sap/oper-version
                    leaf oper-version {
                        type types-igmp:mld-version;
                        description "The operational version of the MLD which is running on this interface.";
                    }

                    ///nokia-state/state/router/mld/forwarding-group-interface/sap/group-count
                    leaf group-count {
                        type int32;
                        description "The number of multicast groups which have been learned on this interface.";
                    }

                    ///nokia-state/state/router/mld/forwarding-group-interface/sap/next-general-query-time
                    leaf next-general-query-time {
                        type uint32;
                        units "seconds";
                        description
                            "The time remaining before the general query is sent on this interface
                             if this router is the querier.";
                    }

                    ///nokia-state/state/router/mld/forwarding-group-interface/sap/maximum-groups-until-now
                    leaf maximum-groups-until-now {
                        type int32;
                        description "The highest value that 'group-count' had till now.";
                    }

                    ///nokia-state/state/router/mld/forwarding-group-interface/sap/statistics
                    container statistics {
                        description "Enter the statistics context";

                        ///nokia-state/state/router/mld/forwarding-group-interface/sap/statistics/received
                        container received {
                            description "Enter the received context";

                            ///nokia-state/state/router/mld/forwarding-group-interface/sap/statistics/received/general-queries
                            leaf general-queries {
                                type yang:counter32;
                                description "General Queries.";
                            }

                            ///nokia-state/state/router/mld/forwarding-group-interface/sap/statistics/received/group-queries
                            leaf group-queries {
                                type yang:counter32;
                                description "Group Specific Queries.";
                            }

                            ///nokia-state/state/router/mld/forwarding-group-interface/sap/statistics/received/group-source-queries
                            leaf group-source-queries {
                                type yang:counter32;
                                description "Group and Source Specific Queries.";
                            }

                            ///nokia-state/state/router/mld/forwarding-group-interface/sap/statistics/received/v1-reports
                            leaf v1-reports {
                                type yang:counter32;
                                description "V1 Reports.";
                            }

                            ///nokia-state/state/router/mld/forwarding-group-interface/sap/statistics/received/v2-reports
                            leaf v2-reports {
                                type yang:counter32;
                                description "V2 Reports.";
                            }

                            ///nokia-state/state/router/mld/forwarding-group-interface/sap/statistics/received/leaves
                            leaf leaves {
                                type yang:counter32;
                                description "Leaves.";
                            }

                            ///nokia-state/state/router/mld/forwarding-group-interface/sap/statistics/received/drops
                            leaf drops {
                                type yang:counter32;
                                description "Total number of dropped packets.";
                            }

                        } // container received

                        ///nokia-state/state/router/mld/forwarding-group-interface/sap/statistics/transmitted
                        container transmitted {
                            description "Enter the transmitted context";

                            ///nokia-state/state/router/mld/forwarding-group-interface/sap/statistics/transmitted/general-queries
                            leaf general-queries {
                                type yang:counter32;
                                description "General Queries.";
                            }

                            ///nokia-state/state/router/mld/forwarding-group-interface/sap/statistics/transmitted/group-queries
                            leaf group-queries {
                                type yang:counter32;
                                description "Group Specific Queries.";
                            }

                            ///nokia-state/state/router/mld/forwarding-group-interface/sap/statistics/transmitted/group-source-queries
                            leaf group-source-queries {
                                type yang:counter32;
                                description "Group and Source Specific Queries.";
                            }

                            ///nokia-state/state/router/mld/forwarding-group-interface/sap/statistics/transmitted/v1-reports
                            leaf v1-reports {
                                type yang:counter32;
                                description "V1 Reports.";
                            }

                            ///nokia-state/state/router/mld/forwarding-group-interface/sap/statistics/transmitted/v2-reports
                            leaf v2-reports {
                                type yang:counter32;
                                description "V2 Reports.";
                            }

                            ///nokia-state/state/router/mld/forwarding-group-interface/sap/statistics/transmitted/leaves
                            leaf leaves {
                                type yang:counter32;
                                description "Leaves.";
                            }

                            ///nokia-state/state/router/mld/forwarding-group-interface/sap/statistics/transmitted/drops
                            leaf drops {
                                type yang:counter32;
                                description "Total number of dropped packets.";
                            }

                            ///nokia-state/state/router/mld/forwarding-group-interface/sap/statistics/transmitted/errors
                            leaf errors {
                                type yang:counter32;
                                description "Transmission Errors.";
                            }

                        } // container transmitted

                        ///nokia-state/state/router/mld/forwarding-group-interface/sap/statistics/error
                        container error {
                            description "Enter the error context";

                            ///nokia-state/state/router/mld/forwarding-group-interface/sap/statistics/error/bad-length
                            leaf bad-length {
                                type yang:counter32;
                                description "Bad length.";
                            }

                            ///nokia-state/state/router/mld/forwarding-group-interface/sap/statistics/error/bad-ip-checksum
                            leaf bad-ip-checksum {
                                type yang:counter32;
                                description "Bad Ip checksum.";
                            }

                            ///nokia-state/state/router/mld/forwarding-group-interface/sap/statistics/error/unknown-type
                            leaf unknown-type {
                                type yang:counter32;
                                description "Unknown type.";
                            }

                            ///nokia-state/state/router/mld/forwarding-group-interface/sap/statistics/error/wrong-version
                            leaf wrong-version {
                                type yang:counter32;
                                description "Wrong version.";
                            }

                            ///nokia-state/state/router/mld/forwarding-group-interface/sap/statistics/error/import-policy-drops
                            leaf import-policy-drops {
                                type yang:counter32;
                                description
                                    "Number of times we matched the host IP address or group or
                                     source addresses specified in the import policy.";
                            }

                            ///nokia-state/state/router/mld/forwarding-group-interface/sap/statistics/error/missing-router-alert
                            leaf missing-router-alert {
                                type yang:counter32;
                                description "Router alert flag is not set.";
                            }

                            ///nokia-state/state/router/mld/forwarding-group-interface/sap/statistics/error/bad-encoding
                            leaf bad-encoding {
                                type yang:counter32;
                                description "Badly encoded.";
                            }

                            ///nokia-state/state/router/mld/forwarding-group-interface/sap/statistics/error/local-scope
                            leaf local-scope {
                                type yang:counter32;
                                description "Link-local scope multicast group address.";
                            }

                            ///nokia-state/state/router/mld/forwarding-group-interface/sap/statistics/error/reserved-scope
                            leaf reserved-scope {
                                type yang:counter32;
                                description "Reserved scope multicast group address.";
                            }

                            ///nokia-state/state/router/mld/forwarding-group-interface/sap/statistics/error/mcac-policy-drops
                            leaf mcac-policy-drops {
                                type yang:counter32;
                                description
                                    "Number of times a join is dropped because of applying a
                                     multicast CAC policy.";
                            }

                            ///nokia-state/state/router/mld/forwarding-group-interface/sap/statistics/error/reached-maximum-number-groups
                            leaf reached-maximum-number-groups {
                                type yang:counter32;
                                description
                                    "Number of times a join is dropped because we reached the maximum
                                     number of groups.";
                            }

                            ///nokia-state/state/router/mld/forwarding-group-interface/sap/statistics/error/reached-maximum-number-group-sources
                            leaf reached-maximum-number-group-sources {
                                type yang:counter32;
                                description
                                    "Number of times a join is dropped because we reached the maximum
                                     number group-source combinations.";
                            }

                            ///nokia-state/state/router/mld/forwarding-group-interface/sap/statistics/error/reached-maximum-number-sources
                            leaf reached-maximum-number-sources {
                                type yang:counter32;
                                description
                                    "Number of times a join is dropped because we reached the maximum
                                     number of sources per group.";
                            }

                            ///nokia-state/state/router/mld/forwarding-group-interface/sap/statistics/error/out-of-memory-drops
                            leaf out-of-memory-drops {
                                type yang:counter32;
                                description "Number of times a join is dropped because we ran out of memory.";
                            }

                            ///nokia-state/state/router/mld/forwarding-group-interface/sap/statistics/error/mcs-failures
                            leaf mcs-failures {
                                type yang:counter32;
                                description "Number of times a group could not be synced through multi chassis synchronisation (MCS).";
                            }

                            ///nokia-state/state/router/mld/forwarding-group-interface/sap/statistics/error/non-local
                            leaf non-local {
                                type yang:counter32;
                                description "Non-local sender source IP address.";
                            }

                        } // container error

                    } // container statistics

                    ///nokia-state/state/router/mld/forwarding-group-interface/sap/group
                    list group {
                        key "group-address";
                        description "Enter the group list instance";

                        ///nokia-state/state/router/mld/forwarding-group-interface/sap/group/group-address
                        leaf group-address {
                            type types-sros:ipv6-multicast-address;
                            description "Group address of multicast channel";
                        }

                        ///nokia-state/state/router/mld/forwarding-group-interface/sap/group/group-type
                        leaf group-type {
                            type types-igmp:learn-type;
                        }

                        ///nokia-state/state/router/mld/forwarding-group-interface/sap/group/filter-mode
                        leaf filter-mode {
                            type types-igmp:filter-mode;
                        }

                        ///nokia-state/state/router/mld/forwarding-group-interface/sap/group/expiry-time
                        leaf expiry-time {
                            type uint32;
                            units "seconds";
                            description "The time left before multicast group timeout.";
                        }

                        ///nokia-state/state/router/mld/forwarding-group-interface/sap/group/up-time
                        leaf up-time {
                            type uint32;
                            units "seconds";
                            description "The time elapsed since this entry was created.";
                        }

                        ///nokia-state/state/router/mld/forwarding-group-interface/sap/group/v1-host-timer
                        leaf v1-host-timer {
                            type uint32;
                            units "seconds";
                            description
                                "The time remaining until the local router will assume that
                                 there are no longer any version 1 members.";
                        }

                        ///nokia-state/state/router/mld/forwarding-group-interface/sap/group/mld-compatibility-mode
                        leaf mld-compatibility-mode {
                            type types-igmp:mld-version;
                            description "Compatibility with older version routers.";
                        }

                        ///nokia-state/state/router/mld/forwarding-group-interface/sap/group/last-reporter
                        leaf last-reporter {
                            type types-sros:ip-address;
                            description
                                "The last host address which has sent the report to join
                                 the multicast group.";
                        }

                        ///nokia-state/state/router/mld/forwarding-group-interface/sap/group/source
                        list source {
                            key "source-address";
                            description "Enter the source list instance";

                            ///nokia-state/state/router/mld/forwarding-group-interface/sap/group/source/source-address
                            leaf source-address {
                                type types-sros:ipv6-address;
                                description "Source address of multicast channel.";
                            }

                            ///nokia-state/state/router/mld/forwarding-group-interface/sap/group/source/source-type
                            leaf source-type {
                                type types-igmp:learn-type;
                            }

                            ///nokia-state/state/router/mld/forwarding-group-interface/sap/group/source/forwarding-state
                            leaf forwarding-state {
                                type types-igmp:forwarding-state;
                                description "Traffic forwardeding state on this port.";
                            }

                            ///nokia-state/state/router/mld/forwarding-group-interface/sap/group/source/expiry-time
                            leaf expiry-time {
                                type uint32;
                                units "seconds";
                                description "The time left before multicast group timeout.";
                            }

                            ///nokia-state/state/router/mld/forwarding-group-interface/sap/group/source/up-time
                            leaf up-time {
                                type uint32;
                                units "seconds";
                                description "The time elapsed since this entry was created.";
                            }

                        } // list source

                    } // list group

                } // list sap

                ///nokia-state/state/router/mld/forwarding-group-interface/host
                list host {
                    key "ip-address mac-address pppoe-session-id";
                    description "Enter the host list instance";

                    ///nokia-state/state/router/mld/forwarding-group-interface/host/ip-address
                    leaf ip-address {
                        type types-sros:ipv6-address;
                        description "The IP address of this host.";
                    }

                    ///nokia-state/state/router/mld/forwarding-group-interface/host/mac-address
                    leaf mac-address {
                        type yang:mac-address;
                        description "The MAC address of this host.";
                    }

                    ///nokia-state/state/router/mld/forwarding-group-interface/host/pppoe-session-id
                    leaf pppoe-session-id {
                        type uint32;
                        description "The PPPoE session id of this host.";
                    }

                    ///nokia-state/state/router/mld/forwarding-group-interface/host/oper-state
                    leaf oper-state {
                        type types-sros:oper-state;
                        description "The current operating state of the MLD protocol on this interface.";
                    }

                    ///nokia-state/state/router/mld/forwarding-group-interface/host/oper-version
                    leaf oper-version {
                        type types-igmp:mld-version;
                        description "The operational version of the MLD which is running on this interface.";
                    }

                    ///nokia-state/state/router/mld/forwarding-group-interface/host/group-count
                    leaf group-count {
                        type int32;
                        description "The number of multicast groups which have been learned on this interface.";
                    }

                    ///nokia-state/state/router/mld/forwarding-group-interface/host/next-general-query-time
                    leaf next-general-query-time {
                        type uint32;
                        units "seconds";
                        description
                            "The time remaining before the general query is sent on this interface
                             if this router is the querier.";
                    }

                    ///nokia-state/state/router/mld/forwarding-group-interface/host/maximum-groups-until-now
                    leaf maximum-groups-until-now {
                        type int32;
                        description "The highest value that 'group-count' had till now.";
                    }

                    ///nokia-state/state/router/mld/forwarding-group-interface/host/subscriber-id
                    leaf subscriber-id {
                        type types-submgt:subscriber-id;
                        description "The subscriber identification of this subscriber host.";
                    }

                    ///nokia-state/state/router/mld/forwarding-group-interface/host/bonding-context-id
                    leaf bonding-context-id {
                        type types-submgt:bonding-context-id;
                        description "The bonding context identifier of the session of this host.";
                    }

                    ///nokia-state/state/router/mld/forwarding-group-interface/host/bonding-connection-index
                    leaf bonding-connection-index {
                        type types-submgt:bonding-connection-index;
                        description "The bonding connection index of the session of this host.";
                    }

                    ///nokia-state/state/router/mld/forwarding-group-interface/host/mld-policy
                    leaf mld-policy {
                        type types-sros:named-item;
                        description "The mld-policy in use.";
                    }

                    ///nokia-state/state/router/mld/forwarding-group-interface/host/statistics
                    container statistics {
                        description "Enter the statistics context";

                        ///nokia-state/state/router/mld/forwarding-group-interface/host/statistics/received
                        container received {
                            description "Enter the received context";

                            ///nokia-state/state/router/mld/forwarding-group-interface/host/statistics/received/general-queries
                            leaf general-queries {
                                type yang:counter32;
                                description "General Queries.";
                            }

                            ///nokia-state/state/router/mld/forwarding-group-interface/host/statistics/received/group-queries
                            leaf group-queries {
                                type yang:counter32;
                                description "Group Specific Queries.";
                            }

                            ///nokia-state/state/router/mld/forwarding-group-interface/host/statistics/received/group-source-queries
                            leaf group-source-queries {
                                type yang:counter32;
                                description "Group and Source Specific Queries.";
                            }

                            ///nokia-state/state/router/mld/forwarding-group-interface/host/statistics/received/v1-reports
                            leaf v1-reports {
                                type yang:counter32;
                                description "V1 Reports.";
                            }

                            ///nokia-state/state/router/mld/forwarding-group-interface/host/statistics/received/v2-reports
                            leaf v2-reports {
                                type yang:counter32;
                                description "V2 Reports.";
                            }

                            ///nokia-state/state/router/mld/forwarding-group-interface/host/statistics/received/leaves
                            leaf leaves {
                                type yang:counter32;
                                description "Leaves.";
                            }

                            ///nokia-state/state/router/mld/forwarding-group-interface/host/statistics/received/drops
                            leaf drops {
                                type yang:counter32;
                                description "Total number of dropped packets.";
                            }

                        } // container received

                        ///nokia-state/state/router/mld/forwarding-group-interface/host/statistics/transmitted
                        container transmitted {
                            description "Enter the transmitted context";

                            ///nokia-state/state/router/mld/forwarding-group-interface/host/statistics/transmitted/general-queries
                            leaf general-queries {
                                type yang:counter32;
                                description "General Queries.";
                            }

                            ///nokia-state/state/router/mld/forwarding-group-interface/host/statistics/transmitted/group-queries
                            leaf group-queries {
                                type yang:counter32;
                                description "Group Specific Queries.";
                            }

                            ///nokia-state/state/router/mld/forwarding-group-interface/host/statistics/transmitted/group-source-queries
                            leaf group-source-queries {
                                type yang:counter32;
                                description "Group and Source Specific Queries.";
                            }

                            ///nokia-state/state/router/mld/forwarding-group-interface/host/statistics/transmitted/v1-reports
                            leaf v1-reports {
                                type yang:counter32;
                                description "V1 Reports.";
                            }

                            ///nokia-state/state/router/mld/forwarding-group-interface/host/statistics/transmitted/v2-reports
                            leaf v2-reports {
                                type yang:counter32;
                                description "V2 Reports.";
                            }

                            ///nokia-state/state/router/mld/forwarding-group-interface/host/statistics/transmitted/leaves
                            leaf leaves {
                                type yang:counter32;
                                description "Leaves.";
                            }

                            ///nokia-state/state/router/mld/forwarding-group-interface/host/statistics/transmitted/drops
                            leaf drops {
                                type yang:counter32;
                                description "Total number of dropped packets.";
                            }

                            ///nokia-state/state/router/mld/forwarding-group-interface/host/statistics/transmitted/errors
                            leaf errors {
                                type yang:counter32;
                                description "Transmission Errors.";
                            }

                        } // container transmitted

                        ///nokia-state/state/router/mld/forwarding-group-interface/host/statistics/error
                        container error {
                            description "Enter the error context";

                            ///nokia-state/state/router/mld/forwarding-group-interface/host/statistics/error/bad-length
                            leaf bad-length {
                                type yang:counter32;
                                description "Bad length.";
                            }

                            ///nokia-state/state/router/mld/forwarding-group-interface/host/statistics/error/bad-ip-checksum
                            leaf bad-ip-checksum {
                                type yang:counter32;
                                description "Bad Ip checksum.";
                            }

                            ///nokia-state/state/router/mld/forwarding-group-interface/host/statistics/error/unknown-type
                            leaf unknown-type {
                                type yang:counter32;
                                description "Unknown type.";
                            }

                            ///nokia-state/state/router/mld/forwarding-group-interface/host/statistics/error/wrong-version
                            leaf wrong-version {
                                type yang:counter32;
                                description "Wrong version.";
                            }

                            ///nokia-state/state/router/mld/forwarding-group-interface/host/statistics/error/import-policy-drops
                            leaf import-policy-drops {
                                type yang:counter32;
                                description
                                    "Number of times we matched the host IP address or group or
                                     source addresses specified in the import policy.";
                            }

                            ///nokia-state/state/router/mld/forwarding-group-interface/host/statistics/error/missing-router-alert
                            leaf missing-router-alert {
                                type yang:counter32;
                                description "Router alert flag is not set.";
                            }

                            ///nokia-state/state/router/mld/forwarding-group-interface/host/statistics/error/bad-encoding
                            leaf bad-encoding {
                                type yang:counter32;
                                description "Badly encoded.";
                            }

                            ///nokia-state/state/router/mld/forwarding-group-interface/host/statistics/error/local-scope
                            leaf local-scope {
                                type yang:counter32;
                                description "Link-local scope multicast group address.";
                            }

                            ///nokia-state/state/router/mld/forwarding-group-interface/host/statistics/error/reserved-scope
                            leaf reserved-scope {
                                type yang:counter32;
                                description "Reserved scope multicast group address.";
                            }

                            ///nokia-state/state/router/mld/forwarding-group-interface/host/statistics/error/mcac-policy-drops
                            leaf mcac-policy-drops {
                                type yang:counter32;
                                description
                                    "Number of times a join is dropped because of applying a
                                     multicast CAC policy.";
                            }

                            ///nokia-state/state/router/mld/forwarding-group-interface/host/statistics/error/reached-maximum-number-groups
                            leaf reached-maximum-number-groups {
                                type yang:counter32;
                                description
                                    "Number of times a join is dropped because we reached the maximum
                                     number of groups.";
                            }

                            ///nokia-state/state/router/mld/forwarding-group-interface/host/statistics/error/reached-maximum-number-group-sources
                            leaf reached-maximum-number-group-sources {
                                type yang:counter32;
                                description
                                    "Number of times a join is dropped because we reached the maximum
                                     number group-source combinations.";
                            }

                            ///nokia-state/state/router/mld/forwarding-group-interface/host/statistics/error/reached-maximum-number-sources
                            leaf reached-maximum-number-sources {
                                type yang:counter32;
                                description
                                    "Number of times a join is dropped because we reached the maximum
                                     number of sources per group.";
                            }

                            ///nokia-state/state/router/mld/forwarding-group-interface/host/statistics/error/out-of-memory-drops
                            leaf out-of-memory-drops {
                                type yang:counter32;
                                description "Number of times a join is dropped because we ran out of memory.";
                            }

                            ///nokia-state/state/router/mld/forwarding-group-interface/host/statistics/error/mcs-failures
                            leaf mcs-failures {
                                type yang:counter32;
                                description "Number of times a group could not be synced through multi chassis synchronisation (MCS).";
                            }

                            ///nokia-state/state/router/mld/forwarding-group-interface/host/statistics/error/non-local
                            leaf non-local {
                                type yang:counter32;
                                description "Non-local sender source IP address.";
                            }

                            ///nokia-state/state/router/mld/forwarding-group-interface/host/statistics/error/redirection-drops
                            leaf redirection-drops {
                                type yang:counter32;
                                description
                                    "Number of times a Group is dropped because of a failure
                                     while applying a redirection policy for this host.";
                            }

                        } // container error

                    } // container statistics

                    ///nokia-state/state/router/mld/forwarding-group-interface/host/group
                    list group {
                        key "group-address";
                        description "Enter the group list instance";

                        ///nokia-state/state/router/mld/forwarding-group-interface/host/group/group-address
                        leaf group-address {
                            type types-sros:ipv6-multicast-address;
                            description "Group address of multicast channel";
                        }

                        ///nokia-state/state/router/mld/forwarding-group-interface/host/group/group-type
                        leaf group-type {
                            type types-igmp:learn-type;
                        }

                        ///nokia-state/state/router/mld/forwarding-group-interface/host/group/filter-mode
                        leaf filter-mode {
                            type types-igmp:filter-mode;
                        }

                        ///nokia-state/state/router/mld/forwarding-group-interface/host/group/expiry-time
                        leaf expiry-time {
                            type uint32;
                            units "seconds";
                            description "The time left before multicast group timeout.";
                        }

                        ///nokia-state/state/router/mld/forwarding-group-interface/host/group/up-time
                        leaf up-time {
                            type uint32;
                            units "seconds";
                            description "The time elapsed since this entry was created.";
                        }

                        ///nokia-state/state/router/mld/forwarding-group-interface/host/group/v1-host-timer
                        leaf v1-host-timer {
                            type uint32;
                            units "seconds";
                            description
                                "The time remaining until the local router will assume that
                                 there are no longer any version 1 members.";
                        }

                        ///nokia-state/state/router/mld/forwarding-group-interface/host/group/mld-compatibility-mode
                        leaf mld-compatibility-mode {
                            type types-igmp:mld-version;
                            description "Compatibility with older version routers.";
                        }

                        ///nokia-state/state/router/mld/forwarding-group-interface/host/group/last-reporter
                        leaf last-reporter {
                            type types-sros:ip-address;
                            description
                                "The last host address which has sent the report to join
                                 the multicast group.";
                        }

                        ///nokia-state/state/router/mld/forwarding-group-interface/host/group/source
                        list source {
                            key "source-address";
                            description "Enter the source list instance";

                            ///nokia-state/state/router/mld/forwarding-group-interface/host/group/source/source-address
                            leaf source-address {
                                type types-sros:ipv6-address;
                                description "Source address of multicast channel.";
                            }

                            ///nokia-state/state/router/mld/forwarding-group-interface/host/group/source/source-type
                            leaf source-type {
                                type types-igmp:learn-type;
                            }

                            ///nokia-state/state/router/mld/forwarding-group-interface/host/group/source/forwarding-state
                            leaf forwarding-state {
                                type types-igmp:forwarding-state;
                                description "Traffic forwardeding state on this port.";
                            }

                            ///nokia-state/state/router/mld/forwarding-group-interface/host/group/source/expiry-time
                            leaf expiry-time {
                                type uint32;
                                units "seconds";
                                description "The time left before multicast group timeout.";
                            }

                            ///nokia-state/state/router/mld/forwarding-group-interface/host/group/source/up-time
                            leaf up-time {
                                type uint32;
                                units "seconds";
                                description "The time elapsed since this entry was created.";
                            }

                        } // list source

                    } // list group

                } // list host

            } // list forwarding-group-interface

            ///nokia-state/state/router/mld/host
            list host {
                key "ip-address mac-address pppoe-session-id";
                description "Enter the host list instance";

                ///nokia-state/state/router/mld/host/ip-address
                leaf ip-address {
                    type types-sros:ipv6-address;
                    description "The IP address of this host.";
                }

                ///nokia-state/state/router/mld/host/mac-address
                leaf mac-address {
                    type yang:mac-address;
                    description "The MAC address of this host.";
                }

                ///nokia-state/state/router/mld/host/pppoe-session-id
                leaf pppoe-session-id {
                    type uint32;
                    description "The PPPoE session id of this host.";
                }

                ///nokia-state/state/router/mld/host/group-interface-name
                leaf group-interface-name {
                    type leafref {
                        path "../../group-interface/group-interface-name";
                    }
                    description "The group-interface this host belongs to.";
                }

            } // list host

            ///nokia-state/state/router/mld/ipsec-static-tunnel
            list ipsec-static-tunnel {
                key "tunnel-name sa-id";
                description "Enter the ipsec-static-tunnel list instance";

                ///nokia-state/state/router/mld/ipsec-static-tunnel/tunnel-name
                leaf tunnel-name {
                    type types-sros:named-item;
                    description "IPsec tunnel name.";
                }

                ///nokia-state/state/router/mld/ipsec-static-tunnel/sa-id
                leaf sa-id {
                    type uint32 {
                        range "1..16";
                    }
                    description "Security Association Id";
                }

                ///nokia-state/state/router/mld/ipsec-static-tunnel/oper-state
                leaf oper-state {
                    type types-sros:oper-state;
                    description "The current operating state of the MLD protocol on this interface.";
                }

                ///nokia-state/state/router/mld/ipsec-static-tunnel/oper-version
                leaf oper-version {
                    type types-igmp:mld-version;
                    description "The operational version of the MLD which is running on this interface.";
                }

                ///nokia-state/state/router/mld/ipsec-static-tunnel/group-count
                leaf group-count {
                    type int32;
                    description "The number of multicast groups which have been learned on this interface.";
                }

                ///nokia-state/state/router/mld/ipsec-static-tunnel/next-general-query-time
                leaf next-general-query-time {
                    type uint32;
                    units "seconds";
                    description
                        "The time remaining before the general query is sent on this interface
                         if this router is the querier.";
                }

                ///nokia-state/state/router/mld/ipsec-static-tunnel/statistics
                container statistics {
                    description "Enter the statistics context";

                    ///nokia-state/state/router/mld/ipsec-static-tunnel/statistics/received
                    container received {
                        description "Enter the received context";

                        ///nokia-state/state/router/mld/ipsec-static-tunnel/statistics/received/general-queries
                        leaf general-queries {
                            type yang:counter32;
                            description "General Queries.";
                        }

                        ///nokia-state/state/router/mld/ipsec-static-tunnel/statistics/received/group-queries
                        leaf group-queries {
                            type yang:counter32;
                            description "Group Specific Queries.";
                        }

                        ///nokia-state/state/router/mld/ipsec-static-tunnel/statistics/received/group-source-queries
                        leaf group-source-queries {
                            type yang:counter32;
                            description "Group and Source Specific Queries.";
                        }

                        ///nokia-state/state/router/mld/ipsec-static-tunnel/statistics/received/v1-reports
                        leaf v1-reports {
                            type yang:counter32;
                            description "V1 Reports.";
                        }

                        ///nokia-state/state/router/mld/ipsec-static-tunnel/statistics/received/v2-reports
                        leaf v2-reports {
                            type yang:counter32;
                            description "V2 Reports.";
                        }

                        ///nokia-state/state/router/mld/ipsec-static-tunnel/statistics/received/v3-reports
                        leaf v3-reports {
                            type yang:counter32;
                            description "V3 Reports.";
                        }

                        ///nokia-state/state/router/mld/ipsec-static-tunnel/statistics/received/leaves
                        leaf leaves {
                            type yang:counter32;
                            description "Leaves.";
                        }

                        ///nokia-state/state/router/mld/ipsec-static-tunnel/statistics/received/drops
                        leaf drops {
                            type yang:counter32;
                            description "Total number of dropped packets.";
                        }

                    } // container received

                    ///nokia-state/state/router/mld/ipsec-static-tunnel/statistics/transmitted
                    container transmitted {
                        description "Enter the transmitted context";

                        ///nokia-state/state/router/mld/ipsec-static-tunnel/statistics/transmitted/general-queries
                        leaf general-queries {
                            type yang:counter32;
                            description "General Queries.";
                        }

                        ///nokia-state/state/router/mld/ipsec-static-tunnel/statistics/transmitted/group-queries
                        leaf group-queries {
                            type yang:counter32;
                            description "Group Specific Queries.";
                        }

                        ///nokia-state/state/router/mld/ipsec-static-tunnel/statistics/transmitted/group-source-queries
                        leaf group-source-queries {
                            type yang:counter32;
                            description "Group and Source Specific Queries.";
                        }

                        ///nokia-state/state/router/mld/ipsec-static-tunnel/statistics/transmitted/v1-reports
                        leaf v1-reports {
                            type yang:counter32;
                            description "V1 Reports.";
                        }

                        ///nokia-state/state/router/mld/ipsec-static-tunnel/statistics/transmitted/v2-reports
                        leaf v2-reports {
                            type yang:counter32;
                            description "V2 Reports.";
                        }

                        ///nokia-state/state/router/mld/ipsec-static-tunnel/statistics/transmitted/v3-reports
                        leaf v3-reports {
                            type yang:counter32;
                            description "V3 Reports.";
                        }

                        ///nokia-state/state/router/mld/ipsec-static-tunnel/statistics/transmitted/leaves
                        leaf leaves {
                            type yang:counter32;
                            description "Leaves.";
                        }

                        ///nokia-state/state/router/mld/ipsec-static-tunnel/statistics/transmitted/drops
                        leaf drops {
                            type yang:counter32;
                            description "Total number of dropped packets.";
                        }

                        ///nokia-state/state/router/mld/ipsec-static-tunnel/statistics/transmitted/errors
                        leaf errors {
                            type yang:counter32;
                            description "Transmission Errors.";
                        }

                    } // container transmitted

                    ///nokia-state/state/router/mld/ipsec-static-tunnel/statistics/error
                    container error {
                        description "Enter the error context";

                        ///nokia-state/state/router/mld/ipsec-static-tunnel/statistics/error/bad-length
                        leaf bad-length {
                            type yang:counter32;
                            description "Bad length.";
                        }

                        ///nokia-state/state/router/mld/ipsec-static-tunnel/statistics/error/bad-ip-checksum
                        leaf bad-ip-checksum {
                            type yang:counter32;
                            description "Bad Ip checksum.";
                        }

                        ///nokia-state/state/router/mld/ipsec-static-tunnel/statistics/error/unknown-type
                        leaf unknown-type {
                            type yang:counter32;
                            description "Unknown type.";
                        }

                        ///nokia-state/state/router/mld/ipsec-static-tunnel/statistics/error/wrong-version
                        leaf wrong-version {
                            type yang:counter32;
                            description "Wrong version.";
                        }

                        ///nokia-state/state/router/mld/ipsec-static-tunnel/statistics/error/import-policy-drops
                        leaf import-policy-drops {
                            type yang:counter32;
                            description
                                "Number of times we matched the host IP address or group or
                                 source addresses specified in the import policy.";
                        }

                        ///nokia-state/state/router/mld/ipsec-static-tunnel/statistics/error/missing-router-alert
                        leaf missing-router-alert {
                            type yang:counter32;
                            description "Router alert flag is not set.";
                        }

                        ///nokia-state/state/router/mld/ipsec-static-tunnel/statistics/error/bad-encoding
                        leaf bad-encoding {
                            type yang:counter32;
                            description "Badly encoded.";
                        }

                        ///nokia-state/state/router/mld/ipsec-static-tunnel/statistics/error/local-scope
                        leaf local-scope {
                            type yang:counter32;
                            description "Link-local scope multicast group address.";
                        }

                        ///nokia-state/state/router/mld/ipsec-static-tunnel/statistics/error/mcac-policy-drops
                        leaf mcac-policy-drops {
                            type yang:counter32;
                            description
                                "Number of times a join is dropped because of applying a
                                 multicast CAC policy.";
                        }

                        ///nokia-state/state/router/mld/ipsec-static-tunnel/statistics/error/reached-maximum-number-groups
                        leaf reached-maximum-number-groups {
                            type yang:counter32;
                            description
                                "Number of times a join is dropped because we reached the maximum
                                 number of groups.";
                        }

                        ///nokia-state/state/router/mld/ipsec-static-tunnel/statistics/error/reached-maximum-number-group-sources
                        leaf reached-maximum-number-group-sources {
                            type yang:counter32;
                            description
                                "Number of times a join is dropped because we reached the maximum
                                 number group-source combinations.";
                        }

                        ///nokia-state/state/router/mld/ipsec-static-tunnel/statistics/error/reached-maximum-number-sources
                        leaf reached-maximum-number-sources {
                            type yang:counter32;
                            description
                                "Number of times a join is dropped because we reached the maximum
                                 number of sources per group.";
                        }

                        ///nokia-state/state/router/mld/ipsec-static-tunnel/statistics/error/out-of-memory-drops
                        leaf out-of-memory-drops {
                            type yang:counter32;
                            description "Number of times a join is dropped because we ran out of memory.";
                        }

                        ///nokia-state/state/router/mld/ipsec-static-tunnel/statistics/error/mcs-failures
                        leaf mcs-failures {
                            type yang:counter32;
                            description "Number of times a group could not be synced through multi chassis synchronisation (MCS).";
                        }

                        ///nokia-state/state/router/mld/ipsec-static-tunnel/statistics/error/non-local
                        leaf non-local {
                            type yang:counter32;
                            description "Non-local sender source IP address.";
                        }

                    } // container error

                } // container statistics

                ///nokia-state/state/router/mld/ipsec-static-tunnel/group
                list group {
                    key "group-address";
                    description "Enter the group list instance";

                    ///nokia-state/state/router/mld/ipsec-static-tunnel/group/group-address
                    leaf group-address {
                        type types-sros:ipv6-multicast-address;
                        description "Group address of multicast channel";
                    }

                    ///nokia-state/state/router/mld/ipsec-static-tunnel/group/group-type
                    leaf group-type {
                        type types-igmp:learn-type;
                    }

                    ///nokia-state/state/router/mld/ipsec-static-tunnel/group/filter-mode
                    leaf filter-mode {
                        type types-igmp:filter-mode;
                    }

                    ///nokia-state/state/router/mld/ipsec-static-tunnel/group/expiry-time
                    leaf expiry-time {
                        type uint32;
                        units "seconds";
                        description "The time left before multicast group timeout.";
                    }

                    ///nokia-state/state/router/mld/ipsec-static-tunnel/group/up-time
                    leaf up-time {
                        type uint32;
                        units "seconds";
                        description "The time elapsed since this entry was created.";
                    }

                    ///nokia-state/state/router/mld/ipsec-static-tunnel/group/v1-host-timer
                    leaf v1-host-timer {
                        type uint32;
                        units "seconds";
                        description
                            "The time remaining until the local router will assume that
                             there are no longer any version 1 members.";
                    }

                    ///nokia-state/state/router/mld/ipsec-static-tunnel/group/v2-host-timer
                    leaf v2-host-timer {
                        type uint32;
                        units "seconds";
                        description
                            "The time remaining until the local router will assume that
                             there are no longer any version 2 members.";
                    }

                    ///nokia-state/state/router/mld/ipsec-static-tunnel/group/igmp-compatibility-mode
                    leaf igmp-compatibility-mode {
                        type types-igmp:igmp-version;
                        description "Compatibility with older version routers.";
                    }

                    ///nokia-state/state/router/mld/ipsec-static-tunnel/group/last-reporter
                    leaf last-reporter {
                        type types-sros:ip-address;
                        description
                            "The last host address which has sent the report to join
                             the multicast group.";
                    }

                    ///nokia-state/state/router/mld/ipsec-static-tunnel/group/source
                    list source {
                        key "source-address";
                        description "Enter the source list instance";

                        ///nokia-state/state/router/mld/ipsec-static-tunnel/group/source/source-address
                        leaf source-address {
                            type types-sros:ipv6-address;
                            description "Source address of multicast channel.";
                        }

                        ///nokia-state/state/router/mld/ipsec-static-tunnel/group/source/source-type
                        leaf source-type {
                            type types-igmp:learn-type;
                        }

                        ///nokia-state/state/router/mld/ipsec-static-tunnel/group/source/forwarding-state
                        leaf forwarding-state {
                            type types-igmp:forwarding-state;
                            description "Traffic forwardeding state on this port.";
                        }

                        ///nokia-state/state/router/mld/ipsec-static-tunnel/group/source/expiry-time
                        leaf expiry-time {
                            type uint32;
                            units "seconds";
                            description "The time left before multicast group timeout.";
                        }

                        ///nokia-state/state/router/mld/ipsec-static-tunnel/group/source/up-time
                        leaf up-time {
                            type uint32;
                            units "seconds";
                            description "The time elapsed since this entry was created.";
                        }

                    } // list source

                } // list group

            } // list ipsec-static-tunnel

            ///nokia-state/state/router/mld/ipsec-ru-tunnel
            list ipsec-ru-tunnel {
                key "gateway-name sap-address sap-port sa-id";
                description "Enter the ipsec-ru-tunnel list instance";

                ///nokia-state/state/router/mld/ipsec-ru-tunnel/gateway-name
                leaf gateway-name {
                    type types-sros:named-item;
                    description "IPsec gateway name.";
                }

                ///nokia-state/state/router/mld/ipsec-ru-tunnel/sap-address
                leaf sap-address {
                    type types-sros:ip-address;
                    description "The address of the SAP IPsec gateway to the tunnel.";
                }

                ///nokia-state/state/router/mld/ipsec-ru-tunnel/sap-port
                leaf sap-port {
                    type types-sros:tcp-udp-port;
                    description "The UDP port of the SAP IPsec gateway to the tunnel.";
                }

                ///nokia-state/state/router/mld/ipsec-ru-tunnel/sa-id
                leaf sa-id {
                    type uint32 {
                        range "1..16";
                    }
                    description "SA Id";
                }

                ///nokia-state/state/router/mld/ipsec-ru-tunnel/oper-state
                leaf oper-state {
                    type types-sros:oper-state;
                    description "The current operating state of the MLD protocol on this interface.";
                }

                ///nokia-state/state/router/mld/ipsec-ru-tunnel/oper-version
                leaf oper-version {
                    type types-igmp:mld-version;
                    description "The operational version of the MLD which is running on this interface.";
                }

                ///nokia-state/state/router/mld/ipsec-ru-tunnel/group-count
                leaf group-count {
                    type int32;
                    description "The number of multicast groups which have been learned on this interface.";
                }

                ///nokia-state/state/router/mld/ipsec-ru-tunnel/next-general-query-time
                leaf next-general-query-time {
                    type uint32;
                    units "seconds";
                    description
                        "The time remaining before the general query is sent on this interface
                         if this router is the querier.";
                }

                ///nokia-state/state/router/mld/ipsec-ru-tunnel/statistics
                container statistics {
                    description "Enter the statistics context";

                    ///nokia-state/state/router/mld/ipsec-ru-tunnel/statistics/received
                    container received {
                        description "Enter the received context";

                        ///nokia-state/state/router/mld/ipsec-ru-tunnel/statistics/received/general-queries
                        leaf general-queries {
                            type yang:counter32;
                            description "General Queries.";
                        }

                        ///nokia-state/state/router/mld/ipsec-ru-tunnel/statistics/received/group-queries
                        leaf group-queries {
                            type yang:counter32;
                            description "Group Specific Queries.";
                        }

                        ///nokia-state/state/router/mld/ipsec-ru-tunnel/statistics/received/group-source-queries
                        leaf group-source-queries {
                            type yang:counter32;
                            description "Group and Source Specific Queries.";
                        }

                        ///nokia-state/state/router/mld/ipsec-ru-tunnel/statistics/received/v1-reports
                        leaf v1-reports {
                            type yang:counter32;
                            description "V1 Reports.";
                        }

                        ///nokia-state/state/router/mld/ipsec-ru-tunnel/statistics/received/v2-reports
                        leaf v2-reports {
                            type yang:counter32;
                            description "V2 Reports.";
                        }

                        ///nokia-state/state/router/mld/ipsec-ru-tunnel/statistics/received/v3-reports
                        leaf v3-reports {
                            type yang:counter32;
                            description "V3 Reports.";
                        }

                        ///nokia-state/state/router/mld/ipsec-ru-tunnel/statistics/received/leaves
                        leaf leaves {
                            type yang:counter32;
                            description "Leaves.";
                        }

                        ///nokia-state/state/router/mld/ipsec-ru-tunnel/statistics/received/drops
                        leaf drops {
                            type yang:counter32;
                            description "Total number of dropped packets.";
                        }

                    } // container received

                    ///nokia-state/state/router/mld/ipsec-ru-tunnel/statistics/transmitted
                    container transmitted {
                        description "Enter the transmitted context";

                        ///nokia-state/state/router/mld/ipsec-ru-tunnel/statistics/transmitted/general-queries
                        leaf general-queries {
                            type yang:counter32;
                            description "General Queries.";
                        }

                        ///nokia-state/state/router/mld/ipsec-ru-tunnel/statistics/transmitted/group-queries
                        leaf group-queries {
                            type yang:counter32;
                            description "Group Specific Queries.";
                        }

                        ///nokia-state/state/router/mld/ipsec-ru-tunnel/statistics/transmitted/group-source-queries
                        leaf group-source-queries {
                            type yang:counter32;
                            description "Group and Source Specific Queries.";
                        }

                        ///nokia-state/state/router/mld/ipsec-ru-tunnel/statistics/transmitted/v1-reports
                        leaf v1-reports {
                            type yang:counter32;
                            description "V1 Reports.";
                        }

                        ///nokia-state/state/router/mld/ipsec-ru-tunnel/statistics/transmitted/v2-reports
                        leaf v2-reports {
                            type yang:counter32;
                            description "V2 Reports.";
                        }

                        ///nokia-state/state/router/mld/ipsec-ru-tunnel/statistics/transmitted/v3-reports
                        leaf v3-reports {
                            type yang:counter32;
                            description "V3 Reports.";
                        }

                        ///nokia-state/state/router/mld/ipsec-ru-tunnel/statistics/transmitted/leaves
                        leaf leaves {
                            type yang:counter32;
                            description "Leaves.";
                        }

                        ///nokia-state/state/router/mld/ipsec-ru-tunnel/statistics/transmitted/drops
                        leaf drops {
                            type yang:counter32;
                            description "Total number of dropped packets.";
                        }

                        ///nokia-state/state/router/mld/ipsec-ru-tunnel/statistics/transmitted/errors
                        leaf errors {
                            type yang:counter32;
                            description "Transmission Errors.";
                        }

                    } // container transmitted

                    ///nokia-state/state/router/mld/ipsec-ru-tunnel/statistics/error
                    container error {
                        description "Enter the error context";

                        ///nokia-state/state/router/mld/ipsec-ru-tunnel/statistics/error/bad-length
                        leaf bad-length {
                            type yang:counter32;
                            description "Bad length.";
                        }

                        ///nokia-state/state/router/mld/ipsec-ru-tunnel/statistics/error/bad-ip-checksum
                        leaf bad-ip-checksum {
                            type yang:counter32;
                            description "Bad Ip checksum.";
                        }

                        ///nokia-state/state/router/mld/ipsec-ru-tunnel/statistics/error/unknown-type
                        leaf unknown-type {
                            type yang:counter32;
                            description "Unknown type.";
                        }

                        ///nokia-state/state/router/mld/ipsec-ru-tunnel/statistics/error/wrong-version
                        leaf wrong-version {
                            type yang:counter32;
                            description "Wrong version.";
                        }

                        ///nokia-state/state/router/mld/ipsec-ru-tunnel/statistics/error/import-policy-drops
                        leaf import-policy-drops {
                            type yang:counter32;
                            description
                                "Number of times we matched the host IP address or group or
                                 source addresses specified in the import policy.";
                        }

                        ///nokia-state/state/router/mld/ipsec-ru-tunnel/statistics/error/missing-router-alert
                        leaf missing-router-alert {
                            type yang:counter32;
                            description "Router alert flag is not set.";
                        }

                        ///nokia-state/state/router/mld/ipsec-ru-tunnel/statistics/error/bad-encoding
                        leaf bad-encoding {
                            type yang:counter32;
                            description "Badly encoded.";
                        }

                        ///nokia-state/state/router/mld/ipsec-ru-tunnel/statistics/error/local-scope
                        leaf local-scope {
                            type yang:counter32;
                            description "Link-local scope multicast group address.";
                        }

                        ///nokia-state/state/router/mld/ipsec-ru-tunnel/statistics/error/mcac-policy-drops
                        leaf mcac-policy-drops {
                            type yang:counter32;
                            description
                                "Number of times a join is dropped because of applying a
                                 multicast CAC policy.";
                        }

                        ///nokia-state/state/router/mld/ipsec-ru-tunnel/statistics/error/reached-maximum-number-groups
                        leaf reached-maximum-number-groups {
                            type yang:counter32;
                            description
                                "Number of times a join is dropped because we reached the maximum
                                 number of groups.";
                        }

                        ///nokia-state/state/router/mld/ipsec-ru-tunnel/statistics/error/reached-maximum-number-group-sources
                        leaf reached-maximum-number-group-sources {
                            type yang:counter32;
                            description
                                "Number of times a join is dropped because we reached the maximum
                                 number group-source combinations.";
                        }

                        ///nokia-state/state/router/mld/ipsec-ru-tunnel/statistics/error/reached-maximum-number-sources
                        leaf reached-maximum-number-sources {
                            type yang:counter32;
                            description
                                "Number of times a join is dropped because we reached the maximum
                                 number of sources per group.";
                        }

                        ///nokia-state/state/router/mld/ipsec-ru-tunnel/statistics/error/out-of-memory-drops
                        leaf out-of-memory-drops {
                            type yang:counter32;
                            description "Number of times a join is dropped because we ran out of memory.";
                        }

                        ///nokia-state/state/router/mld/ipsec-ru-tunnel/statistics/error/mcs-failures
                        leaf mcs-failures {
                            type yang:counter32;
                            description "Number of times a group could not be synced through multi chassis synchronisation (MCS).";
                        }

                        ///nokia-state/state/router/mld/ipsec-ru-tunnel/statistics/error/non-local
                        leaf non-local {
                            type yang:counter32;
                            description "Non-local sender source IP address.";
                        }

                    } // container error

                } // container statistics

                ///nokia-state/state/router/mld/ipsec-ru-tunnel/group
                list group {
                    key "group-address";
                    description "Enter the group list instance";

                    ///nokia-state/state/router/mld/ipsec-ru-tunnel/group/group-address
                    leaf group-address {
                        type types-sros:ipv6-multicast-address;
                        description "Group address of multicast channel";
                    }

                    ///nokia-state/state/router/mld/ipsec-ru-tunnel/group/group-type
                    leaf group-type {
                        type types-igmp:learn-type;
                    }

                    ///nokia-state/state/router/mld/ipsec-ru-tunnel/group/filter-mode
                    leaf filter-mode {
                        type types-igmp:filter-mode;
                    }

                    ///nokia-state/state/router/mld/ipsec-ru-tunnel/group/expiry-time
                    leaf expiry-time {
                        type uint32;
                        units "seconds";
                        description "The time left before multicast group timeout.";
                    }

                    ///nokia-state/state/router/mld/ipsec-ru-tunnel/group/up-time
                    leaf up-time {
                        type uint32;
                        units "seconds";
                        description "The time elapsed since this entry was created.";
                    }

                    ///nokia-state/state/router/mld/ipsec-ru-tunnel/group/v1-host-timer
                    leaf v1-host-timer {
                        type uint32;
                        units "seconds";
                        description
                            "The time remaining until the local router will assume that
                             there are no longer any version 1 members.";
                    }

                    ///nokia-state/state/router/mld/ipsec-ru-tunnel/group/v2-host-timer
                    leaf v2-host-timer {
                        type uint32;
                        units "seconds";
                        description
                            "The time remaining until the local router will assume that
                             there are no longer any version 2 members.";
                    }

                    ///nokia-state/state/router/mld/ipsec-ru-tunnel/group/igmp-compatibility-mode
                    leaf igmp-compatibility-mode {
                        type types-igmp:igmp-version;
                        description "Compatibility with older version routers.";
                    }

                    ///nokia-state/state/router/mld/ipsec-ru-tunnel/group/last-reporter
                    leaf last-reporter {
                        type types-sros:ip-address;
                        description
                            "The last host address which has sent the report to join
                             the multicast group.";
                    }

                    ///nokia-state/state/router/mld/ipsec-ru-tunnel/group/source
                    list source {
                        key "source-address";
                        description "Enter the source list instance";

                        ///nokia-state/state/router/mld/ipsec-ru-tunnel/group/source/source-address
                        leaf source-address {
                            type types-sros:ipv6-address;
                            description "Source address of multicast channel.";
                        }

                        ///nokia-state/state/router/mld/ipsec-ru-tunnel/group/source/source-type
                        leaf source-type {
                            type types-igmp:learn-type;
                        }

                        ///nokia-state/state/router/mld/ipsec-ru-tunnel/group/source/forwarding-state
                        leaf forwarding-state {
                            type types-igmp:forwarding-state;
                            description "Traffic forwardeding state on this port.";
                        }

                        ///nokia-state/state/router/mld/ipsec-ru-tunnel/group/source/expiry-time
                        leaf expiry-time {
                            type uint32;
                            units "seconds";
                            description "The time left before multicast group timeout.";
                        }

                        ///nokia-state/state/router/mld/ipsec-ru-tunnel/group/source/up-time
                        leaf up-time {
                            type uint32;
                            units "seconds";
                            description "The time elapsed since this entry was created.";
                        }

                    } // list source

                } // list group

            } // list ipsec-ru-tunnel

        } // container mld

    } // grouping state-router-mld

}
