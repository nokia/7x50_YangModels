submodule nokia-conf-system-login-control {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure system login-control parameters on SR OS based routers.

         Copyright 2016 Nokia. All rights reserved. Reproduction of this document
         is authorized on the condition that the foregoing copyright notice is included.

         This nokia-conf-system-login-control YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping conf-system-login-control {
        ///nokia-conf/configure/system/login-control
        container login-control {
            description "Enter the login-control context";

            ///nokia-conf/configure/system/login-control/exponential-backoff
            leaf exponential-backoff {
                type boolean;
                default "false";
                description "Enable exponential-backoff of the login prompt";
            }

            ///nokia-conf/configure/system/login-control/idle-timeout
            leaf idle-timeout {
                type union {
                    type enumeration {
                        enum none                           { value 9999; }
                    }
                    type int64 {
                        range "1..1440";
                    }
                }
                units "minutes";
                default "30";
                description "Idle timeout for FTP, console, or Telnet sessions";
            }

            ///nokia-conf/configure/system/login-control/login-banner
            leaf login-banner {
                type boolean;
                default "false";
                description "Display login banner";
            }

            ///nokia-conf/configure/system/login-control/apply-groups
            leaf-list apply-groups {
                type leafref {
                    path "../../../groups/group/name";
                }
                max-elements 8;
                ordered-by user;
                description "Apply a configuration group at this level";
            }

            ///nokia-conf/configure/system/login-control/apply-groups-exclude
            leaf-list apply-groups-exclude {
                type leafref {
                    path "../../../groups/group/name";
                }
                max-elements 8;
                ordered-by user;
                description "Exclude a configuration group at this level";
            }

            ///nokia-conf/configure/system/login-control/login-scripts
            container login-scripts {
                description "Enter the login-scripts context";

                ///nokia-conf/configure/system/login-control/login-scripts/global-script
                leaf global-script {
                    type types-sros:string-not-all-spaces {
                        length "1..180";
                    }
                    description "URL of the global CLI login script";
                }

                ///nokia-conf/configure/system/login-control/login-scripts/per-user-script
                container per-user-script {
                    description "Enter the per-user-script context";

                    ///nokia-conf/configure/system/login-control/login-scripts/per-user-script/user-directory
                    leaf user-directory {
                        type types-sros:string-not-all-spaces {
                            length "1..180";
                        }
                        description "Directory name of user-defined login script";
                    }

                    ///nokia-conf/configure/system/login-control/login-scripts/per-user-script/file-name
                    leaf file-name {
                        type types-sros:filename;
                        description "File name of the per-user login script";
                    }

                } // container per-user-script

            } // container login-scripts

            ///nokia-conf/configure/system/login-control/motd
            container motd {
                description "Enter the motd context";

                ///nokia-conf/configure/system/login-control/motd/motd
                choice motd {
                    ///nokia-conf/configure/system/login-control/motd/motd/url
                    case url {

                        ///nokia-conf/configure/system/login-control/motd/motd/url/url
                        leaf url {
                            type types-sros:string-not-all-spaces {
                                length "1..180";
                            }
                            description "URL of the location of message of the day";
                        }

                    }
                    ///nokia-conf/configure/system/login-control/motd/motd/text
                    case text {

                        ///nokia-conf/configure/system/login-control/motd/motd/text/text
                        leaf text {
                            type types-sros:string-not-all-spaces {
                                length "1..900";
                            }
                            description "Message of the day displayed after console login";
                        }

                    }
                }
            } // container motd

            ///nokia-conf/configure/system/login-control/pre-login-message
            container pre-login-message {
                description "Enter the pre-login-message context";

                ///nokia-conf/configure/system/login-control/pre-login-message/message
                leaf message {
                    type types-sros:string-not-all-spaces {
                        length "1..900";
                    }
                    description "Message displayed prior to the login prompt";
                }

                ///nokia-conf/configure/system/login-control/pre-login-message/name
                leaf name {
                    type boolean;
                    default "false";
                    description "Display the system name before the pre-login message";
                }

            } // container pre-login-message

            ///nokia-conf/configure/system/login-control/ftp
            container ftp {
                description "Enter the ftp context";

                ///nokia-conf/configure/system/login-control/ftp/inbound-max-sessions
                leaf inbound-max-sessions {
                    type uint32 {
                        range "0..5";
                    }
                    default "3";
                    description "Maximum number of concurrent inbound FTP sessions";
                }

            } // container ftp

            ///nokia-conf/configure/system/login-control/ssh
            container ssh {
                description "Enter the ssh context";

                ///nokia-conf/configure/system/login-control/ssh/graceful-shutdown
                leaf graceful-shutdown {
                    type boolean;
                    default "true";
                    description "Allow graceful shutdown of SSH sessions";
                }

                ///nokia-conf/configure/system/login-control/ssh/inbound-max-sessions
                leaf inbound-max-sessions {
                    type uint32 {
                        range "0..50";
                    }
                    default "5";
                    description "Maximum number of concurrent inbound sessions";
                }

                ///nokia-conf/configure/system/login-control/ssh/outbound-max-sessions
                leaf outbound-max-sessions {
                    type uint32 {
                        range "0..15";
                    }
                    default "5";
                    description "Maximum number of concurrent outbound sessions";
                }

                ///nokia-conf/configure/system/login-control/ssh/ttl-security
                leaf ttl-security {
                    type uint32 {
                        range "1..255";
                    }
                    description "Minimum TTL value for incoming packets";
                }

            } // container ssh

            ///nokia-conf/configure/system/login-control/telnet
            container telnet {
                description "Enter the telnet context";

                ///nokia-conf/configure/system/login-control/telnet/graceful-shutdown
                leaf graceful-shutdown {
                    type boolean;
                    default "false";
                    description "Allow graceful shutdown of Telnet sessions";
                }

                ///nokia-conf/configure/system/login-control/telnet/inbound-max-sessions
                leaf inbound-max-sessions {
                    type uint32 {
                        range "0..50";
                    }
                    default "5";
                    description "Maximum number of concurrent inbound sessions";
                }

                ///nokia-conf/configure/system/login-control/telnet/outbound-max-sessions
                leaf outbound-max-sessions {
                    type uint32 {
                        range "0..15";
                    }
                    default "5";
                    description "Maximum number of concurrent outbound sessions";
                }

                ///nokia-conf/configure/system/login-control/telnet/ttl-security
                leaf ttl-security {
                    type uint32 {
                        range "1..255";
                    }
                    description "Minimum TTL value for incoming packets";
                }

            } // container telnet

        } // container login-control

    } // grouping conf-system-login-control

}
