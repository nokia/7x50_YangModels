submodule nokia-conf-router-l2tp {

    yang-version "1.1";

    belongs-to nokia-conf { prefix "conf"; }

    import nokia-sros-yang-extensions     { prefix "sros-ext"; }
    import nokia-types-l2tp               { prefix "types-l2tp"; }
    import nokia-types-ppp                { prefix "types-ppp"; }
    import nokia-types-services           { prefix "types-services"; }
    import nokia-types-sros               { prefix "types-sros"; }

    include nokia-conf-aaa;
    include nokia-conf-groups;
    include nokia-conf-isa;
    include nokia-conf-redundancy;

    sros-ext:sros-major-release "rel23";
    organization "Nokia";
    contact
        "Nokia SR OS Support
         Web: <http://www.nokia.com>";
    description
        "Nokia YANG Data model to configure l2tp on SR OS based routers.

         Copyright 2016 Nokia. All rights reserved. Reproduction of this document
         is authorized on the condition that the foregoing copyright notice is included.

         This nokia-conf-router-l2tp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-11-18";

    grouping conf-router-l2tp {
        ///nokia-conf/configure/router/l2tp
        container l2tp {
            when "../router-name = 'Base'" {
                description "only allowed in the Base router";
            }
            description "Enable the l2tp context";

            ///nokia-conf/configure/router/l2tp/admin-state
            leaf admin-state {
                type types-sros:admin-state;
                default "disable";
                description "Administrative state of L2TP";
            }

            ///nokia-conf/configure/router/l2tp/local-address
            leaf local-address {
                type types-sros:ipv4-unicast-address;
                description "Local address";
            }

            ///nokia-conf/configure/router/l2tp/receive-window-size
            leaf receive-window-size {
                type types-l2tp:base-receive-window-size;
                description "L2TP receive window size";
            }

            ///nokia-conf/configure/router/l2tp/hello-interval
            leaf hello-interval {
                type types-l2tp:base-hello-interval;
                description "Hello interval";
            }

            ///nokia-conf/configure/router/l2tp/idle-timeout
            leaf idle-timeout {
                type types-l2tp:base-idle-timeout;
                description "Idle timeout";
            }

            ///nokia-conf/configure/router/l2tp/destruct-timeout
            leaf destruct-timeout {
                type types-l2tp:base-destruct-timeout;
                description "Destruction timeout";
            }

            ///nokia-conf/configure/router/l2tp/max-retries-estab
            leaf max-retries-estab {
                type types-l2tp:base-max-retries;
                description "Maximum retries for established tunnels";
            }

            ///nokia-conf/configure/router/l2tp/max-retries-not-estab
            leaf max-retries-not-estab {
                type types-l2tp:base-max-retries;
                description "Maximum retries for unestablished tunnels";
            }

            ///nokia-conf/configure/router/l2tp/rtm-debounce-time
            leaf rtm-debounce-time {
                type types-l2tp:rtm-debounce-time;
                description "Debounce timer that declares L2TP action for route table management events";
            }

            ///nokia-conf/configure/router/l2tp/radius-accounting-policy
            leaf radius-accounting-policy {
                type leafref {
                    path "../../../aaa/radius/l2tp-accounting-policy/name";
                }
                description "RADIUS accounting policy";
            }

            ///nokia-conf/configure/router/l2tp/peer-address-change-policy
            leaf peer-address-change-policy {
                type types-l2tp:peer-address-change-policy-option;
                description "Reaction for L2TP response from a different address";
            }

            ///nokia-conf/configure/router/l2tp/local-name
            leaf local-name {
                type types-l2tp:host-name;
                description "Local host name";
            }

            ///nokia-conf/configure/router/l2tp/password
            leaf password {
                type types-sros:encrypted-leaf {
                    length "1..115";
                }
                description "L2TP password";
            }

            ///nokia-conf/configure/router/l2tp/challenge
            leaf challenge {
                type boolean;
                default "false";
                description "Use challenge-response authentication";
            }

            ///nokia-conf/configure/router/l2tp/avp-hiding
            leaf avp-hiding {
                type types-l2tp:base-avp-hiding;
                description "Attribute of the Value Pair (AVP) hiding algorithm";
            }

            ///nokia-conf/configure/router/l2tp/session-limit
            leaf session-limit {
                type types-l2tp:base-session-limit;
                description "L2TP session limit of this router";
            }

            ///nokia-conf/configure/router/l2tp/group-session-limit
            leaf group-session-limit {
                type types-l2tp:base-session-limit;
                description "L2TP session limit for each group of this router";
            }

            ///nokia-conf/configure/router/l2tp/tunnel-session-limit
            leaf tunnel-session-limit {
                type types-l2tp:base-tunnel-session-limit;
                description "L2TP session limit for each tunnel of this router";
            }

            ///nokia-conf/configure/router/l2tp/session-assign-method
            leaf session-assign-method {
                type types-l2tp:base-session-assign-method;
                description "Session assignment method";
            }

            ///nokia-conf/configure/router/l2tp/next-attempt
            leaf next-attempt {
                type enumeration {
                    enum same-preference-level          { value 0; }
                    enum next-preference-level          { value 1; }
                }
                default "next-preference-level";
                description "Tunnel that is selected when previous session setup failed";
            }

            ///nokia-conf/configure/router/l2tp/apply-groups
            leaf-list apply-groups {
                type leafref {
                    path "../../../groups/group/name";
                }
                max-elements 8;
                ordered-by user;
                description "Apply a configuration group at this level";
            }

            ///nokia-conf/configure/router/l2tp/apply-groups-exclude
            leaf-list apply-groups-exclude {
                type leafref {
                    path "../../../groups/group/name";
                }
                max-elements 8;
                ordered-by user;
                description "Exclude a configuration group at this level";
            }

            ///nokia-conf/configure/router/l2tp/exclude-avps
            container exclude-avps {
                description "Enter the exclude-avps context";

                ///nokia-conf/configure/router/l2tp/exclude-avps/calling-number
                leaf calling-number {
                    type boolean;
                    default "false";
                    description "Calling Number AVP to exclude";
                }

                ///nokia-conf/configure/router/l2tp/exclude-avps/initial-rx-lcp-conf-req
                leaf initial-rx-lcp-conf-req {
                    type boolean;
                    default "false";
                    description "Exclude the Initial Received LCP CONFREQ AVP";
                }

            } // container exclude-avps

            ///nokia-conf/configure/router/l2tp/ignore-avps
            container ignore-avps {
                description "Enter the ignore-avps context";

                ///nokia-conf/configure/router/l2tp/ignore-avps/sequencing-required
                leaf sequencing-required {
                    type boolean;
                    default "false";
                    description "Ignore Sequencing Required AVP";
                }

            } // container ignore-avps

            ///nokia-conf/configure/router/l2tp/replace-result-code
            container replace-result-code {
                description "Enter the replace-result-code context";

                ///nokia-conf/configure/router/l2tp/replace-result-code/cdn-invalid-dst
                leaf cdn-invalid-dst {
                    type boolean;
                    default "false";
                    description "Replace result code with general error code";
                }

                ///nokia-conf/configure/router/l2tp/replace-result-code/cdn-permanent-no-facilities
                leaf cdn-permanent-no-facilities {
                    type boolean;
                    default "false";
                    description "Replace result code with general error";
                }

                ///nokia-conf/configure/router/l2tp/replace-result-code/cdn-temporary-no-facilities
                leaf cdn-temporary-no-facilities {
                    type boolean;
                    default "false";
                    description "Replace result code with general error";
                }

            } // container replace-result-code

            ///nokia-conf/configure/router/l2tp/lac
            container lac {
                description "Enter the lac context";

                ///nokia-conf/configure/router/l2tp/lac/df-bit
                leaf df-bit {
                    type boolean;
                    default "true";
                    description "Send all L2TP packets with DF bit set to 1";
                }

                ///nokia-conf/configure/router/l2tp/lac/calling-number-format
                leaf calling-number-format {
                    type types-sros:ascii-specification {
                        length "1..255";
                        pattern "([^%]+|%[Scrsl%])+";
                    }
                    default "%S %s";
                    description "Calling Number AVP for L2TP control messages";
                }

                ///nokia-conf/configure/router/l2tp/lac/cisco-nas-port
                container cisco-nas-port {
                    description "Enter the cisco-nas-port context";

                    ///nokia-conf/configure/router/l2tp/lac/cisco-nas-port/ethernet
                    leaf ethernet {
                        type types-sros:binary-specification {
                            pattern "([01]|(\\*[0123456789]+)?[smpoi])+";
                        }
                        description "L2TP Cisco NAS port AVP with binary patterns for Ethernet";
                    }

                } // container cisco-nas-port

            } // container lac

            ///nokia-conf/configure/router/l2tp/tunnel-selection-blacklist
            container tunnel-selection-blacklist {
                description "Enter the tunnel-selection-blacklist context";

                ///nokia-conf/configure/router/l2tp/tunnel-selection-blacklist/max-time
                leaf max-time {
                    type int32 {
                        range "1..60";
                    }
                    units "minutes";
                    default "5";
                    description "Time that a tunnel or peer can remain in the denylist";
                }

                ///nokia-conf/configure/router/l2tp/tunnel-selection-blacklist/max-list-length
                leaf max-list-length {
                    type union {
                        type int32 {
                            range "1..65535";
                        }
                        type enumeration {
                            enum infinite                       { value -1; }
                        }
                    }
                    default "infinite";
                    description "Number of tunnels or peers in the denylist";
                }

                ///nokia-conf/configure/router/l2tp/tunnel-selection-blacklist/timeout-action
                leaf timeout-action {
                    type enumeration {
                        enum remove-from-blacklist          { value 0; }
                        enum try-one-session                { value 1; }
                    }
                    default "remove-from-blacklist";
                    description "Action when a tunnel or peer exceeds time in denylist";
                }

                ///nokia-conf/configure/router/l2tp/tunnel-selection-blacklist/add-tunnel-on
                container add-tunnel-on {
                    description "Enter the add-tunnel-on context";

                    ///nokia-conf/configure/router/l2tp/tunnel-selection-blacklist/add-tunnel-on/address-change-timeout
                    leaf address-change-timeout {
                        type boolean;
                        default "false";
                        description "Enable a timed-out tunnel to be forced to the denylist";
                    }

                    ///nokia-conf/configure/router/l2tp/tunnel-selection-blacklist/add-tunnel-on/cdn-err-code
                    leaf cdn-err-code {
                        type boolean;
                        default "false";
                        description "Add to deny if CDN is received with code: General error";
                    }

                    ///nokia-conf/configure/router/l2tp/tunnel-selection-blacklist/add-tunnel-on/cdn-invalid-dst
                    leaf cdn-invalid-dst {
                        type boolean;
                        default "false";
                        description "Force tunnel to the denylist in case of Result Codes 6";
                    }

                    ///nokia-conf/configure/router/l2tp/tunnel-selection-blacklist/add-tunnel-on/cdn-permanent-no-facilities
                    leaf cdn-permanent-no-facilities {
                        type boolean;
                        default "false";
                        description "Force tunnel to the denylist in case of Result Codes 5";
                    }

                    ///nokia-conf/configure/router/l2tp/tunnel-selection-blacklist/add-tunnel-on/cdn-temporary-no-facilities
                    leaf cdn-temporary-no-facilities {
                        type boolean;
                        default "false";
                        description "Force tunnel to the denylist in case of Result Codes 4";
                    }

                    ///nokia-conf/configure/router/l2tp/tunnel-selection-blacklist/add-tunnel-on/stop-ccn-err-code
                    leaf stop-ccn-err-code {
                        type boolean;
                        default "false";
                        description "Add to denylist if received with general error code";
                    }

                    ///nokia-conf/configure/router/l2tp/tunnel-selection-blacklist/add-tunnel-on/stop-ccn-other
                    leaf stop-ccn-other {
                        type boolean;
                        default "false";
                        description "Add to denylist if StopCCN received with general error";
                    }

                    ///nokia-conf/configure/router/l2tp/tunnel-selection-blacklist/add-tunnel-on/tx-cdn-not-established-in-time
                    leaf tx-cdn-not-established-in-time {
                        type boolean;
                        default "false";
                        description "Add to denylist if CDN transmitted with result code";
                    }

                } // container add-tunnel-on

            } // container tunnel-selection-blacklist

            ///nokia-conf/configure/router/l2tp/failover
            container failover {
                description "Enter the failover context";

                ///nokia-conf/configure/router/l2tp/failover/recovery-method
                leaf recovery-method {
                    type types-l2tp:base-failover-recovery-method;
                    description "Recovery method of the sequence numbers after failover";
                }

                ///nokia-conf/configure/router/l2tp/failover/recovery-time
                leaf recovery-time {
                    type types-l2tp:base-failover-recovery-time;
                    description "Time requested from the L2TP peer before assuming failover as failed";
                }

                ///nokia-conf/configure/router/l2tp/failover/recovery-max-session-lifetime
                leaf recovery-max-session-lifetime {
                    type uint32 {
                        range "2..4294967295";
                    }
                    units "centiseconds";
                    default "2";
                    description "Subset of sessions that this system attempts to synchronize in the Session State Synchronization phase";
                }

                ///nokia-conf/configure/router/l2tp/failover/track-srrp
                list track-srrp {
                    key "id";
                    description "Enter the track-srrp list instance";

                    ///nokia-conf/configure/router/l2tp/failover/track-srrp/id
                    leaf id {
                        type leafref {
                            path "../../../../../redundancy/multi-chassis/peer/sync/track-srrp/id";
                        }
                        description "SRRP instance ID for multi-chassis redundancy failover";
                    }

                    ///nokia-conf/configure/router/l2tp/failover/track-srrp/peer
                    leaf peer {
                        type leafref {
                            path "../../../../../redundancy/multi-chassis/peer/ip-address";
                        }
                        mandatory true;
                        description "Multi-chassis peer address";
                    }

                    ///nokia-conf/configure/router/l2tp/failover/track-srrp/sync-tag
                    leaf sync-tag {
                        type types-sros:named-item;
                        mandatory true;
                        description "Synchronization tag on the multi-chassis peer";
                    }

                    ///nokia-conf/configure/router/l2tp/failover/track-srrp/apply-groups
                    leaf-list apply-groups {
                        type leafref {
                            path "../../../../../groups/group/name";
                        }
                        max-elements 8;
                        ordered-by user;
                        description "Apply a configuration group at this level";
                    }

                    ///nokia-conf/configure/router/l2tp/failover/track-srrp/apply-groups-exclude
                    leaf-list apply-groups-exclude {
                        type leafref {
                            path "../../../../../groups/group/name";
                        }
                        max-elements 8;
                        ordered-by user;
                        description "Exclude a configuration group at this level";
                    }

                } // list track-srrp

            } // container failover

            ///nokia-conf/configure/router/l2tp/l2tpv3
            container l2tpv3 {
                description "Enter the l2tpv3 context";

                ///nokia-conf/configure/router/l2tp/l2tpv3/password
                leaf password {
                    type types-sros:encrypted-leaf {
                        length "1..115";
                    }
                    description "L2TPv3 password";
                }

                ///nokia-conf/configure/router/l2tp/l2tpv3/cookie-length
                leaf cookie-length {
                    type types-l2tp:base-v3-cookie-length;
                    description "Cookie field length";
                }

                ///nokia-conf/configure/router/l2tp/l2tpv3/digest-type
                leaf digest-type {
                    type types-l2tp:base-v3-digest-type;
                    description "Hashing algorithm that calculates the message digest";
                }

                ///nokia-conf/configure/router/l2tp/l2tpv3/nonce-length
                leaf nonce-length {
                    type types-l2tp:base-v3-nonce-length;
                    description "Length of the local L2TPv3 nonce (random number)";
                }

                ///nokia-conf/configure/router/l2tp/l2tpv3/public-tcp-mss-adjust
                leaf public-tcp-mss-adjust {
                    type types-l2tp:base-v3-tcp-mss-adjust;
                    description "TCP maximum segment size (MSS) on public network";
                }

                ///nokia-conf/configure/router/l2tp/l2tpv3/private-tcp-mss-adjust
                leaf private-tcp-mss-adjust {
                    type types-l2tp:base-v3-tcp-mss-adjust;
                    description "TCP maximum segment size (MSS) on private network";
                }

                ///nokia-conf/configure/router/l2tp/l2tpv3/transport-type
                container transport-type {
                    description "Enter the transport-type context";

                    ///nokia-conf/configure/router/l2tp/l2tpv3/transport-type/ip
                    leaf ip {
                        type boolean;
                        default "false";
                        description "Use IP as the transport type for the L2TPv3 tunnel";
                    }

                } // container transport-type

            } // container l2tpv3

            ///nokia-conf/configure/router/l2tp/ethernet-tunnel
            container ethernet-tunnel {
                description "Enter the ethernet-tunnel context";

                ///nokia-conf/configure/router/l2tp/ethernet-tunnel/reconnect-timeout
                leaf reconnect-timeout {
                    type types-l2tp:base-v3-reconnect-timeout;
                    description "Timeout for a session setup retry";
                }

            } // container ethernet-tunnel

            ///nokia-conf/configure/router/l2tp/group
            list group {
                key "tunnel-group-name";
                description "Enter the group list instance";

                ///nokia-conf/configure/router/l2tp/group/tunnel-group-name
                leaf tunnel-group-name {
                    type types-sros:named-item-64 {
                        length "1..63";
                    }
                    description "Tunnel group name";
                }

                ///nokia-conf/configure/router/l2tp/group/admin-state
                leaf admin-state {
                    type types-sros:admin-state;
                    default "disable";
                    description "Administrative state of the L2TP tunnel group";
                }

                ///nokia-conf/configure/router/l2tp/group/description
                leaf description {
                    type types-sros:description;
                    description "Text description";
                }

                ///nokia-conf/configure/router/l2tp/group/protocol
                leaf protocol {
                    type types-l2tp:protocol-version;
                    sros-ext:immutable;
                    description "Protocol version";
                }

                ///nokia-conf/configure/router/l2tp/group/local-address
                leaf local-address {
                    type types-sros:ipv4-unicast-address;
                    description "Local address";
                }

                ///nokia-conf/configure/router/l2tp/group/receive-window-size
                leaf receive-window-size {
                    type types-l2tp:child-receive-window-size;
                    description "L2TP receive window size";
                }

                ///nokia-conf/configure/router/l2tp/group/hello-interval
                leaf hello-interval {
                    type types-l2tp:child-hello-interval;
                    description "Hello interval";
                }

                ///nokia-conf/configure/router/l2tp/group/idle-timeout
                leaf idle-timeout {
                    type types-l2tp:child-idle-timeout;
                    description "Idle timeout";
                }

                ///nokia-conf/configure/router/l2tp/group/destruct-timeout
                leaf destruct-timeout {
                    type types-l2tp:child-destruct-timeout;
                    description "Destruction timeout";
                }

                ///nokia-conf/configure/router/l2tp/group/max-retries-estab
                leaf max-retries-estab {
                    type types-l2tp:child-max-retries;
                    description "Maximum retries for established tunnels";
                }

                ///nokia-conf/configure/router/l2tp/group/max-retries-not-estab
                leaf max-retries-not-estab {
                    type types-l2tp:child-max-retries;
                    description "Maximum retries for unestablished tunnels";
                }

                ///nokia-conf/configure/router/l2tp/group/radius-accounting-policy
                leaf radius-accounting-policy {
                    type leafref {
                        path "../../../../aaa/radius/l2tp-accounting-policy/name";
                    }
                    description "RADIUS accounting policy";
                }

                ///nokia-conf/configure/router/l2tp/group/local-name
                leaf local-name {
                    type types-l2tp:host-name;
                    description "Local host name used to distinguish tunnels";
                }

                ///nokia-conf/configure/router/l2tp/group/password
                leaf password {
                    type types-sros:encrypted-leaf {
                        length "1..115";
                    }
                    description "Password between L2TP LAC and LNS";
                }

                ///nokia-conf/configure/router/l2tp/group/challenge
                leaf challenge {
                    type types-sros:bool-with-inherit;
                    description "Enable use of challenge-response authentication";
                }

                ///nokia-conf/configure/router/l2tp/group/avp-hiding
                leaf avp-hiding {
                    type types-l2tp:child-avp-hiding;
                    description "The AVP hiding algorithm";
                }

                ///nokia-conf/configure/router/l2tp/group/session-limit
                leaf session-limit {
                    type types-l2tp:child-session-limit;
                    description "Session limit";
                }

                ///nokia-conf/configure/router/l2tp/group/session-assign-method
                leaf session-assign-method {
                    type types-l2tp:child-session-assign-method;
                    description "Session assignment method";
                }

                ///nokia-conf/configure/router/l2tp/group/apply-groups
                leaf-list apply-groups {
                    type leafref {
                        path "../../../../groups/group/name";
                    }
                    max-elements 8;
                    ordered-by user;
                    description "Apply a configuration group at this level";
                }

                ///nokia-conf/configure/router/l2tp/group/apply-groups-exclude
                leaf-list apply-groups-exclude {
                    type leafref {
                        path "../../../../groups/group/name";
                    }
                    max-elements 8;
                    ordered-by user;
                    description "Exclude a configuration group at this level";
                }

                ///nokia-conf/configure/router/l2tp/group/failover
                container failover {
                    when "../protocol = 'v2'" {
                        description "Protocol must be v2 to access this container";
                    }
                    description "Enter the failover context";

                    ///nokia-conf/configure/router/l2tp/group/failover/recovery-method
                    leaf recovery-method {
                        type types-l2tp:child-failover-recovery-method;
                        description "Recovery method of the sequence numbers after failover";
                    }

                    ///nokia-conf/configure/router/l2tp/group/failover/recovery-time
                    leaf recovery-time {
                        type types-l2tp:child-failover-recovery-time;
                        description "Time requested from the L2TP peer before assuming failover as failed";
                    }

                } // container failover

                ///nokia-conf/configure/router/l2tp/group/lac
                container lac {
                    when "../protocol = 'v2'" {
                        description "Protocol must be v2 to access this container";
                    }
                    description "Enter the lac context";

                    ///nokia-conf/configure/router/l2tp/group/lac/df-bit
                    leaf df-bit {
                        type types-sros:bool-with-inherit;
                        description "DF (do not fragment) bit in data traffic transmitted as LAC";
                    }

                } // container lac

                ///nokia-conf/configure/router/l2tp/group/l2tpv3
                container l2tpv3 {
                    when "not(../protocol = 'v2')" {
                        description "Protocol must be v3 or v3draft to access this container";
                    }
                    description "Enter the l2tpv3 context";

                    ///nokia-conf/configure/router/l2tp/group/l2tpv3/rem-router-id
                    leaf rem-router-id {
                        type types-sros:ipv4-address;
                        default "0.0.0.0";
                        description "Filter on remote router ID";
                    }

                    ///nokia-conf/configure/router/l2tp/group/l2tpv3/password
                    leaf password {
                        type types-sros:encrypted-leaf {
                            length "1..115";
                        }
                        description "L2TPv3 password";
                    }

                    ///nokia-conf/configure/router/l2tp/group/l2tpv3/track-password-change
                    leaf track-password-change {
                        type boolean;
                        default "false";
                        description "Enable tracking of password changes";
                    }

                    ///nokia-conf/configure/router/l2tp/group/l2tpv3/cookie-length
                    leaf cookie-length {
                        type types-l2tp:child-v3-cookie-length;
                        description "Cookie field length";
                    }

                    ///nokia-conf/configure/router/l2tp/group/l2tpv3/digest-type
                    leaf digest-type {
                        type types-l2tp:child-v3-digest-type;
                        description "Hashing algorithm that calculates the message digest";
                    }

                    ///nokia-conf/configure/router/l2tp/group/l2tpv3/nonce-length
                    leaf nonce-length {
                        type types-l2tp:child-v3-nonce-length;
                        description "Length for the local L2TPv3 nonce (random number)";
                    }

                    ///nokia-conf/configure/router/l2tp/group/l2tpv3/public-tcp-mss-adjust
                    leaf public-tcp-mss-adjust {
                        type types-l2tp:child-v3-tcp-mss-adjust;
                        description "TCP Maximum Segment Size (MSS) on public network";
                    }

                    ///nokia-conf/configure/router/l2tp/group/l2tpv3/private-tcp-mss-adjust
                    leaf private-tcp-mss-adjust {
                        type types-l2tp:child-v3-tcp-mss-adjust;
                        description "TCP maximum segment size (MSS) on private network";
                    }

                    ///nokia-conf/configure/router/l2tp/group/l2tpv3/pw-cap-list
                    container pw-cap-list {
                        description "Enter the pw-cap-list context";

                        ///nokia-conf/configure/router/l2tp/group/l2tpv3/pw-cap-list/ethernet
                        leaf ethernet {
                            type boolean;
                            sros-ext:auto-restart-to-modify;
                            default "false";
                            description "Advertise Ethernet pseudowire type";
                        }

                        ///nokia-conf/configure/router/l2tp/group/l2tpv3/pw-cap-list/ethernet-vlan
                        leaf ethernet-vlan {
                            type boolean;
                            sros-ext:auto-restart-to-modify;
                            default "false";
                            description "Advertise Ethernet VLAN pseudowire type";
                        }

                    } // container pw-cap-list

                } // container l2tpv3

                ///nokia-conf/configure/router/l2tp/group/ethernet-tunnel
                container ethernet-tunnel {
                    when "not(../protocol = 'v2')" {
                        description "Protocol must be v3 or v3draft to access this container";
                    }
                    description "Enter the ethernet-tunnel context";

                    ///nokia-conf/configure/router/l2tp/group/ethernet-tunnel/reconnect-timeout
                    leaf reconnect-timeout {
                        type types-l2tp:child-v3-reconnect-timeout;
                        description "Timeout for a session setup retry at group level";
                    }

                } // container ethernet-tunnel

                ///nokia-conf/configure/router/l2tp/group/lns
                container lns {
                    when "../protocol = 'v2'" {
                        description "Protocol must be v2 to access this container";
                    }
                    description "Enter the lns context";

                    ///nokia-conf/configure/router/l2tp/group/lns/load-balance-method
                    leaf load-balance-method {
                        type types-l2tp:base-load-balance-method;
                        default "per-session";
                        description "New sessions for L2TP ISA MDA";
                    }

                    ///nokia-conf/configure/router/l2tp/group/lns/lns-group
                    leaf lns-group {
                        type leafref {
                            path "../../../../../isa/lns-group/id";
                        }
                        description "ISA LNS group";
                    }

                    ///nokia-conf/configure/router/l2tp/group/lns/ppp
                    container ppp {
                        description "Enter the ppp context";

                        ///nokia-conf/configure/router/l2tp/group/lns/ppp/authentication-policy
                        leaf authentication-policy {
                            type types-sros:named-item;
                            description "Authentication policy when a DHCP message is received";
                        }

                        ///nokia-conf/configure/router/l2tp/group/lns/ppp/user-db
                        leaf user-db {
                            type types-sros:named-item;
                            description "Local user database for PPP PAP and CHAP authentication";
                        }

                        ///nokia-conf/configure/router/l2tp/group/lns/ppp/proxy-lcp
                        leaf proxy-lcp {
                            type boolean;
                            default "false";
                            description "Proxy LCP AVPs that are received from LAC";
                        }

                        ///nokia-conf/configure/router/l2tp/group/lns/ppp/lcp-ignore-magic-numbers
                        leaf lcp-ignore-magic-numbers {
                            type boolean;
                            default "false";
                            description "Check magic number in echo request and reply messages";
                        }

                        ///nokia-conf/configure/router/l2tp/group/lns/ppp/lcp-force-ack-accm
                        leaf lcp-force-ack-accm {
                            type boolean;
                            default "false";
                            description "Force acknowledgement of the LCP Asynchronous Control Character Map (ACCM) option";
                        }

                        ///nokia-conf/configure/router/l2tp/group/lns/ppp/reject-disabled-ncp
                        leaf reject-disabled-ncp {
                            type boolean;
                            default "false";
                            description "Force LCP Protocol Reject for IPv6CP Configure Request";
                        }

                        ///nokia-conf/configure/router/l2tp/group/lns/ppp/mtu
                        leaf mtu {
                            type types-l2tp:base-ppp-mtu;
                            default "1500";
                            description "Maximum PPP MTU size";
                        }

                        ///nokia-conf/configure/router/l2tp/group/lns/ppp/proxy-authentication
                        leaf proxy-authentication {
                            type boolean;
                            default "false";
                            description "Use authentication AVPs that are received from LAC";
                        }

                        ///nokia-conf/configure/router/l2tp/group/lns/ppp/authentication
                        leaf authentication {
                            type types-l2tp:base-ppp-auth-protocol;
                            default "pref-chap";
                            description "PPP authentication protocol to negotiate";
                        }

                        ///nokia-conf/configure/router/l2tp/group/lns/ppp/ipcp-subnet-negotiation
                        leaf ipcp-subnet-negotiation {
                            type boolean;
                            default "false";
                            description "Allow IPCP subnet negotiation for PPPoE hosts";
                        }

                        ///nokia-conf/configure/router/l2tp/group/lns/ppp/default-group-interface
                        container default-group-interface {
                            description "Enter the default-group-interface context";

                            ///nokia-conf/configure/router/l2tp/group/lns/ppp/default-group-interface/interface
                            leaf interface {
                                type types-sros:named-item;
                                description "Group interface";
                            }

                            ///nokia-conf/configure/router/l2tp/group/lns/ppp/default-group-interface/service-name
                            leaf service-name {
                                type types-services:service-name;
                                description "Administrative service name";
                            }

                        } // container default-group-interface

                        ///nokia-conf/configure/router/l2tp/group/lns/ppp/keepalive
                        container keepalive {
                            description "Enter the keepalive context";

                            ///nokia-conf/configure/router/l2tp/group/lns/ppp/keepalive/interval
                            leaf interval {
                                type types-l2tp:base-lcp-keepalive-interval;
                                default "30";
                                description "PPP keepalive interval";
                            }

                            ///nokia-conf/configure/router/l2tp/group/lns/ppp/keepalive/multiplier
                            leaf multiplier {
                                type types-l2tp:base-lcp-keepalive-multiplier;
                                default "3";
                                description "PPP keepalive multiplier";
                            }

                        } // container keepalive

                        ///nokia-conf/configure/router/l2tp/group/lns/ppp/chap-challenge-length
                        container chap-challenge-length {
                            description "Enter the chap-challenge-length context";

                            ///nokia-conf/configure/router/l2tp/group/lns/ppp/chap-challenge-length/start
                            leaf start {
                                type types-l2tp:base-chap-challenge-length;
                                default "32";
                                description "Lower bound of the PPP CHAP challenge length";
                            }

                            ///nokia-conf/configure/router/l2tp/group/lns/ppp/chap-challenge-length/end
                            leaf end {
                                type types-l2tp:base-chap-challenge-length;
                                default "64";
                                description "Upper bound of the PPP CHAP challenge length";
                            }

                        } // container chap-challenge-length

                    } // container ppp

                    ///nokia-conf/configure/router/l2tp/group/lns/mlppp
                    container mlppp {
                        description "Enter the mlppp context";

                        ///nokia-conf/configure/router/l2tp/group/lns/mlppp/admin-state
                        leaf admin-state {
                            type types-sros:admin-state;
                            default "disable";
                            description "Administrative state of MLPPP in the L2TP tunnel group";
                        }

                        ///nokia-conf/configure/router/l2tp/group/lns/mlppp/max-links
                        leaf max-links {
                            type types-l2tp:base-mlppp-max-links;
                            default "1";
                            description "Maximum MLPPP links";
                        }

                        ///nokia-conf/configure/router/l2tp/group/lns/mlppp/interleave
                        leaf interleave {
                            type boolean;
                            default "false";
                            description "Enable link fragmentation and interleaving";
                        }

                        ///nokia-conf/configure/router/l2tp/group/lns/mlppp/max-fragment-delay
                        leaf max-fragment-delay {
                            type types-l2tp:base-mlppp-max-frag-delay;
                            default "no-fragmentation";
                            description "Maximum fragment delay caused by transmission on a link";
                        }

                        ///nokia-conf/configure/router/l2tp/group/lns/mlppp/reassembly-timeout
                        leaf reassembly-timeout {
                            type types-l2tp:base-mlppp-reassembly-timeout;
                            default "1000";
                            description "Reassembly timeout";
                        }

                        ///nokia-conf/configure/router/l2tp/group/lns/mlppp/short-sequence-numbers
                        leaf short-sequence-numbers {
                            type boolean;
                            default "false";
                            description "Request a peer to send short sequence numbers";
                        }

                        ///nokia-conf/configure/router/l2tp/group/lns/mlppp/apply-groups
                        leaf-list apply-groups {
                            type leafref {
                                path "../../../../../../groups/group/name";
                            }
                            max-elements 8;
                            ordered-by user;
                            description "Apply a configuration group at this level";
                        }

                        ///nokia-conf/configure/router/l2tp/group/lns/mlppp/apply-groups-exclude
                        leaf-list apply-groups-exclude {
                            type leafref {
                                path "../../../../../../groups/group/name";
                            }
                            max-elements 8;
                            ordered-by user;
                            description "Exclude a configuration group at this level";
                        }

                        ///nokia-conf/configure/router/l2tp/group/lns/mlppp/endpoint
                        container endpoint {
                            description "Enter the endpoint context";

                            ///nokia-conf/configure/router/l2tp/group/lns/mlppp/endpoint/endpoint
                            choice endpoint {
                                ///nokia-conf/configure/router/l2tp/group/lns/mlppp/endpoint/endpoint/ip
                                case ip {

                                    ///nokia-conf/configure/router/l2tp/group/lns/mlppp/endpoint/endpoint/ip/ip
                                    leaf ip {
                                        type types-ppp:mlppp-ip-endpoint;
                                        description "Endpoint ID as an IP address";
                                    }

                                }
                                ///nokia-conf/configure/router/l2tp/group/lns/mlppp/endpoint/endpoint/mac
                                case mac {

                                    ///nokia-conf/configure/router/l2tp/group/lns/mlppp/endpoint/endpoint/mac/mac
                                    leaf mac {
                                        type types-ppp:mlppp-mac-endpoint;
                                        description "Endpoint ID as a MAC address";
                                    }

                                }
                            }
                        } // container endpoint

                    } // container mlppp

                } // container lns

                ///nokia-conf/configure/router/l2tp/group/tunnel
                list tunnel {
                    key "tunnel-name";
                    max-elements 31;
                    description "Enter the tunnel list instance";

                    ///nokia-conf/configure/router/l2tp/group/tunnel/tunnel-name
                    leaf tunnel-name {
                        type types-sros:named-item {
                            length "1..32";
                        }
                        description "Tunnel name";
                    }

                    ///nokia-conf/configure/router/l2tp/group/tunnel/admin-state
                    leaf admin-state {
                        type types-sros:admin-state;
                        default "disable";
                        description "Administrative state of the L2TP tunnel";
                    }

                    ///nokia-conf/configure/router/l2tp/group/tunnel/description
                    leaf description {
                        type types-sros:description;
                        description "Text description";
                    }

                    ///nokia-conf/configure/router/l2tp/group/tunnel/preference
                    leaf preference {
                        type uint32 {
                            range "0..16777215";
                        }
                        default "50";
                        description "Tunnel preference number with its group";
                    }

                    ///nokia-conf/configure/router/l2tp/group/tunnel/auto-establish
                    leaf auto-establish {
                        type boolean;
                        default "false";
                        description "Allow the tunnel to be automatically set up by the system";
                    }

                    ///nokia-conf/configure/router/l2tp/group/tunnel/peer
                    leaf peer {
                        type types-sros:ipv4-unicast-address;
                        description "Peer address";
                    }

                    ///nokia-conf/configure/router/l2tp/group/tunnel/local-address
                    leaf local-address {
                        type types-sros:ipv4-unicast-address;
                        description "Local address";
                    }

                    ///nokia-conf/configure/router/l2tp/group/tunnel/receive-window-size
                    leaf receive-window-size {
                        type types-l2tp:child-receive-window-size;
                        description "L2TP receive window size";
                    }

                    ///nokia-conf/configure/router/l2tp/group/tunnel/hello-interval
                    leaf hello-interval {
                        type types-l2tp:child-hello-interval;
                        description "Hello interval";
                    }

                    ///nokia-conf/configure/router/l2tp/group/tunnel/idle-timeout
                    leaf idle-timeout {
                        type types-l2tp:child-idle-timeout;
                        description "Idle timeout";
                    }

                    ///nokia-conf/configure/router/l2tp/group/tunnel/destruct-timeout
                    leaf destruct-timeout {
                        type types-l2tp:child-destruct-timeout;
                        description "Destruction timeout";
                    }

                    ///nokia-conf/configure/router/l2tp/group/tunnel/max-retries-estab
                    leaf max-retries-estab {
                        type types-l2tp:child-max-retries;
                        description "Maximum retries for established tunnels";
                    }

                    ///nokia-conf/configure/router/l2tp/group/tunnel/max-retries-not-estab
                    leaf max-retries-not-estab {
                        type types-l2tp:child-max-retries;
                        description "Maximum retries for unestablished tunnels";
                    }

                    ///nokia-conf/configure/router/l2tp/group/tunnel/radius-accounting-policy
                    leaf radius-accounting-policy {
                        type leafref {
                            path "../../../../../aaa/radius/l2tp-accounting-policy/name";
                        }
                        description "RADIUS accounting policy";
                    }

                    ///nokia-conf/configure/router/l2tp/group/tunnel/remote-name
                    leaf remote-name {
                        type types-l2tp:host-name;
                        description "Remote tunnel host name";
                    }

                    ///nokia-conf/configure/router/l2tp/group/tunnel/local-name
                    leaf local-name {
                        type types-l2tp:host-name;
                        description "Local host name used to distinguish tunnels";
                    }

                    ///nokia-conf/configure/router/l2tp/group/tunnel/password
                    leaf password {
                        type types-sros:encrypted-leaf {
                            length "1..115";
                        }
                        description "Password between L2TP LAC and LNS";
                    }

                    ///nokia-conf/configure/router/l2tp/group/tunnel/challenge
                    leaf challenge {
                        type types-sros:bool-with-inherit;
                        description "Enable use of challenge-response authentication";
                    }

                    ///nokia-conf/configure/router/l2tp/group/tunnel/avp-hiding
                    leaf avp-hiding {
                        type types-l2tp:child-avp-hiding;
                        description "The AVP hiding algorithm";
                    }

                    ///nokia-conf/configure/router/l2tp/group/tunnel/session-limit
                    leaf session-limit {
                        type types-l2tp:child-tunnel-session-limit;
                        description "L2TP session limit for each tunnel of this router";
                    }

                    ///nokia-conf/configure/router/l2tp/group/tunnel/apply-groups
                    leaf-list apply-groups {
                        type leafref {
                            path "../../../../../groups/group/name";
                        }
                        max-elements 8;
                        ordered-by user;
                        description "Apply a configuration group at this level";
                    }

                    ///nokia-conf/configure/router/l2tp/group/tunnel/apply-groups-exclude
                    leaf-list apply-groups-exclude {
                        type leafref {
                            path "../../../../../groups/group/name";
                        }
                        max-elements 8;
                        ordered-by user;
                        description "Exclude a configuration group at this level";
                    }

                    ///nokia-conf/configure/router/l2tp/group/tunnel/failover
                    container failover {
                        when "../../protocol = 'v2'" {
                            description "Protocol must be v2 to access this container";
                        }
                        description "Enter the failover context";

                        ///nokia-conf/configure/router/l2tp/group/tunnel/failover/recovery-method
                        leaf recovery-method {
                            type types-l2tp:child-failover-recovery-method;
                            description "Recovery method of the sequence numbers after failover";
                        }

                        ///nokia-conf/configure/router/l2tp/group/tunnel/failover/recovery-time
                        leaf recovery-time {
                            type types-l2tp:child-failover-recovery-time;
                            description "Time requested from the L2TP peer before assuming failover as failed";
                        }

                    } // container failover

                    ///nokia-conf/configure/router/l2tp/group/tunnel/lac
                    container lac {
                        when "../../protocol = 'v2'" {
                            description "Protocol must be v2 to access this container";
                        }
                        description "Enter the lac context";

                        ///nokia-conf/configure/router/l2tp/group/tunnel/lac/df-bit
                        leaf df-bit {
                            type types-sros:bool-with-inherit;
                            description "DF (do not fragment) bit in data traffic transmitted as LAC";
                        }

                    } // container lac

                    ///nokia-conf/configure/router/l2tp/group/tunnel/l2tpv3
                    container l2tpv3 {
                        when "not(../../protocol = 'v2')" {
                            description "Protocol must be v3 or v3draft to access this container";
                        }
                        description "Enter the l2tpv3 context";

                        ///nokia-conf/configure/router/l2tp/group/tunnel/l2tpv3/public-tcp-mss-adjust
                        leaf public-tcp-mss-adjust {
                            type types-l2tp:child-v3-tcp-mss-adjust;
                            description "TCP maximum segment size (MSS) on public network";
                        }

                        ///nokia-conf/configure/router/l2tp/group/tunnel/l2tpv3/private-tcp-mss-adjust
                        leaf private-tcp-mss-adjust {
                            type types-l2tp:child-v3-tcp-mss-adjust;
                            description "TCP maximum segment size (MSS) on private network";
                        }

                    } // container l2tpv3

                    ///nokia-conf/configure/router/l2tp/group/tunnel/lns
                    container lns {
                        when "../../protocol = 'v2'" {
                            description "Protocol must be v2 to access this container";
                        }
                        description "Enter the lns context";

                        ///nokia-conf/configure/router/l2tp/group/tunnel/lns/load-balance-method
                        leaf load-balance-method {
                            type types-l2tp:child-load-balance-method;
                            description "New sessions for L2TP ISA MDA";
                        }

                        ///nokia-conf/configure/router/l2tp/group/tunnel/lns/lns-group
                        leaf lns-group {
                            type leafref {
                                path "../../../../../../isa/lns-group/id";
                            }
                            description "ISA LNS group";
                        }

                        ///nokia-conf/configure/router/l2tp/group/tunnel/lns/ppp
                        container ppp {
                            description "Enter the ppp context";

                            ///nokia-conf/configure/router/l2tp/group/tunnel/lns/ppp/authentication-policy
                            leaf authentication-policy {
                                type types-sros:named-item;
                                description "Authentication policy when a DHCP message is received";
                            }

                            ///nokia-conf/configure/router/l2tp/group/tunnel/lns/ppp/user-db
                            leaf user-db {
                                type types-sros:named-item;
                                description "Local user database for PPP PAP and CHAP authentication";
                            }

                            ///nokia-conf/configure/router/l2tp/group/tunnel/lns/ppp/proxy-lcp
                            leaf proxy-lcp {
                                type types-sros:bool-with-inherit;
                                description "Use the Proxy LCP AVPs that are received from the LAC";
                            }

                            ///nokia-conf/configure/router/l2tp/group/tunnel/lns/ppp/lcp-ignore-magic-numbers
                            leaf lcp-ignore-magic-numbers {
                                type types-sros:bool-with-inherit;
                                description "Magic-Number field in LCP Echo-Request and LCP Echo-Reply messages that are checked";
                            }

                            ///nokia-conf/configure/router/l2tp/group/tunnel/lns/ppp/lcp-force-ack-accm
                            leaf lcp-force-ack-accm {
                                type types-sros:bool-with-inherit;
                                description "Forced acknowledgement of the LCP Asynchronous Control Character Map (ACCM) option";
                            }

                            ///nokia-conf/configure/router/l2tp/group/tunnel/lns/ppp/reject-disabled-ncp
                            leaf reject-disabled-ncp {
                                type types-sros:bool-with-inherit;
                                description "Force LCP Project Reject for IPv6CP Configure Request";
                            }

                            ///nokia-conf/configure/router/l2tp/group/tunnel/lns/ppp/mtu
                            leaf mtu {
                                type types-l2tp:child-ppp-mtu;
                                description "Maximum PPP MTU size";
                            }

                            ///nokia-conf/configure/router/l2tp/group/tunnel/lns/ppp/proxy-authentication
                            leaf proxy-authentication {
                                type types-sros:bool-with-inherit;
                                description "Authentication AVPs that are received from LAC";
                            }

                            ///nokia-conf/configure/router/l2tp/group/tunnel/lns/ppp/authentication
                            leaf authentication {
                                type types-l2tp:child-ppp-auth-protocol;
                                description "PPP authentication protocol to negotiate";
                            }

                            ///nokia-conf/configure/router/l2tp/group/tunnel/lns/ppp/ipcp-subnet-negotiation
                            leaf ipcp-subnet-negotiation {
                                type types-sros:bool-with-inherit;
                                description "Use of IPCP subnet negotiation for PPPoE hosts";
                            }

                            ///nokia-conf/configure/router/l2tp/group/tunnel/lns/ppp/default-group-interface
                            container default-group-interface {
                                description "Enter the default-group-interface context";

                                ///nokia-conf/configure/router/l2tp/group/tunnel/lns/ppp/default-group-interface/interface
                                leaf interface {
                                    type types-sros:named-item;
                                    description "Group interface";
                                }

                                ///nokia-conf/configure/router/l2tp/group/tunnel/lns/ppp/default-group-interface/service-name
                                leaf service-name {
                                    type types-services:service-name;
                                    description "Administrative service name";
                                }

                            } // container default-group-interface

                            ///nokia-conf/configure/router/l2tp/group/tunnel/lns/ppp/keepalive
                            container keepalive {
                                description "Enter the keepalive context";

                                ///nokia-conf/configure/router/l2tp/group/tunnel/lns/ppp/keepalive/interval
                                leaf interval {
                                    type types-l2tp:child-lcp-keepalive-interval;
                                    description "PPP keepalive interval";
                                }

                                ///nokia-conf/configure/router/l2tp/group/tunnel/lns/ppp/keepalive/multiplier
                                leaf multiplier {
                                    type types-l2tp:child-lcp-keepalive-multiplier;
                                    description "PPP keepalive multiplier";
                                }

                            } // container keepalive

                            ///nokia-conf/configure/router/l2tp/group/tunnel/lns/ppp/chap-challenge-length
                            container chap-challenge-length {
                                description "Enter the chap-challenge-length context";

                                ///nokia-conf/configure/router/l2tp/group/tunnel/lns/ppp/chap-challenge-length/start
                                leaf start {
                                    type types-l2tp:child-chap-challenge-length;
                                    description "Lower bound of the PPP CHAP challenge length";
                                }

                                ///nokia-conf/configure/router/l2tp/group/tunnel/lns/ppp/chap-challenge-length/end
                                leaf end {
                                    type types-l2tp:child-chap-challenge-length;
                                    description "Upper bound of the PPP CHAP challenge length";
                                }

                            } // container chap-challenge-length

                        } // container ppp

                        ///nokia-conf/configure/router/l2tp/group/tunnel/lns/mlppp
                        container mlppp {
                            description "Enter the mlppp context";

                            ///nokia-conf/configure/router/l2tp/group/tunnel/lns/mlppp/admin-state
                            leaf admin-state {
                                type types-sros:admin-state-with-inherit;
                                description "Administrative state of MLPPP in the L2TP tunnel";
                            }

                            ///nokia-conf/configure/router/l2tp/group/tunnel/lns/mlppp/max-links
                            leaf max-links {
                                type types-l2tp:child-mlppp-max-links;
                                description "Maximum MLPPP links";
                            }

                            ///nokia-conf/configure/router/l2tp/group/tunnel/lns/mlppp/interleave
                            leaf interleave {
                                type types-sros:bool-with-inherit;
                                description "Use of Link fragmentation and interleaving";
                            }

                            ///nokia-conf/configure/router/l2tp/group/tunnel/lns/mlppp/max-fragment-delay
                            leaf max-fragment-delay {
                                type types-l2tp:child-mlppp-max-frag-delay;
                                description "Maximum fragment delay caused by transmission on a link";
                            }

                            ///nokia-conf/configure/router/l2tp/group/tunnel/lns/mlppp/reassembly-timeout
                            leaf reassembly-timeout {
                                type types-l2tp:child-mlppp-reassembly-timeout;
                                description "Reassembly timeout";
                            }

                            ///nokia-conf/configure/router/l2tp/group/tunnel/lns/mlppp/short-sequence-numbers
                            leaf short-sequence-numbers {
                                type types-sros:bool-with-inherit;
                                description "Request a peer to send short sequence numbers";
                            }

                            ///nokia-conf/configure/router/l2tp/group/tunnel/lns/mlppp/apply-groups
                            leaf-list apply-groups {
                                type leafref {
                                    path "../../../../../../../groups/group/name";
                                }
                                max-elements 8;
                                ordered-by user;
                                description "Apply a configuration group at this level";
                            }

                            ///nokia-conf/configure/router/l2tp/group/tunnel/lns/mlppp/apply-groups-exclude
                            leaf-list apply-groups-exclude {
                                type leafref {
                                    path "../../../../../../../groups/group/name";
                                }
                                max-elements 8;
                                ordered-by user;
                                description "Exclude a configuration group at this level";
                            }

                            ///nokia-conf/configure/router/l2tp/group/tunnel/lns/mlppp/endpoint
                            container endpoint {
                                description "Enter the endpoint context";

                                ///nokia-conf/configure/router/l2tp/group/tunnel/lns/mlppp/endpoint/endpoint
                                choice endpoint {
                                    ///nokia-conf/configure/router/l2tp/group/tunnel/lns/mlppp/endpoint/endpoint/ip
                                    case ip {

                                        ///nokia-conf/configure/router/l2tp/group/tunnel/lns/mlppp/endpoint/endpoint/ip/ip
                                        leaf ip {
                                            type types-ppp:mlppp-ip-endpoint;
                                            description "Endpoint ID as an IP address";
                                        }

                                    }
                                    ///nokia-conf/configure/router/l2tp/group/tunnel/lns/mlppp/endpoint/endpoint/mac
                                    case mac {

                                        ///nokia-conf/configure/router/l2tp/group/tunnel/lns/mlppp/endpoint/endpoint/mac/mac
                                        leaf mac {
                                            type types-ppp:mlppp-mac-endpoint;
                                            description "Endpoint ID as a MAC address";
                                        }

                                    }
                                }
                            } // container endpoint

                        } // container mlppp

                    } // container lns

                } // list tunnel

            } // list group

        } // container l2tp

    } // grouping conf-router-l2tp

}
