submodule nokia-conf-router-twamp-light {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure  OAM Performance Monitoring TWAMP-Light (Two-Way Active Measurement Protocol, Light) on SR OS based routers.

         Copyright 2016 Nokia. All rights reserved. Reproduction of this document
         is authorized on the condition that the foregoing copyright notice is included.

         This nokia-conf-router-twamp-light YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping conf-router-twamp-light {
        ///nokia-conf/configure/router/twamp-light
        container twamp-light {
            when "../router-name = 'Base'" {
                description "router-name must be 'Base'";
            }
            description "Enter the twamp-light context";

            ///nokia-conf/configure/router/twamp-light/apply-groups
            leaf-list apply-groups {
                type leafref {
                    path "../../../groups/group/name";
                }
                max-elements 8;
                ordered-by user;
                description "Apply a configuration group at this level";
            }

            ///nokia-conf/configure/router/twamp-light/apply-groups-exclude
            leaf-list apply-groups-exclude {
                type leafref {
                    path "../../../groups/group/name";
                }
                max-elements 8;
                ordered-by user;
                description "Exclude a configuration group at this level";
            }

            ///nokia-conf/configure/router/twamp-light/reflector
            container reflector {
                presence "Enable the reflector context";
                description "Enable the reflector context";

                ///nokia-conf/configure/router/twamp-light/reflector/admin-state
                leaf admin-state {
                    type types-sros:admin-state;
                    default "disable";
                    description "Administrative state of TWAMP Light functionality";
                }

                ///nokia-conf/configure/router/twamp-light/reflector/description
                leaf description {
                    type types-sros:description;
                    description "Text description";
                }

                ///nokia-conf/configure/router/twamp-light/reflector/udp-port
                leaf udp-port {
                    type types-sros:tcp-udp-port-non-zero {
                        range "862|64364..64373";
                    }
                    sros-ext:auto-restart-to-modify;
                    mandatory true;
                    description "UDP port on which the specified TWAMP-Light reflector listens for TWAMP PDUs";
                }

                ///nokia-conf/configure/router/twamp-light/reflector/allow-ipv6-udp-checksum-zero
                leaf allow-ipv6-udp-checksum-zero {
                    type boolean;
                    sros-ext:auto-restart-to-modify;
                    default "false";
                    description "Process IPv6 packets with a zero UDP checksum";
                }

                ///nokia-conf/configure/router/twamp-light/reflector/type
                leaf type {
                    type enumeration {
                        enum stamp                          { value 1; }
                        enum twamp-light                    { value 2; }
                    }
                    default "twamp-light";
                    description "Processing behavior type for the reflector";
                }

                ///nokia-conf/configure/router/twamp-light/reflector/apply-groups
                leaf-list apply-groups {
                    type leafref {
                        path "../../../../groups/group/name";
                    }
                    max-elements 8;
                    ordered-by user;
                    description "Apply a configuration group at this level";
                }

                ///nokia-conf/configure/router/twamp-light/reflector/apply-groups-exclude
                leaf-list apply-groups-exclude {
                    type leafref {
                        path "../../../../groups/group/name";
                    }
                    max-elements 8;
                    ordered-by user;
                    description "Exclude a configuration group at this level";
                }

                ///nokia-conf/configure/router/twamp-light/reflector/prefix
                list prefix {
                    key "ip-prefix";
                    max-elements 50;
                    description "Enter the prefix list instance";

                    ///nokia-conf/configure/router/twamp-light/reflector/prefix/ip-prefix
                    leaf ip-prefix {
                        type types-sros:ip-prefix;
                        description "Source prefix for the TWAMP-Light reflector";
                    }

                    ///nokia-conf/configure/router/twamp-light/reflector/prefix/description
                    leaf description {
                        type types-sros:description;
                        description "Text description";
                    }

                    ///nokia-conf/configure/router/twamp-light/reflector/prefix/apply-groups
                    leaf-list apply-groups {
                        type leafref {
                            path "../../../../../groups/group/name";
                        }
                        max-elements 8;
                        ordered-by user;
                        description "Apply a configuration group at this level";
                    }

                    ///nokia-conf/configure/router/twamp-light/reflector/prefix/apply-groups-exclude
                    leaf-list apply-groups-exclude {
                        type leafref {
                            path "../../../../../groups/group/name";
                        }
                        max-elements 8;
                        ordered-by user;
                        description "Exclude a configuration group at this level";
                    }

                } // list prefix

            } // container reflector

        } // container twamp-light

    } // grouping conf-router-twamp-light

}
