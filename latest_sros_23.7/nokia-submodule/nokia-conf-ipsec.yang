submodule nokia-conf-ipsec {

    yang-version "1.1";

    belongs-to nokia-conf { prefix "conf"; }

    import nokia-sros-yang-extensions     { prefix "sros-ext"; }
    import nokia-types-ipsec              { prefix "types-ipsec"; }
    import nokia-types-security           { prefix "types-security"; }
    import nokia-types-services           { prefix "types-services"; }
    import nokia-types-sros               { prefix "types-sros"; }

    include nokia-conf-aaa;
    include nokia-conf-groups;
    include nokia-conf-system;
    include nokia-conf-system-security;
    include nokia-conf-system-security-pki;

    sros-ext:sros-major-release "rel23";
    organization "Nokia";
    contact
        "Nokia SR OS Support
         Web: <http://www.nokia.com>";
    description
        "Nokia YANG Data model to configure IPsec configuration on SR OS based routers.

         Copyright 2016 Nokia. All rights reserved. Reproduction of this document
         is authorized on the condition that the foregoing copyright notice is included.

         This nokia-conf-ipsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-27";

    grouping conf-ipsec {
        ///nokia-conf/configure/ipsec
        container ipsec {
            description "Enable the ipsec context";

            ///nokia-conf/configure/ipsec/show-ipsec-keys
            leaf show-ipsec-keys {
                type boolean;
                default "false";
                description "Show IPsec IKE and ESP keys in the output";
            }

            ///nokia-conf/configure/ipsec/apply-groups
            leaf-list apply-groups {
                type leafref {
                    path "../../groups/group/name";
                }
                max-elements 8;
                ordered-by user;
                description "Apply a configuration group at this level";
            }

            ///nokia-conf/configure/ipsec/apply-groups-exclude
            leaf-list apply-groups-exclude {
                type leafref {
                    path "../../groups/group/name";
                }
                max-elements 8;
                ordered-by user;
                description "Exclude a configuration group at this level";
            }

            ///nokia-conf/configure/ipsec/cert-profile
            list cert-profile {
                key "name";
                max-elements 10200;
                description "Enter the cert-profile list instance";

                ///nokia-conf/configure/ipsec/cert-profile/name
                leaf name {
                    type types-sros:named-item;
                    description "Certificate profile name";
                }

                ///nokia-conf/configure/ipsec/cert-profile/admin-state
                leaf admin-state {
                    type types-sros:admin-state;
                    default "disable";
                    description "Administrative state of the certificate profile";
                }

                ///nokia-conf/configure/ipsec/cert-profile/apply-groups
                leaf-list apply-groups {
                    type leafref {
                        path "../../../groups/group/name";
                    }
                    max-elements 8;
                    ordered-by user;
                    description "Apply a configuration group at this level";
                }

                ///nokia-conf/configure/ipsec/cert-profile/apply-groups-exclude
                leaf-list apply-groups-exclude {
                    type leafref {
                        path "../../../groups/group/name";
                    }
                    max-elements 8;
                    ordered-by user;
                    description "Exclude a configuration group at this level";
                }

                ///nokia-conf/configure/ipsec/cert-profile/entry
                list entry {
                    key "id";
                    max-elements 8;
                    description "Enter the entry list instance";

                    ///nokia-conf/configure/ipsec/cert-profile/entry/id
                    leaf id {
                        type uint32 {
                            range "1..8";
                        }
                        description "Certificate profile entry ID";
                    }

                    ///nokia-conf/configure/ipsec/cert-profile/entry/cert
                    leaf cert {
                        type types-security:pki-file-name;
                        description "File name of the imported certificate for the entry";
                    }

                    ///nokia-conf/configure/ipsec/cert-profile/entry/key
                    leaf key {
                        type types-security:pki-file-name;
                        description "File name of the imported key used for authentication";
                    }

                    ///nokia-conf/configure/ipsec/cert-profile/entry/rsa-signature
                    leaf rsa-signature {
                        type enumeration {
                            enum pkcs1                          { value 1; }
                            enum pss                            { value 2; }
                        }
                        default "pkcs1";
                        description "Signature scheme for the RSA key";
                    }

                    ///nokia-conf/configure/ipsec/cert-profile/entry/apply-groups
                    leaf-list apply-groups {
                        type leafref {
                            path "../../../../groups/group/name";
                        }
                        max-elements 8;
                        ordered-by user;
                        description "Apply a configuration group at this level";
                    }

                    ///nokia-conf/configure/ipsec/cert-profile/entry/apply-groups-exclude
                    leaf-list apply-groups-exclude {
                        type leafref {
                            path "../../../../groups/group/name";
                        }
                        max-elements 8;
                        ordered-by user;
                        description "Exclude a configuration group at this level";
                    }

                    ///nokia-conf/configure/ipsec/cert-profile/entry/send-chain
                    container send-chain {
                        description "Enter the send-chain context";

                        ///nokia-conf/configure/ipsec/cert-profile/entry/send-chain/ca-profile
                        leaf-list ca-profile {
                            type leafref {
                                path "../../../../../system/security/pki/ca-profile/ca-profile-name";
                            }
                            max-elements 7;
                            description "CA certificate to send to the peer";
                        }

                    } // container send-chain

                } // list entry

            } // list cert-profile

            ///nokia-conf/configure/ipsec/client-db
            list client-db {
                key "name";
                max-elements 1000;
                description "Enter the client-db list instance";

                ///nokia-conf/configure/ipsec/client-db/name
                leaf name {
                    type types-sros:named-item;
                    description "IPsec client database name";
                }

                ///nokia-conf/configure/ipsec/client-db/admin-state
                leaf admin-state {
                    type types-sros:admin-state;
                    default "disable";
                    description "Administrative state of the client database";
                }

                ///nokia-conf/configure/ipsec/client-db/description
                leaf description {
                    type types-sros:description;
                    description "Text description";
                }

                ///nokia-conf/configure/ipsec/client-db/apply-groups
                leaf-list apply-groups {
                    type leafref {
                        path "../../../groups/group/name";
                    }
                    max-elements 8;
                    ordered-by user;
                    sros-ext:auto-restart-to-modify;
                    description "Apply a configuration group at this level";
                }

                ///nokia-conf/configure/ipsec/client-db/apply-groups-exclude
                leaf-list apply-groups-exclude {
                    type leafref {
                        path "../../../groups/group/name";
                    }
                    max-elements 8;
                    ordered-by user;
                    sros-ext:auto-restart-to-modify;
                    description "Exclude a configuration group at this level";
                }

                ///nokia-conf/configure/ipsec/client-db/match-list
                container match-list {
                    sros-ext:auto-restart-to-modify;
                    description "Enter the match-list context";

                    ///nokia-conf/configure/ipsec/client-db/match-list/idi
                    leaf idi {
                        type boolean;
                        sros-ext:auto-restart-to-modify;
                        default "false";
                        description "Use IDi type in the IPsec client matching process";
                    }

                    ///nokia-conf/configure/ipsec/client-db/match-list/peer-ip-prefix
                    leaf peer-ip-prefix {
                        type boolean;
                        sros-ext:auto-restart-to-modify;
                        default "false";
                        description "Use the peer tunnel IP address in the matching process";
                    }

                } // container match-list

                ///nokia-conf/configure/ipsec/client-db/client
                list client {
                    key "id";
                    description "Enter the client list instance";

                    ///nokia-conf/configure/ipsec/client-db/client/id
                    leaf id {
                        type uint32 {
                            range "1..8000";
                        }
                        description "Client ID";
                    }

                    ///nokia-conf/configure/ipsec/client-db/client/admin-state
                    leaf admin-state {
                        type types-sros:admin-state;
                        default "disable";
                        description "Administrative state of the database client";
                    }

                    ///nokia-conf/configure/ipsec/client-db/client/client-name
                    leaf client-name {
                        type types-sros:named-item;
                        sros-ext:auto-restart-to-modify;
                        description "Client name";
                    }

                    ///nokia-conf/configure/ipsec/client-db/client/private-interface
                    leaf private-interface {
                        type types-sros:named-item;
                        sros-ext:auto-restart-to-modify;
                        description "Private interface name used for tunnel setup";
                    }

                    ///nokia-conf/configure/ipsec/client-db/client/private-service-name
                    leaf private-service-name {
                        type types-services:service-name;
                        sros-ext:auto-restart-to-modify;
                        description "Name of the private service used for tunnel setup";
                    }

                    ///nokia-conf/configure/ipsec/client-db/client/ts-list
                    leaf ts-list {
                        type types-sros:named-item;
                        sros-ext:auto-restart-to-modify;
                        description "Traffic selector list used by the tunnel";
                    }

                    ///nokia-conf/configure/ipsec/client-db/client/tunnel-template
                    leaf tunnel-template {
                        type uint32 {
                            range "1..2048";
                        }
                        sros-ext:auto-restart-to-modify;
                        description "Tunnel template ID";
                    }

                    ///nokia-conf/configure/ipsec/client-db/client/apply-groups
                    leaf-list apply-groups {
                        type leafref {
                            path "../../../../groups/group/name";
                        }
                        max-elements 8;
                        ordered-by user;
                        sros-ext:auto-restart-to-modify;
                        description "Apply a configuration group at this level";
                    }

                    ///nokia-conf/configure/ipsec/client-db/client/apply-groups-exclude
                    leaf-list apply-groups-exclude {
                        type leafref {
                            path "../../../../groups/group/name";
                        }
                        max-elements 8;
                        ordered-by user;
                        sros-ext:auto-restart-to-modify;
                        description "Exclude a configuration group at this level";
                    }

                    ///nokia-conf/configure/ipsec/client-db/client/credential
                    container credential {
                        sros-ext:auto-restart-to-modify;
                        description "Enter the credential context";

                        ///nokia-conf/configure/ipsec/client-db/client/credential/pre-shared-key
                        leaf pre-shared-key {
                            type types-sros:encrypted-leaf-hex-without-prefix {
                                length "1..115";
                            }
                            sros-ext:auto-restart-to-modify;
                            description "Pre-shared key used to authenticate peers";
                        }

                    } // container credential

                    ///nokia-conf/configure/ipsec/client-db/client/identification
                    container identification {
                        sros-ext:auto-restart-to-modify;
                        description "Enter the identification context";

                        ///nokia-conf/configure/ipsec/client-db/client/identification/idi
                        container idi {
                            presence "Enable the idi context";
                            sros-ext:auto-restart-to-modify;
                            description "Enable the idi context";

                            ///nokia-conf/configure/ipsec/client-db/client/identification/idi/idi
                            choice idi {
                                mandatory true;
                                ///nokia-conf/configure/ipsec/client-db/client/identification/idi/idi/any
                                case any {

                                    ///nokia-conf/configure/ipsec/client-db/client/identification/idi/idi/any/any
                                    leaf any {
                                        type boolean;
                                        sros-ext:auto-restart-to-modify;
                                        description "Accept any IDi value as a match";
                                    }

                                }
                                ///nokia-conf/configure/ipsec/client-db/client/identification/idi/idi/ipv4-prefix
                                case ipv4-prefix {

                                    ///nokia-conf/configure/ipsec/client-db/client/identification/idi/idi/ipv4-prefix/ipv4-prefix
                                    leaf ipv4-prefix {
                                        type types-sros:ipv4-prefix;
                                        sros-ext:auto-restart-to-modify;
                                        description "IPv4 prefix used as the match criteria for the IDi";
                                    }

                                }
                                ///nokia-conf/configure/ipsec/client-db/client/identification/idi/idi/ipv4-prefix-any
                                case ipv4-prefix-any {

                                    ///nokia-conf/configure/ipsec/client-db/client/identification/idi/idi/ipv4-prefix-any/ipv4-prefix-any
                                    leaf ipv4-prefix-any {
                                        type boolean;
                                        sros-ext:auto-restart-to-modify;
                                        description "Accept any valid IPv4 prefix as a match for the IDi";
                                    }

                                }
                                ///nokia-conf/configure/ipsec/client-db/client/identification/idi/idi/ipv6-prefix
                                case ipv6-prefix {

                                    ///nokia-conf/configure/ipsec/client-db/client/identification/idi/idi/ipv6-prefix/ipv6-prefix
                                    leaf ipv6-prefix {
                                        type types-sros:ipv6-prefix;
                                        sros-ext:auto-restart-to-modify;
                                        description "IPv6 prefix used as the match criteria for the IDi";
                                    }

                                }
                                ///nokia-conf/configure/ipsec/client-db/client/identification/idi/idi/ipv6-prefix-any
                                case ipv6-prefix-any {

                                    ///nokia-conf/configure/ipsec/client-db/client/identification/idi/idi/ipv6-prefix-any/ipv6-prefix-any
                                    leaf ipv6-prefix-any {
                                        type boolean;
                                        sros-ext:auto-restart-to-modify;
                                        description "Accept any valid IPv6 prefix as a match for the IDi";
                                    }

                                }
                                ///nokia-conf/configure/ipsec/client-db/client/identification/idi/idi/fqdn
                                case fqdn {

                                    ///nokia-conf/configure/ipsec/client-db/client/identification/idi/idi/fqdn/fqdn
                                    leaf fqdn {
                                        type types-sros:display-string-or-empty;
                                        sros-ext:auto-restart-to-modify;
                                        description "FQDN used as the match criteria for the IDi";
                                    }

                                }
                                ///nokia-conf/configure/ipsec/client-db/client/identification/idi/idi/fqdn-suffix
                                case fqdn-suffix {

                                    ///nokia-conf/configure/ipsec/client-db/client/identification/idi/idi/fqdn-suffix/fqdn-suffix
                                    leaf fqdn-suffix {
                                        type types-sros:display-string-or-empty;
                                        sros-ext:auto-restart-to-modify;
                                        description "FQDN suffix used as the match criteria for the IDi";
                                    }

                                }
                                ///nokia-conf/configure/ipsec/client-db/client/identification/idi/idi/rfc822
                                case rfc822 {

                                    ///nokia-conf/configure/ipsec/client-db/client/identification/idi/idi/rfc822/rfc822
                                    leaf rfc822 {
                                        type types-sros:display-string-or-empty;
                                        sros-ext:auto-restart-to-modify;
                                        description "Email address (RFC 822) used as match criteria for IDi";
                                    }

                                }
                                ///nokia-conf/configure/ipsec/client-db/client/identification/idi/idi/rfc822-suffix
                                case rfc822-suffix {

                                    ///nokia-conf/configure/ipsec/client-db/client/identification/idi/idi/rfc822-suffix/rfc822-suffix
                                    leaf rfc822-suffix {
                                        type types-sros:display-string-or-empty;
                                        sros-ext:auto-restart-to-modify;
                                        description "Email address domain (RFC 822) as IDi match criteria";
                                    }

                                }
                            }
                        } // container idi

                        ///nokia-conf/configure/ipsec/client-db/client/identification/peer-ip-prefix
                        container peer-ip-prefix {
                            presence "Enable the peer-ip-prefix context";
                            sros-ext:auto-restart-to-modify;
                            description "Enable the peer-ip-prefix context";

                            ///nokia-conf/configure/ipsec/client-db/client/identification/peer-ip-prefix/prefix
                            choice prefix {
                                mandatory true;
                                ///nokia-conf/configure/ipsec/client-db/client/identification/peer-ip-prefix/prefix/ipv4-only
                                case ipv4-only {

                                    ///nokia-conf/configure/ipsec/client-db/client/identification/peer-ip-prefix/prefix/ipv4-only/ipv4-only
                                    leaf ipv4-only {
                                        type boolean;
                                        sros-ext:auto-restart-to-modify;
                                        description "Accept any valid IPv4 address as a match";
                                    }

                                }
                                ///nokia-conf/configure/ipsec/client-db/client/identification/peer-ip-prefix/prefix/ipv6-only
                                case ipv6-only {

                                    ///nokia-conf/configure/ipsec/client-db/client/identification/peer-ip-prefix/prefix/ipv6-only/ipv6-only
                                    leaf ipv6-only {
                                        type boolean;
                                        sros-ext:auto-restart-to-modify;
                                        description "Accept any valid IPv6 address as a match";
                                    }

                                }
                                ///nokia-conf/configure/ipsec/client-db/client/identification/peer-ip-prefix/prefix/ip-prefix
                                case ip-prefix {

                                    ///nokia-conf/configure/ipsec/client-db/client/identification/peer-ip-prefix/prefix/ip-prefix/ip-prefix
                                    leaf ip-prefix {
                                        type types-sros:ip-prefix;
                                        sros-ext:auto-restart-to-modify;
                                        description "IP prefix used as the match criteria";
                                    }

                                }
                            }
                        } // container peer-ip-prefix

                    } // container identification

                } // list client

            } // list client-db

            ///nokia-conf/configure/ipsec/ike-policy
            list ike-policy {
                key "id";
                max-elements 2048;
                description "Enter the ike-policy list instance";

                ///nokia-conf/configure/ipsec/ike-policy/id
                leaf id {
                    type types-ipsec:ike-policy-id;
                    description "IKE policy ID";
                }

                ///nokia-conf/configure/ipsec/ike-policy/description
                leaf description {
                    type types-sros:description;
                    description "Text description";
                }

                ///nokia-conf/configure/ipsec/ike-policy/ipsec-lifetime
                leaf ipsec-lifetime {
                    type types-ipsec:lifetime;
                    default "3600";
                    description "Lifetime of the Phase 2 IKE key";
                }

                ///nokia-conf/configure/ipsec/ike-policy/match-peer-id-to-cert
                leaf match-peer-id-to-cert {
                    type boolean;
                    default "false";
                    description "Check IKE peer ID during certificate authentication";
                }

                ///nokia-conf/configure/ipsec/ike-policy/ike-transform
                leaf-list ike-transform {
                    type leafref {
                        path "../../ike-transform/id";
                    }
                    max-elements 4;
                    description "IKE transform instance associated with the IKE policy";
                }

                ///nokia-conf/configure/ipsec/ike-policy/apply-groups
                leaf-list apply-groups {
                    type leafref {
                        path "../../../groups/group/name";
                    }
                    max-elements 8;
                    ordered-by user;
                    description "Apply a configuration group at this level";
                }

                ///nokia-conf/configure/ipsec/ike-policy/apply-groups-exclude
                leaf-list apply-groups-exclude {
                    type leafref {
                        path "../../../groups/group/name";
                    }
                    max-elements 8;
                    ordered-by user;
                    description "Exclude a configuration group at this level";
                }

                ///nokia-conf/configure/ipsec/ike-policy/ike-version
                choice ike-version {
                    default "version-1";
                    ///nokia-conf/configure/ipsec/ike-policy/ike-version/version-1
                    case version-1 {

                        ///nokia-conf/configure/ipsec/ike-policy/ike-version/version-1/ike-version-1
                        container ike-version-1 {
                            description "Enter the ike-version-1 context";

                            ///nokia-conf/configure/ipsec/ike-policy/ike-version/version-1/ike-version-1/auth-method
                            leaf auth-method {
                                type enumeration {
                                    enum psk                            { value 1; }
                                    enum plain-psk-xauth                { value 4; }
                                }
                                default "psk";
                                description "Authentication method used with the IKE policy";
                            }

                            ///nokia-conf/configure/ipsec/ike-policy/ike-version/version-1/ike-version-1/own-auth-method
                            leaf own-auth-method {
                                type enumeration {
                                    enum symmetric                      { value 0; }
                                }
                                default "symmetric";
                                description "Authentication method used with policy on its own side";
                            }

                            ///nokia-conf/configure/ipsec/ike-policy/ike-version/version-1/ike-version-1/ike-mode
                            leaf ike-mode {
                                type enumeration {
                                    enum main                           { value 1; }
                                    enum aggressive                     { value 2; }
                                }
                                default "main";
                                description "Mode of operation";
                            }

                            ///nokia-conf/configure/ipsec/ike-policy/ike-version/version-1/ike-version-1/ph1-responder-delete-notify
                            leaf ph1-responder-delete-notify {
                                type boolean;
                                default "true";
                                description "Send delete notification for IKEv1 phase 1 removal";
                            }

                        } // container ike-version-1

                    }
                    ///nokia-conf/configure/ipsec/ike-policy/ike-version/version-2
                    case version-2 {

                        ///nokia-conf/configure/ipsec/ike-policy/ike-version/version-2/ike-version-2
                        container ike-version-2 {
                            presence "Enable the ike-version-2 context";
                            description "Enable the ike-version-2 context";

                            ///nokia-conf/configure/ipsec/ike-policy/ike-version/version-2/ike-version-2/auth-method
                            leaf auth-method {
                                type enumeration {
                                    enum psk                            { value 1; }
                                    enum cert                           { value 5; }
                                    enum psk-radius                     { value 6; }
                                    enum cert-radius                    { value 7; }
                                    enum eap                            { value 8; }
                                    enum auto-eap-radius                { value 9; }
                                    enum auto-eap                       { value 10; }
                                }
                                default "psk";
                                description "Authentication method used with the IKE policy";
                            }

                            ///nokia-conf/configure/ipsec/ike-policy/ike-version/version-2/ike-version-2/own-auth-method
                            leaf own-auth-method {
                                type enumeration {
                                    enum symmetric                      { value 0; }
                                    enum psk                            { value 1; }
                                    enum cert                           { value 5; }
                                    enum eap-only                       { value 8; }
                                }
                                default "symmetric";
                                description "Authentication method used with IKE policy on own side";
                            }

                            ///nokia-conf/configure/ipsec/ike-policy/ike-version/version-2/ike-version-2/auto-eap-method
                            leaf auto-eap-method {
                                type enumeration {
                                    enum psk                            { value 1; }
                                    enum cert                           { value 2; }
                                    enum psk-or-cert                    { value 3; }
                                }
                                default "cert";
                                description "Authentication method used for the remote peer";
                            }

                            ///nokia-conf/configure/ipsec/ike-policy/ike-version/version-2/ike-version-2/own-auto-eap-method
                            leaf own-auto-eap-method {
                                type enumeration {
                                    enum psk                            { value 1; }
                                    enum cert                           { value 2; }
                                }
                                default "cert";
                                description "Authentication method used on its own side";
                            }

                            ///nokia-conf/configure/ipsec/ike-policy/ike-version/version-2/ike-version-2/send-idr-after-eap-success
                            leaf send-idr-after-eap-success {
                                type boolean;
                                default "true";
                                description "Send IDr payload in last IKE authentication response";
                            }

                            ///nokia-conf/configure/ipsec/ike-policy/ike-version/version-2/ike-version-2/ikev2-fragment
                            container ikev2-fragment {
                                presence "Enable the ikev2-fragment context";
                                description "Enable the ikev2-fragment context";

                                ///nokia-conf/configure/ipsec/ike-policy/ike-version/version-2/ike-version-2/ikev2-fragment/mtu
                                leaf mtu {
                                    type uint32 {
                                        range "512..9000";
                                    }
                                    units "octets";
                                    default "1500";
                                    description "Maximum size of the IKEv2 packet";
                                }

                                ///nokia-conf/configure/ipsec/ike-policy/ike-version/version-2/ike-version-2/ikev2-fragment/reassembly-timeout
                                leaf reassembly-timeout {
                                    type uint32 {
                                        range "1..5";
                                    }
                                    units "seconds";
                                    default "2";
                                    description "Timeout for reassembly of IKEv2 message fragments";
                                }

                            } // container ikev2-fragment

                        } // container ike-version-2

                    }
                }
                ///nokia-conf/configure/ipsec/ike-policy/limit-init-exchange
                container limit-init-exchange {
                    when "../ike-version-2" {
                        description "Feature not supported in IKEv1";
                    }
                    description "Enter the limit-init-exchange context";

                    ///nokia-conf/configure/ipsec/ike-policy/limit-init-exchange/admin-state
                    leaf admin-state {
                        type types-sros:admin-state;
                        default "enable";
                        description "Administrative state of limiting initial IKE exchanges";
                    }

                    ///nokia-conf/configure/ipsec/ike-policy/limit-init-exchange/reduced-max-exchange-timeout
                    leaf reduced-max-exchange-timeout {
                        type union {
                            type uint32 {
                                range "2..60";
                            }
                            type enumeration {
                                enum none                           { value 0; }
                            }
                        }
                        units "seconds";
                        default "2";
                        description "Maximum timeout for in-progress initial IKE exchange";
                    }

                } // container limit-init-exchange

                ///nokia-conf/configure/ipsec/ike-policy/dpd
                container dpd {
                    presence "Enable the dpd context";
                    description "Enable the dpd context";

                    ///nokia-conf/configure/ipsec/ike-policy/dpd/reply-only
                    leaf reply-only {
                        type boolean;
                        default "false";
                        description "Initiate DPD request for incoming ESP or IKE packets";
                    }

                    ///nokia-conf/configure/ipsec/ike-policy/dpd/interval
                    leaf interval {
                        type uint32 {
                            range "10..300";
                        }
                        units "seconds";
                        default "30";
                        description "DPD interval";
                    }

                    ///nokia-conf/configure/ipsec/ike-policy/dpd/max-retries
                    leaf max-retries {
                        type uint32 {
                            range "2..5";
                        }
                        default "3";
                        description "Maximum number of retries before the tunnel is removed";
                    }

                } // container dpd

                ///nokia-conf/configure/ipsec/ike-policy/nat-traversal
                container nat-traversal {
                    presence "Enable the nat-traversal context";
                    description "Enable the nat-traversal context";

                    ///nokia-conf/configure/ipsec/ike-policy/nat-traversal/force
                    leaf force {
                        type boolean;
                        default "false";
                        description "Enable NAT-T in forced mode";
                    }

                    ///nokia-conf/configure/ipsec/ike-policy/nat-traversal/keep-alive-interval
                    leaf keep-alive-interval {
                        type uint32 {
                            range "120..600";
                        }
                        units "seconds";
                        description "Keepalive interval for NAT-T";
                    }

                    ///nokia-conf/configure/ipsec/ike-policy/nat-traversal/force-keep-alive
                    leaf force-keep-alive {
                        type boolean;
                        default "true";
                        description "Continue sending keepalive packets (no expiry)";
                    }

                } // container nat-traversal

                ///nokia-conf/configure/ipsec/ike-policy/lockout
                container lockout {
                    presence "Enable the lockout context";
                    description "Enable the lockout context";

                    ///nokia-conf/configure/ipsec/ike-policy/lockout/failed-attempts
                    leaf failed-attempts {
                        type uint32 {
                            range "1..64";
                        }
                        default "3";
                        description "Maximum failed authentications allowed in the duration";
                    }

                    ///nokia-conf/configure/ipsec/ike-policy/lockout/duration
                    leaf duration {
                        type uint32 {
                            range "1..60";
                        }
                        units "minutes";
                        default "5";
                        description "Time interval for failed attempts threshold";
                    }

                    ///nokia-conf/configure/ipsec/ike-policy/lockout/block
                    leaf block {
                        type union {
                            type uint32 {
                                range "1..1440";
                            }
                            type enumeration {
                                enum infinite                       { value 0; }
                            }
                        }
                        units "minutes";
                        default "10";
                        description "Time a client is blocked for failed authentications";
                    }

                    ///nokia-conf/configure/ipsec/ike-policy/lockout/max-port-per-ip
                    leaf max-port-per-ip {
                        type uint32 {
                            range "1..32000";
                        }
                        default "16";
                        description "Maximum number of ports allowed under same IP address";
                    }

                } // container lockout

                ///nokia-conf/configure/ipsec/ike-policy/pfs
                container pfs {
                    presence "Enable the pfs context";
                    description "Enable the pfs context";

                    ///nokia-conf/configure/ipsec/ike-policy/pfs/dh-group
                    leaf dh-group {
                        type types-ipsec:dh-group;
                        default "group-2";
                        description "Diffie-Helman group used to calculate session keys";
                    }

                } // container pfs

                ///nokia-conf/configure/ipsec/ike-policy/relay-unsolicited-cfg-attribute
                container relay-unsolicited-cfg-attribute {
                    description "Enter the relay-unsolicited-cfg-attribute context";

                    ///nokia-conf/configure/ipsec/ike-policy/relay-unsolicited-cfg-attribute/internal-ip4-address
                    leaf internal-ip4-address {
                        type boolean;
                        default "false";
                        description "Return the IPv4 address from the source to the client";
                    }

                    ///nokia-conf/configure/ipsec/ike-policy/relay-unsolicited-cfg-attribute/internal-ip4-netmask
                    leaf internal-ip4-netmask {
                        type boolean;
                        default "false";
                        description "Return the IPv4 netmask from the source to the client";
                    }

                    ///nokia-conf/configure/ipsec/ike-policy/relay-unsolicited-cfg-attribute/internal-ip4-dns
                    leaf internal-ip4-dns {
                        type boolean;
                        default "false";
                        description "Return IPv4 DNS server address from source to client";
                    }

                    ///nokia-conf/configure/ipsec/ike-policy/relay-unsolicited-cfg-attribute/internal-ip6-address
                    leaf internal-ip6-address {
                        type boolean;
                        default "false";
                        description "Return the IPv6 address from the source to the client";
                    }

                    ///nokia-conf/configure/ipsec/ike-policy/relay-unsolicited-cfg-attribute/internal-ip6-dns
                    leaf internal-ip6-dns {
                        type boolean;
                        default "false";
                        description "Return IPv6 DNS server address from source to client";
                    }

                } // container relay-unsolicited-cfg-attribute

            } // list ike-policy

            ///nokia-conf/configure/ipsec/ike-transform
            list ike-transform {
                key "id";
                max-elements 4096;
                description "Enter the ike-transform list instance";

                ///nokia-conf/configure/ipsec/ike-transform/id
                leaf id {
                    type types-ipsec:ike-transform-id;
                    description "IKE transform instance ID";
                }

                ///nokia-conf/configure/ipsec/ike-transform/dh-group
                leaf dh-group {
                    type types-ipsec:dh-group;
                    default "group-2";
                    description "Diffie-Helman group used to calculate session keys";
                }

                ///nokia-conf/configure/ipsec/ike-transform/ike-auth-algorithm
                leaf ike-auth-algorithm {
                    type types-ipsec:ike-auth-algorithms;
                    default "sha-1";
                    description "IKE authentication algorithm for IKE transform instance";
                }

                ///nokia-conf/configure/ipsec/ike-transform/ike-encryption-algorithm
                leaf ike-encryption-algorithm {
                    type types-ipsec:ike-encryption-algorithms;
                    default "aes-128";
                    description "IKE encryption algorith for the IKE transform instance";
                }

                ///nokia-conf/configure/ipsec/ike-transform/ike-prf-algorithm
                leaf ike-prf-algorithm {
                    type types-ipsec:prf-algorithms;
                    default "same-as-auth";
                    description "PRF algorithm for the IKE transform instance";
                }

                ///nokia-conf/configure/ipsec/ike-transform/isakmp-lifetime
                leaf isakmp-lifetime {
                    type types-ipsec:lifetime;
                    default "86400";
                    description "Phase 1 lifetime for the IKE transform instance";
                }

                ///nokia-conf/configure/ipsec/ike-transform/apply-groups
                leaf-list apply-groups {
                    type leafref {
                        path "../../../groups/group/name";
                    }
                    max-elements 8;
                    ordered-by user;
                    description "Apply a configuration group at this level";
                }

                ///nokia-conf/configure/ipsec/ike-transform/apply-groups-exclude
                leaf-list apply-groups-exclude {
                    type leafref {
                        path "../../../groups/group/name";
                    }
                    max-elements 8;
                    ordered-by user;
                    description "Exclude a configuration group at this level";
                }

            } // list ike-transform

            ///nokia-conf/configure/ipsec/ipsec-transform
            list ipsec-transform {
                key "id";
                max-elements 2048;
                description "Enter the ipsec-transform list instance";

                ///nokia-conf/configure/ipsec/ipsec-transform/id
                leaf id {
                    type uint32 {
                        range "1..2048";
                    }
                    description "IPsec transform policy ID";
                }

                ///nokia-conf/configure/ipsec/ipsec-transform/esp-auth-algorithm
                leaf esp-auth-algorithm {
                    type types-ipsec:auth-algorithms;
                    default "sha-1";
                    description "Encapsulating Security Payload (ESP) authentication";
                }

                ///nokia-conf/configure/ipsec/ipsec-transform/esp-encryption-algorithm
                leaf esp-encryption-algorithm {
                    type types-ipsec:encryption-algorithms;
                    default "aes-128";
                    description "Encryption algorithm for the IPsec transform session";
                }

                ///nokia-conf/configure/ipsec/ipsec-transform/ipsec-lifetime
                leaf ipsec-lifetime {
                    type types-ipsec:lifetime;
                    description "Phase 2 lifetime for the IPsec transform session";
                }

                ///nokia-conf/configure/ipsec/ipsec-transform/pfs-dh-group
                leaf pfs-dh-group {
                    type enumeration {
                        enum none                           { value 0; }
                        enum group-1                        { value 1; }
                        enum group-2                        { value 2; }
                        enum group-5                        { value 5; }
                        enum group-14                       { value 14; }
                        enum group-15                       { value 15; }
                        enum group-19                       { value 19; }
                        enum group-20                       { value 20; }
                        enum group-21                       { value 21; }
                    }
                    description "Diffie-Hellman group used for PFS compilation";
                }

                ///nokia-conf/configure/ipsec/ipsec-transform/extended-sequence-number
                leaf extended-sequence-number {
                    type boolean;
                    default "false";
                    description "Enable extended sequence numbering support";
                }

                ///nokia-conf/configure/ipsec/ipsec-transform/apply-groups
                leaf-list apply-groups {
                    type leafref {
                        path "../../../groups/group/name";
                    }
                    max-elements 8;
                    ordered-by user;
                    description "Apply a configuration group at this level";
                }

                ///nokia-conf/configure/ipsec/ipsec-transform/apply-groups-exclude
                leaf-list apply-groups-exclude {
                    type leafref {
                        path "../../../groups/group/name";
                    }
                    max-elements 8;
                    ordered-by user;
                    description "Exclude a configuration group at this level";
                }

            } // list ipsec-transform

            ///nokia-conf/configure/ipsec/static-sa
            list static-sa {
                key "name";
                max-elements 1000;
                description "Enter the static-sa list instance";

                ///nokia-conf/configure/ipsec/static-sa/name
                leaf name {
                    type types-sros:named-item;
                    description "Static SA name";
                }

                ///nokia-conf/configure/ipsec/static-sa/description
                leaf description {
                    type types-sros:named-item;
                    description "Text description";
                }

                ///nokia-conf/configure/ipsec/static-sa/direction
                leaf direction {
                    type enumeration {
                        enum inbound                        { value 1; }
                        enum outbound                       { value 2; }
                        enum bidirectional                  { value 3; }
                    }
                    default "bidirectional";
                    description "Direction to which the static SA entry can be applied";
                }

                ///nokia-conf/configure/ipsec/static-sa/protocol
                leaf protocol {
                    type enumeration {
                        enum ah                             { value 1; }
                        enum esp                            { value 2; }
                    }
                    default "esp";
                    description "IPsec protocol used with the static SA";
                }

                ///nokia-conf/configure/ipsec/static-sa/spi
                leaf spi {
                    type uint32 {
                        range "256..16383";
                    }
                    description "Security Parameter Index (SPI) for the static SA";
                }

                ///nokia-conf/configure/ipsec/static-sa/apply-groups
                leaf-list apply-groups {
                    type leafref {
                        path "../../../groups/group/name";
                    }
                    max-elements 8;
                    ordered-by user;
                    description "Apply a configuration group at this level";
                }

                ///nokia-conf/configure/ipsec/static-sa/apply-groups-exclude
                leaf-list apply-groups-exclude {
                    type leafref {
                        path "../../../groups/group/name";
                    }
                    max-elements 8;
                    ordered-by user;
                    description "Exclude a configuration group at this level";
                }

                ///nokia-conf/configure/ipsec/static-sa/authentication
                container authentication {
                    presence "Enable the authentication context";
                    description "Enable the authentication context";

                    ///nokia-conf/configure/ipsec/static-sa/authentication/algorithm
                    leaf algorithm {
                        type enumeration {
                            enum md5                            { value 2; }
                            enum sha1                           { value 3; }
                        }
                        mandatory true;
                        description "Authentication algorithm used for an IPsec manual SA";
                    }

                    ///nokia-conf/configure/ipsec/static-sa/authentication/key
                    leaf key {
                        type types-sros:encrypted-leaf {
                            length "1..54";
                        }
                        mandatory true;
                        description "Key used for the authentication algorithm";
                    }

                } // container authentication

            } // list static-sa

            ///nokia-conf/configure/ipsec/ts-list
            list ts-list {
                key "name";
                max-elements 32768;
                description "Enter the ts-list list instance";

                ///nokia-conf/configure/ipsec/ts-list/name
                leaf name {
                    type types-sros:named-item;
                    description "Traffic Selector (TS) list name";
                }

                ///nokia-conf/configure/ipsec/ts-list/apply-groups
                leaf-list apply-groups {
                    type leafref {
                        path "../../../groups/group/name";
                    }
                    max-elements 8;
                    ordered-by user;
                    description "Apply a configuration group at this level";
                }

                ///nokia-conf/configure/ipsec/ts-list/apply-groups-exclude
                leaf-list apply-groups-exclude {
                    type leafref {
                        path "../../../groups/group/name";
                    }
                    max-elements 8;
                    ordered-by user;
                    description "Exclude a configuration group at this level";
                }

                ///nokia-conf/configure/ipsec/ts-list/local
                container local {
                    description "Enter the local context";

                    ///nokia-conf/configure/ipsec/ts-list/local/entry
                    list entry {
                        key "id";
                        description "Enter the entry list instance";

                        ///nokia-conf/configure/ipsec/ts-list/local/entry/id
                        leaf id {
                            type uint32 {
                                range "1..32";
                            }
                            description "TS list entry ID";
                        }

                        ///nokia-conf/configure/ipsec/ts-list/local/entry/apply-groups
                        leaf-list apply-groups {
                            type leafref {
                                path "../../../../../groups/group/name";
                            }
                            max-elements 8;
                            ordered-by user;
                            description "Apply a configuration group at this level";
                        }

                        ///nokia-conf/configure/ipsec/ts-list/local/entry/apply-groups-exclude
                        leaf-list apply-groups-exclude {
                            type leafref {
                                path "../../../../../groups/group/name";
                            }
                            max-elements 8;
                            ordered-by user;
                            description "Exclude a configuration group at this level";
                        }

                        ///nokia-conf/configure/ipsec/ts-list/local/entry/address
                        container address {
                            presence "Enable the address context";
                            description "Enable the address context";

                            ///nokia-conf/configure/ipsec/ts-list/local/entry/address/address-range
                            choice address-range {
                                mandatory true;
                                ///nokia-conf/configure/ipsec/ts-list/local/entry/address/address-range/prefix
                                case prefix {

                                    ///nokia-conf/configure/ipsec/ts-list/local/entry/address/address-range/prefix/prefix
                                    leaf prefix {
                                        type types-sros:ip-prefix;
                                        description "IP prefix for address range in IKEv2 traffic selector";
                                    }

                                }
                                ///nokia-conf/configure/ipsec/ts-list/local/entry/address/address-range/range
                                case range {

                                    ///nokia-conf/configure/ipsec/ts-list/local/entry/address/address-range/range/range
                                    container range {
                                        presence "Enable the range context";
                                        description "Enable the range context";

                                        ///nokia-conf/configure/ipsec/ts-list/local/entry/address/address-range/range/range/begin
                                        leaf begin {
                                            type types-sros:ip-address;
                                            mandatory true;
                                            description "Lower bound of the IP address range for the entry";
                                        }

                                        ///nokia-conf/configure/ipsec/ts-list/local/entry/address/address-range/range/range/end
                                        leaf end {
                                            type types-sros:ip-address;
                                            mandatory true;
                                            description "Upper bound of the IP address range";
                                        }

                                    } // container range

                                }
                            }
                        } // container address

                        ///nokia-conf/configure/ipsec/ts-list/local/entry/protocol
                        container protocol {
                            presence "Enable the protocol context";
                            description "Enable the protocol context";

                            ///nokia-conf/configure/ipsec/ts-list/local/entry/protocol/range
                            choice range {
                                mandatory true;
                                ///nokia-conf/configure/ipsec/ts-list/local/entry/protocol/range/any
                                case any {

                                    ///nokia-conf/configure/ipsec/ts-list/local/entry/protocol/range/any/any
                                    leaf any {
                                        type empty;
                                        description "Match any protocol ID";
                                    }

                                }
                                ///nokia-conf/configure/ipsec/ts-list/local/entry/protocol/range/id
                                case id {

                                    ///nokia-conf/configure/ipsec/ts-list/local/entry/protocol/range/id/id
                                    container id {
                                        presence "Enable the id context";
                                        description "Enable the id context";

                                        ///nokia-conf/configure/ipsec/ts-list/local/entry/protocol/range/id/id/id
                                        choice id {
                                            mandatory true;
                                            ///nokia-conf/configure/ipsec/ts-list/local/entry/protocol/range/id/id/id/tcp
                                            case tcp {

                                                ///nokia-conf/configure/ipsec/ts-list/local/entry/protocol/range/id/id/id/tcp/tcp
                                                container tcp {
                                                    description "Enter the tcp context";

                                                    ///nokia-conf/configure/ipsec/ts-list/local/entry/protocol/range/id/id/id/tcp/tcp/port
                                                    choice port {
                                                        ///nokia-conf/configure/ipsec/ts-list/local/entry/protocol/range/id/id/id/tcp/tcp/port/opaque-port
                                                        case opaque-port {

                                                            ///nokia-conf/configure/ipsec/ts-list/local/entry/protocol/range/id/id/id/tcp/tcp/port/opaque-port/opaque
                                                            leaf opaque {
                                                                type empty;
                                                                description "Support OPAQUE ports";
                                                            }

                                                        }
                                                        ///nokia-conf/configure/ipsec/ts-list/local/entry/protocol/range/id/id/id/tcp/tcp/port/port-range
                                                        case port-range {

                                                            ///nokia-conf/configure/ipsec/ts-list/local/entry/protocol/range/id/id/id/tcp/tcp/port/port-range/port-range
                                                            container port-range {
                                                                presence "Enable the port-range context";
                                                                description "Enable the port-range context";

                                                                ///nokia-conf/configure/ipsec/ts-list/local/entry/protocol/range/id/id/id/tcp/tcp/port/port-range/port-range/begin
                                                                leaf begin {
                                                                    type uint32 {
                                                                        range "0..65535";
                                                                    }
                                                                    mandatory true;
                                                                    description "Lower bound of the port range";
                                                                }

                                                                ///nokia-conf/configure/ipsec/ts-list/local/entry/protocol/range/id/id/id/tcp/tcp/port/port-range/port-range/end
                                                                leaf end {
                                                                    type uint32 {
                                                                        range "0..65535";
                                                                    }
                                                                    mandatory true;
                                                                    description "Upper bound of the port range";
                                                                }

                                                            } // container port-range

                                                        }
                                                    }
                                                } // container tcp

                                            }
                                            ///nokia-conf/configure/ipsec/ts-list/local/entry/protocol/range/id/id/id/udp
                                            case udp {

                                                ///nokia-conf/configure/ipsec/ts-list/local/entry/protocol/range/id/id/id/udp/udp
                                                container udp {
                                                    description "Enter the udp context";

                                                    ///nokia-conf/configure/ipsec/ts-list/local/entry/protocol/range/id/id/id/udp/udp/port
                                                    choice port {
                                                        ///nokia-conf/configure/ipsec/ts-list/local/entry/protocol/range/id/id/id/udp/udp/port/opaque-port
                                                        case opaque-port {

                                                            ///nokia-conf/configure/ipsec/ts-list/local/entry/protocol/range/id/id/id/udp/udp/port/opaque-port/opaque
                                                            leaf opaque {
                                                                type empty;
                                                                description "Support OPAQUE ports";
                                                            }

                                                        }
                                                        ///nokia-conf/configure/ipsec/ts-list/local/entry/protocol/range/id/id/id/udp/udp/port/port-range
                                                        case port-range {

                                                            ///nokia-conf/configure/ipsec/ts-list/local/entry/protocol/range/id/id/id/udp/udp/port/port-range/port-range
                                                            container port-range {
                                                                presence "Enable the port-range context";
                                                                description "Enable the port-range context";

                                                                ///nokia-conf/configure/ipsec/ts-list/local/entry/protocol/range/id/id/id/udp/udp/port/port-range/port-range/begin
                                                                leaf begin {
                                                                    type uint32 {
                                                                        range "0..65535";
                                                                    }
                                                                    mandatory true;
                                                                    description "Lower bound of the port range";
                                                                }

                                                                ///nokia-conf/configure/ipsec/ts-list/local/entry/protocol/range/id/id/id/udp/udp/port/port-range/port-range/end
                                                                leaf end {
                                                                    type uint32 {
                                                                        range "0..65535";
                                                                    }
                                                                    mandatory true;
                                                                    description "Upper bound of the port range";
                                                                }

                                                            } // container port-range

                                                        }
                                                    }
                                                } // container udp

                                            }
                                            ///nokia-conf/configure/ipsec/ts-list/local/entry/protocol/range/id/id/id/sctp
                                            case sctp {

                                                ///nokia-conf/configure/ipsec/ts-list/local/entry/protocol/range/id/id/id/sctp/sctp
                                                container sctp {
                                                    description "Enter the sctp context";

                                                    ///nokia-conf/configure/ipsec/ts-list/local/entry/protocol/range/id/id/id/sctp/sctp/port
                                                    choice port {
                                                        ///nokia-conf/configure/ipsec/ts-list/local/entry/protocol/range/id/id/id/sctp/sctp/port/opaque-port
                                                        case opaque-port {

                                                            ///nokia-conf/configure/ipsec/ts-list/local/entry/protocol/range/id/id/id/sctp/sctp/port/opaque-port/opaque
                                                            leaf opaque {
                                                                type empty;
                                                                description "Support OPAQUE ports";
                                                            }

                                                        }
                                                        ///nokia-conf/configure/ipsec/ts-list/local/entry/protocol/range/id/id/id/sctp/sctp/port/port-range
                                                        case port-range {

                                                            ///nokia-conf/configure/ipsec/ts-list/local/entry/protocol/range/id/id/id/sctp/sctp/port/port-range/port-range
                                                            container port-range {
                                                                presence "Enable the port-range context";
                                                                description "Enable the port-range context";

                                                                ///nokia-conf/configure/ipsec/ts-list/local/entry/protocol/range/id/id/id/sctp/sctp/port/port-range/port-range/begin
                                                                leaf begin {
                                                                    type uint32 {
                                                                        range "0..65535";
                                                                    }
                                                                    mandatory true;
                                                                    description "Lower bound of the port range";
                                                                }

                                                                ///nokia-conf/configure/ipsec/ts-list/local/entry/protocol/range/id/id/id/sctp/sctp/port/port-range/port-range/end
                                                                leaf end {
                                                                    type uint32 {
                                                                        range "0..65535";
                                                                    }
                                                                    mandatory true;
                                                                    description "Upper bound of the port range";
                                                                }

                                                            } // container port-range

                                                        }
                                                    }
                                                } // container sctp

                                            }
                                            ///nokia-conf/configure/ipsec/ts-list/local/entry/protocol/range/id/id/id/icmp
                                            case icmp {

                                                ///nokia-conf/configure/ipsec/ts-list/local/entry/protocol/range/id/id/id/icmp/icmp
                                                container icmp {
                                                    description "Enter the icmp context";

                                                    ///nokia-conf/configure/ipsec/ts-list/local/entry/protocol/range/id/id/id/icmp/icmp/port
                                                    choice port {
                                                        ///nokia-conf/configure/ipsec/ts-list/local/entry/protocol/range/id/id/id/icmp/icmp/port/opaque-port
                                                        case opaque-port {

                                                            ///nokia-conf/configure/ipsec/ts-list/local/entry/protocol/range/id/id/id/icmp/icmp/port/opaque-port/opaque
                                                            leaf opaque {
                                                                type empty;
                                                                description "Support OPAQUE ports";
                                                            }

                                                        }
                                                        ///nokia-conf/configure/ipsec/ts-list/local/entry/protocol/range/id/id/id/icmp/icmp/port/port-range
                                                        case port-range {

                                                            ///nokia-conf/configure/ipsec/ts-list/local/entry/protocol/range/id/id/id/icmp/icmp/port/port-range/port-range
                                                            container port-range {
                                                                presence "Enable the port-range context";
                                                                description "Enable the port-range context";

                                                                ///nokia-conf/configure/ipsec/ts-list/local/entry/protocol/range/id/id/id/icmp/icmp/port/port-range/port-range/begin-icmp-type
                                                                leaf begin-icmp-type {
                                                                    type uint16 {
                                                                        range "0..255";
                                                                    }
                                                                    mandatory true;
                                                                    description "Lower bound of the ICMP type range";
                                                                }

                                                                ///nokia-conf/configure/ipsec/ts-list/local/entry/protocol/range/id/id/id/icmp/icmp/port/port-range/port-range/begin-icmp-code
                                                                leaf begin-icmp-code {
                                                                    type uint16 {
                                                                        range "0..255";
                                                                    }
                                                                    mandatory true;
                                                                    description "Lower bound of the ICMP code range";
                                                                }

                                                                ///nokia-conf/configure/ipsec/ts-list/local/entry/protocol/range/id/id/id/icmp/icmp/port/port-range/port-range/end-icmp-type
                                                                leaf end-icmp-type {
                                                                    type uint16 {
                                                                        range "0..255";
                                                                    }
                                                                    mandatory true;
                                                                    description "Upper bound of the ICMP type range";
                                                                }

                                                                ///nokia-conf/configure/ipsec/ts-list/local/entry/protocol/range/id/id/id/icmp/icmp/port/port-range/port-range/end-icmp-code
                                                                leaf end-icmp-code {
                                                                    type uint16 {
                                                                        range "0..255";
                                                                    }
                                                                    mandatory true;
                                                                    description "Upper bound of the ICMP code range";
                                                                }

                                                            } // container port-range

                                                        }
                                                    }
                                                } // container icmp

                                            }
                                            ///nokia-conf/configure/ipsec/ts-list/local/entry/protocol/range/id/id/id/icmp6
                                            case icmp6 {

                                                ///nokia-conf/configure/ipsec/ts-list/local/entry/protocol/range/id/id/id/icmp6/icmp6
                                                container icmp6 {
                                                    description "Enter the icmp6 context";

                                                    ///nokia-conf/configure/ipsec/ts-list/local/entry/protocol/range/id/id/id/icmp6/icmp6/port
                                                    choice port {
                                                        ///nokia-conf/configure/ipsec/ts-list/local/entry/protocol/range/id/id/id/icmp6/icmp6/port/opaque-port
                                                        case opaque-port {

                                                            ///nokia-conf/configure/ipsec/ts-list/local/entry/protocol/range/id/id/id/icmp6/icmp6/port/opaque-port/opaque
                                                            leaf opaque {
                                                                type empty;
                                                                description "Support OPAQUE ports";
                                                            }

                                                        }
                                                        ///nokia-conf/configure/ipsec/ts-list/local/entry/protocol/range/id/id/id/icmp6/icmp6/port/port-range
                                                        case port-range {

                                                            ///nokia-conf/configure/ipsec/ts-list/local/entry/protocol/range/id/id/id/icmp6/icmp6/port/port-range/port-range
                                                            container port-range {
                                                                presence "Enable the port-range context";
                                                                description "Enable the port-range context";

                                                                ///nokia-conf/configure/ipsec/ts-list/local/entry/protocol/range/id/id/id/icmp6/icmp6/port/port-range/port-range/begin-icmp-type
                                                                leaf begin-icmp-type {
                                                                    type uint16 {
                                                                        range "0..255";
                                                                    }
                                                                    mandatory true;
                                                                    description "Lower bound of the ICMP type range";
                                                                }

                                                                ///nokia-conf/configure/ipsec/ts-list/local/entry/protocol/range/id/id/id/icmp6/icmp6/port/port-range/port-range/begin-icmp-code
                                                                leaf begin-icmp-code {
                                                                    type uint16 {
                                                                        range "0..255";
                                                                    }
                                                                    mandatory true;
                                                                    description "Lower bound of the ICMP code range";
                                                                }

                                                                ///nokia-conf/configure/ipsec/ts-list/local/entry/protocol/range/id/id/id/icmp6/icmp6/port/port-range/port-range/end-icmp-type
                                                                leaf end-icmp-type {
                                                                    type uint16 {
                                                                        range "0..255";
                                                                    }
                                                                    mandatory true;
                                                                    description "Upper bound of the ICMP type range";
                                                                }

                                                                ///nokia-conf/configure/ipsec/ts-list/local/entry/protocol/range/id/id/id/icmp6/icmp6/port/port-range/port-range/end-icmp-code
                                                                leaf end-icmp-code {
                                                                    type uint16 {
                                                                        range "0..255";
                                                                    }
                                                                    mandatory true;
                                                                    description "Upper bound of the ICMP code range";
                                                                }

                                                            } // container port-range

                                                        }
                                                    }
                                                } // container icmp6

                                            }
                                            ///nokia-conf/configure/ipsec/ts-list/local/entry/protocol/range/id/id/id/mipv6
                                            case mipv6 {

                                                ///nokia-conf/configure/ipsec/ts-list/local/entry/protocol/range/id/id/id/mipv6/mipv6
                                                container mipv6 {
                                                    description "Enter the mipv6 context";

                                                    ///nokia-conf/configure/ipsec/ts-list/local/entry/protocol/range/id/id/id/mipv6/mipv6/port
                                                    choice port {
                                                        ///nokia-conf/configure/ipsec/ts-list/local/entry/protocol/range/id/id/id/mipv6/mipv6/port/opaque-port
                                                        case opaque-port {

                                                            ///nokia-conf/configure/ipsec/ts-list/local/entry/protocol/range/id/id/id/mipv6/mipv6/port/opaque-port/opaque
                                                            leaf opaque {
                                                                type empty;
                                                                description "Support OPAQUE ports";
                                                            }

                                                        }
                                                        ///nokia-conf/configure/ipsec/ts-list/local/entry/protocol/range/id/id/id/mipv6/mipv6/port/port-range
                                                        case port-range {

                                                            ///nokia-conf/configure/ipsec/ts-list/local/entry/protocol/range/id/id/id/mipv6/mipv6/port/port-range/port-range
                                                            container port-range {
                                                                presence "Enable the port-range context";
                                                                description "Enable the port-range context";

                                                                ///nokia-conf/configure/ipsec/ts-list/local/entry/protocol/range/id/id/id/mipv6/mipv6/port/port-range/port-range/begin
                                                                leaf begin {
                                                                    type uint16 {
                                                                        range "0..255";
                                                                    }
                                                                    mandatory true;
                                                                    description "Lower bound of the port range";
                                                                }

                                                                ///nokia-conf/configure/ipsec/ts-list/local/entry/protocol/range/id/id/id/mipv6/mipv6/port/port-range/port-range/end
                                                                leaf end {
                                                                    type uint16 {
                                                                        range "0..255";
                                                                    }
                                                                    mandatory true;
                                                                    description "Upper bound of the port range";
                                                                }

                                                            } // container port-range

                                                        }
                                                    }
                                                } // container mipv6

                                            }
                                            ///nokia-conf/configure/ipsec/ts-list/local/entry/protocol/range/id/id/id/any
                                            case any {

                                                ///nokia-conf/configure/ipsec/ts-list/local/entry/protocol/range/id/id/id/any/protocol-id-with-any-port
                                                leaf protocol-id-with-any-port {
                                                    type union {
                                                        type enumeration {
                                                            enum icmp                           { value 1; }
                                                            enum tcp                            { value 6; }
                                                            enum udp                            { value 17; }
                                                            enum icmp6                          { value 58; }
                                                            enum sctp                           { value 132; }
                                                            enum mipv6                          { value 135; }
                                                        }
                                                        type int32 {
                                                            range "1..255";
                                                        }
                                                    }
                                                    description "Protocol ID that accepts any port value";
                                                }

                                            }
                                        }
                                    } // container id

                                }
                            }
                        } // container protocol

                    } // list entry

                } // container local

                ///nokia-conf/configure/ipsec/ts-list/remote
                container remote {
                    description "Enter the remote context";

                    ///nokia-conf/configure/ipsec/ts-list/remote/entry
                    list entry {
                        key "id";
                        description "Enter the entry list instance";

                        ///nokia-conf/configure/ipsec/ts-list/remote/entry/id
                        leaf id {
                            type uint32 {
                                range "1..32";
                            }
                            description "TS list entry ID";
                        }

                        ///nokia-conf/configure/ipsec/ts-list/remote/entry/apply-groups
                        leaf-list apply-groups {
                            type leafref {
                                path "../../../../../groups/group/name";
                            }
                            max-elements 8;
                            ordered-by user;
                            description "Apply a configuration group at this level";
                        }

                        ///nokia-conf/configure/ipsec/ts-list/remote/entry/apply-groups-exclude
                        leaf-list apply-groups-exclude {
                            type leafref {
                                path "../../../../../groups/group/name";
                            }
                            max-elements 8;
                            ordered-by user;
                            description "Exclude a configuration group at this level";
                        }

                        ///nokia-conf/configure/ipsec/ts-list/remote/entry/address
                        container address {
                            presence "Enable the address context";
                            description "Enable the address context";

                            ///nokia-conf/configure/ipsec/ts-list/remote/entry/address/address-range
                            choice address-range {
                                mandatory true;
                                ///nokia-conf/configure/ipsec/ts-list/remote/entry/address/address-range/prefix
                                case prefix {

                                    ///nokia-conf/configure/ipsec/ts-list/remote/entry/address/address-range/prefix/prefix
                                    leaf prefix {
                                        type types-sros:ip-prefix;
                                        description "IP prefix for address range in IKEv2 traffic selector";
                                    }

                                }
                                ///nokia-conf/configure/ipsec/ts-list/remote/entry/address/address-range/range
                                case range {

                                    ///nokia-conf/configure/ipsec/ts-list/remote/entry/address/address-range/range/range
                                    container range {
                                        presence "Enable the range context";
                                        description "Enable the range context";

                                        ///nokia-conf/configure/ipsec/ts-list/remote/entry/address/address-range/range/range/begin
                                        leaf begin {
                                            type types-sros:ip-address;
                                            mandatory true;
                                            description "Lower bound of the IP address range for the entry";
                                        }

                                        ///nokia-conf/configure/ipsec/ts-list/remote/entry/address/address-range/range/range/end
                                        leaf end {
                                            type types-sros:ip-address;
                                            mandatory true;
                                            description "Upper bound of the IP address range";
                                        }

                                    } // container range

                                }
                            }
                        } // container address

                        ///nokia-conf/configure/ipsec/ts-list/remote/entry/protocol
                        container protocol {
                            presence "Enable the protocol context";
                            description "Enable the protocol context";

                            ///nokia-conf/configure/ipsec/ts-list/remote/entry/protocol/range
                            choice range {
                                mandatory true;
                                ///nokia-conf/configure/ipsec/ts-list/remote/entry/protocol/range/any
                                case any {

                                    ///nokia-conf/configure/ipsec/ts-list/remote/entry/protocol/range/any/any
                                    leaf any {
                                        type empty;
                                        description "Match any protocol ID";
                                    }

                                }
                                ///nokia-conf/configure/ipsec/ts-list/remote/entry/protocol/range/id
                                case id {

                                    ///nokia-conf/configure/ipsec/ts-list/remote/entry/protocol/range/id/id
                                    container id {
                                        presence "Enable the id context";
                                        description "Enable the id context";

                                        ///nokia-conf/configure/ipsec/ts-list/remote/entry/protocol/range/id/id/id
                                        choice id {
                                            mandatory true;
                                            ///nokia-conf/configure/ipsec/ts-list/remote/entry/protocol/range/id/id/id/tcp
                                            case tcp {

                                                ///nokia-conf/configure/ipsec/ts-list/remote/entry/protocol/range/id/id/id/tcp/tcp
                                                container tcp {
                                                    description "Enter the tcp context";

                                                    ///nokia-conf/configure/ipsec/ts-list/remote/entry/protocol/range/id/id/id/tcp/tcp/port
                                                    choice port {
                                                        ///nokia-conf/configure/ipsec/ts-list/remote/entry/protocol/range/id/id/id/tcp/tcp/port/opaque-port
                                                        case opaque-port {

                                                            ///nokia-conf/configure/ipsec/ts-list/remote/entry/protocol/range/id/id/id/tcp/tcp/port/opaque-port/opaque
                                                            leaf opaque {
                                                                type empty;
                                                                description "Support OPAQUE ports";
                                                            }

                                                        }
                                                        ///nokia-conf/configure/ipsec/ts-list/remote/entry/protocol/range/id/id/id/tcp/tcp/port/port-range
                                                        case port-range {

                                                            ///nokia-conf/configure/ipsec/ts-list/remote/entry/protocol/range/id/id/id/tcp/tcp/port/port-range/port-range
                                                            container port-range {
                                                                presence "Enable the port-range context";
                                                                description "Enable the port-range context";

                                                                ///nokia-conf/configure/ipsec/ts-list/remote/entry/protocol/range/id/id/id/tcp/tcp/port/port-range/port-range/begin
                                                                leaf begin {
                                                                    type uint32 {
                                                                        range "0..65535";
                                                                    }
                                                                    mandatory true;
                                                                    description "Lower bound of the port range";
                                                                }

                                                                ///nokia-conf/configure/ipsec/ts-list/remote/entry/protocol/range/id/id/id/tcp/tcp/port/port-range/port-range/end
                                                                leaf end {
                                                                    type uint32 {
                                                                        range "0..65535";
                                                                    }
                                                                    mandatory true;
                                                                    description "Upper bound of the port range";
                                                                }

                                                            } // container port-range

                                                        }
                                                    }
                                                } // container tcp

                                            }
                                            ///nokia-conf/configure/ipsec/ts-list/remote/entry/protocol/range/id/id/id/udp
                                            case udp {

                                                ///nokia-conf/configure/ipsec/ts-list/remote/entry/protocol/range/id/id/id/udp/udp
                                                container udp {
                                                    description "Enter the udp context";

                                                    ///nokia-conf/configure/ipsec/ts-list/remote/entry/protocol/range/id/id/id/udp/udp/port
                                                    choice port {
                                                        ///nokia-conf/configure/ipsec/ts-list/remote/entry/protocol/range/id/id/id/udp/udp/port/opaque-port
                                                        case opaque-port {

                                                            ///nokia-conf/configure/ipsec/ts-list/remote/entry/protocol/range/id/id/id/udp/udp/port/opaque-port/opaque
                                                            leaf opaque {
                                                                type empty;
                                                                description "Support OPAQUE ports";
                                                            }

                                                        }
                                                        ///nokia-conf/configure/ipsec/ts-list/remote/entry/protocol/range/id/id/id/udp/udp/port/port-range
                                                        case port-range {

                                                            ///nokia-conf/configure/ipsec/ts-list/remote/entry/protocol/range/id/id/id/udp/udp/port/port-range/port-range
                                                            container port-range {
                                                                presence "Enable the port-range context";
                                                                description "Enable the port-range context";

                                                                ///nokia-conf/configure/ipsec/ts-list/remote/entry/protocol/range/id/id/id/udp/udp/port/port-range/port-range/begin
                                                                leaf begin {
                                                                    type uint32 {
                                                                        range "0..65535";
                                                                    }
                                                                    mandatory true;
                                                                    description "Lower bound of the port range";
                                                                }

                                                                ///nokia-conf/configure/ipsec/ts-list/remote/entry/protocol/range/id/id/id/udp/udp/port/port-range/port-range/end
                                                                leaf end {
                                                                    type uint32 {
                                                                        range "0..65535";
                                                                    }
                                                                    mandatory true;
                                                                    description "Upper bound of the port range";
                                                                }

                                                            } // container port-range

                                                        }
                                                    }
                                                } // container udp

                                            }
                                            ///nokia-conf/configure/ipsec/ts-list/remote/entry/protocol/range/id/id/id/sctp
                                            case sctp {

                                                ///nokia-conf/configure/ipsec/ts-list/remote/entry/protocol/range/id/id/id/sctp/sctp
                                                container sctp {
                                                    description "Enter the sctp context";

                                                    ///nokia-conf/configure/ipsec/ts-list/remote/entry/protocol/range/id/id/id/sctp/sctp/port
                                                    choice port {
                                                        ///nokia-conf/configure/ipsec/ts-list/remote/entry/protocol/range/id/id/id/sctp/sctp/port/opaque-port
                                                        case opaque-port {

                                                            ///nokia-conf/configure/ipsec/ts-list/remote/entry/protocol/range/id/id/id/sctp/sctp/port/opaque-port/opaque
                                                            leaf opaque {
                                                                type empty;
                                                                description "Support OPAQUE ports";
                                                            }

                                                        }
                                                        ///nokia-conf/configure/ipsec/ts-list/remote/entry/protocol/range/id/id/id/sctp/sctp/port/port-range
                                                        case port-range {

                                                            ///nokia-conf/configure/ipsec/ts-list/remote/entry/protocol/range/id/id/id/sctp/sctp/port/port-range/port-range
                                                            container port-range {
                                                                presence "Enable the port-range context";
                                                                description "Enable the port-range context";

                                                                ///nokia-conf/configure/ipsec/ts-list/remote/entry/protocol/range/id/id/id/sctp/sctp/port/port-range/port-range/begin
                                                                leaf begin {
                                                                    type uint32 {
                                                                        range "0..65535";
                                                                    }
                                                                    mandatory true;
                                                                    description "Lower bound of the port range";
                                                                }

                                                                ///nokia-conf/configure/ipsec/ts-list/remote/entry/protocol/range/id/id/id/sctp/sctp/port/port-range/port-range/end
                                                                leaf end {
                                                                    type uint32 {
                                                                        range "0..65535";
                                                                    }
                                                                    mandatory true;
                                                                    description "Upper bound of the port range";
                                                                }

                                                            } // container port-range

                                                        }
                                                    }
                                                } // container sctp

                                            }
                                            ///nokia-conf/configure/ipsec/ts-list/remote/entry/protocol/range/id/id/id/icmp
                                            case icmp {

                                                ///nokia-conf/configure/ipsec/ts-list/remote/entry/protocol/range/id/id/id/icmp/icmp
                                                container icmp {
                                                    description "Enter the icmp context";

                                                    ///nokia-conf/configure/ipsec/ts-list/remote/entry/protocol/range/id/id/id/icmp/icmp/port
                                                    choice port {
                                                        ///nokia-conf/configure/ipsec/ts-list/remote/entry/protocol/range/id/id/id/icmp/icmp/port/opaque-port
                                                        case opaque-port {

                                                            ///nokia-conf/configure/ipsec/ts-list/remote/entry/protocol/range/id/id/id/icmp/icmp/port/opaque-port/opaque
                                                            leaf opaque {
                                                                type empty;
                                                                description "Support OPAQUE ports";
                                                            }

                                                        }
                                                        ///nokia-conf/configure/ipsec/ts-list/remote/entry/protocol/range/id/id/id/icmp/icmp/port/port-range
                                                        case port-range {

                                                            ///nokia-conf/configure/ipsec/ts-list/remote/entry/protocol/range/id/id/id/icmp/icmp/port/port-range/port-range
                                                            container port-range {
                                                                presence "Enable the port-range context";
                                                                description "Enable the port-range context";

                                                                ///nokia-conf/configure/ipsec/ts-list/remote/entry/protocol/range/id/id/id/icmp/icmp/port/port-range/port-range/begin-icmp-type
                                                                leaf begin-icmp-type {
                                                                    type uint16 {
                                                                        range "0..255";
                                                                    }
                                                                    mandatory true;
                                                                    description "Lower bound of the ICMP type range";
                                                                }

                                                                ///nokia-conf/configure/ipsec/ts-list/remote/entry/protocol/range/id/id/id/icmp/icmp/port/port-range/port-range/begin-icmp-code
                                                                leaf begin-icmp-code {
                                                                    type uint16 {
                                                                        range "0..255";
                                                                    }
                                                                    mandatory true;
                                                                    description "Lower bound of the ICMP code range";
                                                                }

                                                                ///nokia-conf/configure/ipsec/ts-list/remote/entry/protocol/range/id/id/id/icmp/icmp/port/port-range/port-range/end-icmp-type
                                                                leaf end-icmp-type {
                                                                    type uint16 {
                                                                        range "0..255";
                                                                    }
                                                                    mandatory true;
                                                                    description "Upper bound of the ICMP type range";
                                                                }

                                                                ///nokia-conf/configure/ipsec/ts-list/remote/entry/protocol/range/id/id/id/icmp/icmp/port/port-range/port-range/end-icmp-code
                                                                leaf end-icmp-code {
                                                                    type uint16 {
                                                                        range "0..255";
                                                                    }
                                                                    mandatory true;
                                                                    description "Upper bound of the ICMP code range";
                                                                }

                                                            } // container port-range

                                                        }
                                                    }
                                                } // container icmp

                                            }
                                            ///nokia-conf/configure/ipsec/ts-list/remote/entry/protocol/range/id/id/id/icmp6
                                            case icmp6 {

                                                ///nokia-conf/configure/ipsec/ts-list/remote/entry/protocol/range/id/id/id/icmp6/icmp6
                                                container icmp6 {
                                                    description "Enter the icmp6 context";

                                                    ///nokia-conf/configure/ipsec/ts-list/remote/entry/protocol/range/id/id/id/icmp6/icmp6/port
                                                    choice port {
                                                        ///nokia-conf/configure/ipsec/ts-list/remote/entry/protocol/range/id/id/id/icmp6/icmp6/port/opaque-port
                                                        case opaque-port {

                                                            ///nokia-conf/configure/ipsec/ts-list/remote/entry/protocol/range/id/id/id/icmp6/icmp6/port/opaque-port/opaque
                                                            leaf opaque {
                                                                type empty;
                                                                description "Support OPAQUE ports";
                                                            }

                                                        }
                                                        ///nokia-conf/configure/ipsec/ts-list/remote/entry/protocol/range/id/id/id/icmp6/icmp6/port/port-range
                                                        case port-range {

                                                            ///nokia-conf/configure/ipsec/ts-list/remote/entry/protocol/range/id/id/id/icmp6/icmp6/port/port-range/port-range
                                                            container port-range {
                                                                presence "Enable the port-range context";
                                                                description "Enable the port-range context";

                                                                ///nokia-conf/configure/ipsec/ts-list/remote/entry/protocol/range/id/id/id/icmp6/icmp6/port/port-range/port-range/begin-icmp-type
                                                                leaf begin-icmp-type {
                                                                    type uint16 {
                                                                        range "0..255";
                                                                    }
                                                                    mandatory true;
                                                                    description "Lower bound of the ICMP type range";
                                                                }

                                                                ///nokia-conf/configure/ipsec/ts-list/remote/entry/protocol/range/id/id/id/icmp6/icmp6/port/port-range/port-range/begin-icmp-code
                                                                leaf begin-icmp-code {
                                                                    type uint16 {
                                                                        range "0..255";
                                                                    }
                                                                    mandatory true;
                                                                    description "Lower bound of the ICMP code range";
                                                                }

                                                                ///nokia-conf/configure/ipsec/ts-list/remote/entry/protocol/range/id/id/id/icmp6/icmp6/port/port-range/port-range/end-icmp-type
                                                                leaf end-icmp-type {
                                                                    type uint16 {
                                                                        range "0..255";
                                                                    }
                                                                    mandatory true;
                                                                    description "Upper bound of the ICMP type range";
                                                                }

                                                                ///nokia-conf/configure/ipsec/ts-list/remote/entry/protocol/range/id/id/id/icmp6/icmp6/port/port-range/port-range/end-icmp-code
                                                                leaf end-icmp-code {
                                                                    type uint16 {
                                                                        range "0..255";
                                                                    }
                                                                    mandatory true;
                                                                    description "Upper bound of the ICMP code range";
                                                                }

                                                            } // container port-range

                                                        }
                                                    }
                                                } // container icmp6

                                            }
                                            ///nokia-conf/configure/ipsec/ts-list/remote/entry/protocol/range/id/id/id/mipv6
                                            case mipv6 {

                                                ///nokia-conf/configure/ipsec/ts-list/remote/entry/protocol/range/id/id/id/mipv6/mipv6
                                                container mipv6 {
                                                    description "Enter the mipv6 context";

                                                    ///nokia-conf/configure/ipsec/ts-list/remote/entry/protocol/range/id/id/id/mipv6/mipv6/port
                                                    choice port {
                                                        ///nokia-conf/configure/ipsec/ts-list/remote/entry/protocol/range/id/id/id/mipv6/mipv6/port/opaque-port
                                                        case opaque-port {

                                                            ///nokia-conf/configure/ipsec/ts-list/remote/entry/protocol/range/id/id/id/mipv6/mipv6/port/opaque-port/opaque
                                                            leaf opaque {
                                                                type empty;
                                                                description "Support OPAQUE ports";
                                                            }

                                                        }
                                                        ///nokia-conf/configure/ipsec/ts-list/remote/entry/protocol/range/id/id/id/mipv6/mipv6/port/port-range
                                                        case port-range {

                                                            ///nokia-conf/configure/ipsec/ts-list/remote/entry/protocol/range/id/id/id/mipv6/mipv6/port/port-range/port-range
                                                            container port-range {
                                                                presence "Enable the port-range context";
                                                                description "Enable the port-range context";

                                                                ///nokia-conf/configure/ipsec/ts-list/remote/entry/protocol/range/id/id/id/mipv6/mipv6/port/port-range/port-range/begin
                                                                leaf begin {
                                                                    type uint16 {
                                                                        range "0..255";
                                                                    }
                                                                    mandatory true;
                                                                    description "Lower bound of the port range";
                                                                }

                                                                ///nokia-conf/configure/ipsec/ts-list/remote/entry/protocol/range/id/id/id/mipv6/mipv6/port/port-range/port-range/end
                                                                leaf end {
                                                                    type uint16 {
                                                                        range "0..255";
                                                                    }
                                                                    mandatory true;
                                                                    description "Upper bound of the port range";
                                                                }

                                                            } // container port-range

                                                        }
                                                    }
                                                } // container mipv6

                                            }
                                            ///nokia-conf/configure/ipsec/ts-list/remote/entry/protocol/range/id/id/id/any
                                            case any {

                                                ///nokia-conf/configure/ipsec/ts-list/remote/entry/protocol/range/id/id/id/any/protocol-id-with-any-port
                                                leaf protocol-id-with-any-port {
                                                    type union {
                                                        type enumeration {
                                                            enum icmp                           { value 1; }
                                                            enum tcp                            { value 6; }
                                                            enum udp                            { value 17; }
                                                            enum icmp6                          { value 58; }
                                                            enum sctp                           { value 132; }
                                                            enum mipv6                          { value 135; }
                                                        }
                                                        type int32 {
                                                            range "1..255";
                                                        }
                                                    }
                                                    description "Protocol ID that accepts any port value";
                                                }

                                            }
                                        }
                                    } // container id

                                }
                            }
                        } // container protocol

                    } // list entry

                } // container remote

            } // list ts-list

            ///nokia-conf/configure/ipsec/tunnel-template
            list tunnel-template {
                key "id";
                max-elements 2048;
                description "Enter the tunnel-template list instance";

                ///nokia-conf/configure/ipsec/tunnel-template/id
                leaf id {
                    type types-ipsec:tunnel-template-id;
                    description "Tunnel template ID";
                }

                ///nokia-conf/configure/ipsec/tunnel-template/description
                leaf description {
                    type types-sros:description;
                    description "Text description";
                }

                ///nokia-conf/configure/ipsec/tunnel-template/clear-df-bit
                leaf clear-df-bit {
                    type boolean;
                    default "false";
                    description "Clear the Do-not-Fragment (DF) bit";
                }

                ///nokia-conf/configure/ipsec/tunnel-template/encapsulated-ip-mtu
                leaf encapsulated-ip-mtu {
                    type uint32 {
                        range "512..9000";
                    }
                    units "octets";
                    description "Maximum size of the encapsulated tunnel packet";
                }

                ///nokia-conf/configure/ipsec/tunnel-template/ip-mtu
                leaf ip-mtu {
                    type uint32 {
                        range "512..9000";
                    }
                    units "octets";
                    description "Maximum size of the IP MTU for the payload packets";
                }

                ///nokia-conf/configure/ipsec/tunnel-template/private-tcp-mss-adjust
                leaf private-tcp-mss-adjust {
                    type int32 {
                        range "512..9000";
                    }
                    units "octets";
                    description "New TCP MSS value on the private side";
                }

                ///nokia-conf/configure/ipsec/tunnel-template/public-tcp-mss-adjust
                leaf public-tcp-mss-adjust {
                    type union {
                        type uint32 {
                            range "512..9000";
                        }
                        type enumeration {
                            enum auto                           { value 0; }
                        }
                    }
                    units "octets";
                    description "New TCP MSS value on the public side";
                }

                ///nokia-conf/configure/ipsec/tunnel-template/replay-window
                leaf replay-window {
                    type uint32 {
                        range "32|64|128|256|512";
                    }
                    description "Anti-replay window size for the tunnel template";
                }

                ///nokia-conf/configure/ipsec/tunnel-template/sp-reverse-route
                leaf sp-reverse-route {
                    type enumeration {
                        enum none                           { value 0; }
                        enum use-security-policy            { value 1; }
                    }
                    default "none";
                    description "Reverse route creation method in private service";
                }

                ///nokia-conf/configure/ipsec/tunnel-template/ipsec-transform
                leaf-list ipsec-transform {
                    type leafref {
                        path "../../ipsec-transform/id";
                    }
                    max-elements 4;
                    description "IPsec transform ID for the tunnel template";
                }

                ///nokia-conf/configure/ipsec/tunnel-template/ignore-default-route
                leaf ignore-default-route {
                    type boolean;
                    default "false";
                    description "Ignore any full range traffic selector in TSi";
                }

                ///nokia-conf/configure/ipsec/tunnel-template/copy-traffic-class-upon-decapsulation
                leaf copy-traffic-class-upon-decapsulation {
                    type boolean;
                    default "false";
                    description "Enable traffic class copy upon decapsulation";
                }

                ///nokia-conf/configure/ipsec/tunnel-template/propagate-pmtu-v4
                leaf propagate-pmtu-v4 {
                    type boolean;
                    default "true";
                    description "Enable propagation of the path MTU to IPv4 hosts";
                }

                ///nokia-conf/configure/ipsec/tunnel-template/propagate-pmtu-v6
                leaf propagate-pmtu-v6 {
                    type boolean;
                    default "true";
                    description "Enable propagation of the path MTU to IPv6 hosts";
                }

                ///nokia-conf/configure/ipsec/tunnel-template/pmtu-discovery-aging
                leaf pmtu-discovery-aging {
                    type uint32 {
                        range "900..3600";
                    }
                    units "seconds";
                    default "900";
                    description "Aging out time of the learned path MTU";
                }

                ///nokia-conf/configure/ipsec/tunnel-template/apply-groups
                leaf-list apply-groups {
                    type leafref {
                        path "../../../groups/group/name";
                    }
                    max-elements 8;
                    ordered-by user;
                    description "Apply a configuration group at this level";
                }

                ///nokia-conf/configure/ipsec/tunnel-template/apply-groups-exclude
                leaf-list apply-groups-exclude {
                    type leafref {
                        path "../../../groups/group/name";
                    }
                    max-elements 8;
                    ordered-by user;
                    description "Exclude a configuration group at this level";
                }

                ///nokia-conf/configure/ipsec/tunnel-template/icmp6-generation
                container icmp6-generation {
                    description "Enter the icmp6-generation context";

                    ///nokia-conf/configure/ipsec/tunnel-template/icmp6-generation/pkt-too-big
                    container pkt-too-big {
                        description "Enter the pkt-too-big context";

                        ///nokia-conf/configure/ipsec/tunnel-template/icmp6-generation/pkt-too-big/admin-state
                        leaf admin-state {
                            type types-sros:admin-state;
                            default "enable";
                            description "Administrative state of Packet Too Big message sends";
                        }

                        ///nokia-conf/configure/ipsec/tunnel-template/icmp6-generation/pkt-too-big/interval
                        leaf interval {
                            type uint32 {
                                range "1..60";
                            }
                            units "seconds";
                            default "10";
                            description "Maximum interval during which PTB messages can be sent";
                        }

                        ///nokia-conf/configure/ipsec/tunnel-template/icmp6-generation/pkt-too-big/message-count
                        leaf message-count {
                            type uint32 {
                                range "10..1000";
                            }
                            default "100";
                            description "Max ICMPv6 messages that can be sent during interval";
                        }

                    } // container pkt-too-big

                } // container icmp6-generation

                ///nokia-conf/configure/ipsec/tunnel-template/icmp-generation
                container icmp-generation {
                    description "Enter the icmp-generation context";

                    ///nokia-conf/configure/ipsec/tunnel-template/icmp-generation/frag-required
                    container frag-required {
                        description "Enter the frag-required context";

                        ///nokia-conf/configure/ipsec/tunnel-template/icmp-generation/frag-required/admin-state
                        leaf admin-state {
                            type types-sros:admin-state;
                            default "enable";
                            description "Administrative state of sending ICMP messages";
                        }

                        ///nokia-conf/configure/ipsec/tunnel-template/icmp-generation/frag-required/message-count
                        leaf message-count {
                            type uint32 {
                                range "10..1000";
                            }
                            default "100";
                            description "Maximum number of ICMP messages that can be sent";
                        }

                        ///nokia-conf/configure/ipsec/tunnel-template/icmp-generation/frag-required/interval
                        leaf interval {
                            type uint32 {
                                range "1..60";
                            }
                            units "seconds";
                            default "10";
                            description "Interval for sending ICMP messages";
                        }

                    } // container frag-required

                } // container icmp-generation

            } // list tunnel-template

            ///nokia-conf/configure/ipsec/trust-anchor-profile
            list trust-anchor-profile {
                key "name";
                max-elements 10128;
                description "Enter the trust-anchor-profile list instance";

                ///nokia-conf/configure/ipsec/trust-anchor-profile/name
                leaf name {
                    type types-sros:named-item;
                    description "Trust anchor profile name for IPsec tunnel or gateway";
                }

                ///nokia-conf/configure/ipsec/trust-anchor-profile/apply-groups
                leaf-list apply-groups {
                    type leafref {
                        path "../../../groups/group/name";
                    }
                    max-elements 8;
                    ordered-by user;
                    description "Apply a configuration group at this level";
                }

                ///nokia-conf/configure/ipsec/trust-anchor-profile/apply-groups-exclude
                leaf-list apply-groups-exclude {
                    type leafref {
                        path "../../../groups/group/name";
                    }
                    max-elements 8;
                    ordered-by user;
                    description "Exclude a configuration group at this level";
                }

                ///nokia-conf/configure/ipsec/trust-anchor-profile/trust-anchor
                list trust-anchor {
                    key "ca-profile";
                    max-elements 8;
                    description "Add a list entry for trust-anchor";

                    ///nokia-conf/configure/ipsec/trust-anchor-profile/trust-anchor/ca-profile
                    leaf ca-profile {
                        type leafref {
                            path "../../../../system/security/pki/ca-profile/ca-profile-name";
                        }
                        description "Name of the CA profile as a trust anchor profile";
                    }

                } // list trust-anchor

            } // list trust-anchor-profile

            ///nokia-conf/configure/ipsec/ipsec-transport-mode-profile
            list ipsec-transport-mode-profile {
                key "name";
                description "Enter the ipsec-transport-mode-profile list instance";

                ///nokia-conf/configure/ipsec/ipsec-transport-mode-profile/name
                leaf name {
                    type types-sros:named-item;
                    description "IPsec transport mode profile name string";
                }

                ///nokia-conf/configure/ipsec/ipsec-transport-mode-profile/description
                leaf description {
                    type types-sros:description;
                    description "Text description";
                }

                ///nokia-conf/configure/ipsec/ipsec-transport-mode-profile/replay-window
                leaf replay-window {
                    type uint32 {
                        range "32|64|128|256|512";
                    }
                    units "packets";
                    description "Anti-replay window size";
                }

                ///nokia-conf/configure/ipsec/ipsec-transport-mode-profile/apply-groups
                leaf-list apply-groups {
                    type leafref {
                        path "../../../groups/group/name";
                    }
                    max-elements 8;
                    ordered-by user;
                    description "Apply a configuration group at this level";
                }

                ///nokia-conf/configure/ipsec/ipsec-transport-mode-profile/apply-groups-exclude
                leaf-list apply-groups-exclude {
                    type leafref {
                        path "../../../groups/group/name";
                    }
                    max-elements 8;
                    ordered-by user;
                    description "Exclude a configuration group at this level";
                }

                ///nokia-conf/configure/ipsec/ipsec-transport-mode-profile/key-exchange
                container key-exchange {
                    description "Enter the key-exchange context";

                    ///nokia-conf/configure/ipsec/ipsec-transport-mode-profile/key-exchange/dynamic
                    container dynamic {
                        description "Enter the dynamic context";

                        ///nokia-conf/configure/ipsec/ipsec-transport-mode-profile/key-exchange/dynamic/auto-establish
                        leaf auto-establish {
                            type boolean;
                            default "false";
                            description "Attempt to establish a phase 1 exchange automatically";
                        }

                        ///nokia-conf/configure/ipsec/ipsec-transport-mode-profile/key-exchange/dynamic/ike-policy
                        leaf ike-policy {
                            type leafref {
                                path "../../../../ike-policy/id";
                            }
                            description "IKE policy ID";
                        }

                        ///nokia-conf/configure/ipsec/ipsec-transport-mode-profile/key-exchange/dynamic/ipsec-transform
                        leaf-list ipsec-transform {
                            type leafref {
                                path "../../../../ipsec-transform/id";
                            }
                            max-elements 4;
                            description "IPsec transform IDs used by the dynamic key";
                        }

                        ///nokia-conf/configure/ipsec/ipsec-transport-mode-profile/key-exchange/dynamic/pre-shared-key
                        leaf pre-shared-key {
                            type types-sros:encrypted-leaf {
                                length "1..115";
                            }
                            description "Pre-shared key for IKE authentication";
                        }

                        ///nokia-conf/configure/ipsec/ipsec-transport-mode-profile/key-exchange/dynamic/cert
                        container cert {
                            description "Enter the cert context";

                            ///nokia-conf/configure/ipsec/ipsec-transport-mode-profile/key-exchange/dynamic/cert/cert-profile
                            leaf cert-profile {
                                type leafref {
                                    path "../../../../../cert-profile/name";
                                }
                                description "Certificate profile name";
                            }

                            ///nokia-conf/configure/ipsec/ipsec-transport-mode-profile/key-exchange/dynamic/cert/trust-anchor-profile
                            leaf trust-anchor-profile {
                                type leafref {
                                    path "../../../../../trust-anchor-profile/name";
                                }
                                description "Trust anchor profile name";
                            }

                            ///nokia-conf/configure/ipsec/ipsec-transport-mode-profile/key-exchange/dynamic/cert/status-verify
                            container status-verify {
                                description "Enter the status-verify context";

                                ///nokia-conf/configure/ipsec/ipsec-transport-mode-profile/key-exchange/dynamic/cert/status-verify/default-result
                                leaf default-result {
                                    type enumeration {
                                        enum revoked                        { value 0; }
                                        enum good                           { value 1; }
                                    }
                                    default "revoked";
                                    description "Default result for Certificate Status Verification";
                                }

                                ///nokia-conf/configure/ipsec/ipsec-transport-mode-profile/key-exchange/dynamic/cert/status-verify/primary
                                leaf primary {
                                    type types-ipsec:cert-revocation-status;
                                    default "crl";
                                    description "Primary method of CSV to verify the revocation status";
                                }

                                ///nokia-conf/configure/ipsec/ipsec-transport-mode-profile/key-exchange/dynamic/cert/status-verify/secondary
                                leaf secondary {
                                    type types-ipsec:cert-revocation-status-with-none;
                                    default "none";
                                    description "Secondary method used to verify certificate revocation";
                                }

                            } // container status-verify

                        } // container cert

                        ///nokia-conf/configure/ipsec/ipsec-transport-mode-profile/key-exchange/dynamic/id
                        container id {
                            description "Enter the id context";

                            ///nokia-conf/configure/ipsec/ipsec-transport-mode-profile/key-exchange/dynamic/id/id
                            choice id {
                                ///nokia-conf/configure/ipsec/ipsec-transport-mode-profile/key-exchange/dynamic/id/id/ipv4
                                case ipv4 {

                                    ///nokia-conf/configure/ipsec/ipsec-transport-mode-profile/key-exchange/dynamic/id/id/ipv4/ipv4
                                    leaf ipv4 {
                                        type types-sros:ipv4-unicast-address;
                                        description "IPv4 as the local ID type";
                                    }

                                }
                                ///nokia-conf/configure/ipsec/ipsec-transport-mode-profile/key-exchange/dynamic/id/id/ipv6
                                case ipv6 {

                                    ///nokia-conf/configure/ipsec/ipsec-transport-mode-profile/key-exchange/dynamic/id/id/ipv6/ipv6
                                    leaf ipv6 {
                                        type types-sros:ip-address;
                                        description "IPv6 used as the local IKE ID type";
                                    }

                                }
                                ///nokia-conf/configure/ipsec/ipsec-transport-mode-profile/key-exchange/dynamic/id/id/fqdn
                                case fqdn {

                                    ///nokia-conf/configure/ipsec/ipsec-transport-mode-profile/key-exchange/dynamic/id/id/fqdn/fqdn
                                    leaf fqdn {
                                        type types-sros:fully-qualified-domain-name;
                                        description "FQDN used as the local ID IKE type";
                                    }

                                }
                            }
                        } // container id

                    } // container dynamic

                } // container key-exchange

                ///nokia-conf/configure/ipsec/ipsec-transport-mode-profile/max-history-key-records
                container max-history-key-records {
                    description "Enter the max-history-key-records context";

                    ///nokia-conf/configure/ipsec/ipsec-transport-mode-profile/max-history-key-records/ike
                    leaf ike {
                        type uint32 {
                            range "1..3";
                        }
                        description "Maximum number of historical IKE key records";
                    }

                    ///nokia-conf/configure/ipsec/ipsec-transport-mode-profile/max-history-key-records/esp
                    leaf esp {
                        type uint32 {
                            range "1..48";
                        }
                        description "Maximum number of recent records";
                    }

                } // container max-history-key-records

            } // list ipsec-transport-mode-profile

            ///nokia-conf/configure/ipsec/radius
            container radius {
                description "Enter the radius context";

                ///nokia-conf/configure/ipsec/radius/accounting-policy
                list accounting-policy {
                    key "name";
                    max-elements 100;
                    description "Enter the accounting-policy list instance";

                    ///nokia-conf/configure/ipsec/radius/accounting-policy/name
                    leaf name {
                        type types-sros:named-item;
                        description "RADIUS accounting policy name";
                    }

                    ///nokia-conf/configure/ipsec/radius/accounting-policy/radius-server-policy
                    leaf radius-server-policy {
                        type leafref {
                            path "../../../../aaa/radius/server-policy/name";
                        }
                        description "Referenced RADIUS server policy";
                    }

                    ///nokia-conf/configure/ipsec/radius/accounting-policy/apply-groups
                    leaf-list apply-groups {
                        type leafref {
                            path "../../../../groups/group/name";
                        }
                        max-elements 8;
                        ordered-by user;
                        description "Apply a configuration group at this level";
                    }

                    ///nokia-conf/configure/ipsec/radius/accounting-policy/apply-groups-exclude
                    leaf-list apply-groups-exclude {
                        type leafref {
                            path "../../../../groups/group/name";
                        }
                        max-elements 8;
                        ordered-by user;
                        description "Exclude a configuration group at this level";
                    }

                    ///nokia-conf/configure/ipsec/radius/accounting-policy/update-interval
                    container update-interval {
                        description "Enter the update-interval context";

                        ///nokia-conf/configure/ipsec/radius/accounting-policy/update-interval/value
                        leaf value {
                            type int32 {
                                range "0|5..259200";
                            }
                            units "minutes";
                            default "10";
                            description "Update interval of the RADIUS accounting data";
                        }

                        ///nokia-conf/configure/ipsec/radius/accounting-policy/update-interval/jitter
                        leaf jitter {
                            type int32 {
                                range "0..3600";
                            }
                            units "seconds";
                            description "Jitter interval for sending each interim-update packet";
                        }

                    } // container update-interval

                    ///nokia-conf/configure/ipsec/radius/accounting-policy/include-radius-attribute
                    container include-radius-attribute {
                        description "Enter the include-radius-attribute context";

                        ///nokia-conf/configure/ipsec/radius/accounting-policy/include-radius-attribute/called-station-id
                        leaf called-station-id {
                            type boolean;
                            default "false";
                            description "Include the Called-Station-Id attribute";
                        }

                        ///nokia-conf/configure/ipsec/radius/accounting-policy/include-radius-attribute/calling-station-id
                        leaf calling-station-id {
                            type boolean;
                            default "false";
                            description "Include the Calling-Station-Id attribute";
                        }

                        ///nokia-conf/configure/ipsec/radius/accounting-policy/include-radius-attribute/nas-identifier
                        leaf nas-identifier {
                            type boolean;
                            default "false";
                            description "Include the NAS-Identifier attribute";
                        }

                        ///nokia-conf/configure/ipsec/radius/accounting-policy/include-radius-attribute/nas-ip-addr
                        leaf nas-ip-addr {
                            type boolean;
                            default "false";
                            description "Include the NAS-IP-Address attribute";
                        }

                        ///nokia-conf/configure/ipsec/radius/accounting-policy/include-radius-attribute/nas-port-id
                        leaf nas-port-id {
                            type boolean;
                            default "false";
                            description "Include the NAS-Port-Id attribute";
                        }

                        ///nokia-conf/configure/ipsec/radius/accounting-policy/include-radius-attribute/acct-stats
                        leaf acct-stats {
                            type boolean;
                            default "false";
                            description "Include accounting attributes in RADIUS packets";
                        }

                        ///nokia-conf/configure/ipsec/radius/accounting-policy/include-radius-attribute/framed-ip-addr
                        leaf framed-ip-addr {
                            type boolean;
                            default "false";
                            description "Include the Framed-IP-Address attribute";
                        }

                        ///nokia-conf/configure/ipsec/radius/accounting-policy/include-radius-attribute/framed-ipv6-prefix
                        leaf framed-ipv6-prefix {
                            type boolean;
                            default "false";
                            description "Include the Framed-IPv6-Prefix attribute";
                        }

                    } // container include-radius-attribute

                } // list accounting-policy

                ///nokia-conf/configure/ipsec/radius/authentication-policy
                list authentication-policy {
                    key "name";
                    max-elements 100;
                    description "Enter the authentication-policy list instance";

                    ///nokia-conf/configure/ipsec/radius/authentication-policy/name
                    leaf name {
                        type types-sros:named-item;
                        description "RADIUS authentication policy name";
                    }

                    ///nokia-conf/configure/ipsec/radius/authentication-policy/radius-server-policy
                    leaf radius-server-policy {
                        type leafref {
                            path "../../../../aaa/radius/server-policy/name";
                        }
                        description "Referenced RADIUS server policy";
                    }

                    ///nokia-conf/configure/ipsec/radius/authentication-policy/password
                    leaf password {
                        type types-sros:encrypted-leaf {
                            length "1..115";
                        }
                        description "Password used in RADIUS access requests";
                    }

                    ///nokia-conf/configure/ipsec/radius/authentication-policy/apply-groups
                    leaf-list apply-groups {
                        type leafref {
                            path "../../../../groups/group/name";
                        }
                        max-elements 8;
                        ordered-by user;
                        description "Apply a configuration group at this level";
                    }

                    ///nokia-conf/configure/ipsec/radius/authentication-policy/apply-groups-exclude
                    leaf-list apply-groups-exclude {
                        type leafref {
                            path "../../../../groups/group/name";
                        }
                        max-elements 8;
                        ordered-by user;
                        description "Exclude a configuration group at this level";
                    }

                    ///nokia-conf/configure/ipsec/radius/authentication-policy/include-radius-attribute
                    container include-radius-attribute {
                        description "Enter the include-radius-attribute context";

                        ///nokia-conf/configure/ipsec/radius/authentication-policy/include-radius-attribute/called-station-id
                        leaf called-station-id {
                            type boolean;
                            default "false";
                            description "Include the Called-Station-Id attribute";
                        }

                        ///nokia-conf/configure/ipsec/radius/authentication-policy/include-radius-attribute/calling-station-id
                        leaf calling-station-id {
                            type boolean;
                            default "false";
                            description "Include the Calling-Station-Id attribute";
                        }

                        ///nokia-conf/configure/ipsec/radius/authentication-policy/include-radius-attribute/nas-identifier
                        leaf nas-identifier {
                            type boolean;
                            default "false";
                            description "Include the NAS-Identifier attribute";
                        }

                        ///nokia-conf/configure/ipsec/radius/authentication-policy/include-radius-attribute/nas-ip-addr
                        leaf nas-ip-addr {
                            type boolean;
                            default "false";
                            description "Include the NAS-IP-Address attribute";
                        }

                        ///nokia-conf/configure/ipsec/radius/authentication-policy/include-radius-attribute/nas-port-id
                        leaf nas-port-id {
                            type boolean;
                            default "false";
                            description "Include the NAS-Port-Id attribute";
                        }

                        ///nokia-conf/configure/ipsec/radius/authentication-policy/include-radius-attribute/client-cert-subject-key-id
                        leaf client-cert-subject-key-id {
                            type boolean;
                            default "false";
                            description "Include the Subject Key Identifier";
                        }

                    } // container include-radius-attribute

                } // list authentication-policy

            } // container radius

        } // container ipsec

    } // grouping conf-ipsec

}
