submodule nokia-state-router-ospf3 {

    yang-version "1.1";

    belongs-to nokia-state { prefix "state"; }

    import ietf-inet-types                { prefix "inet"; }
    import ietf-yang-types                { prefix "yang"; }
    import nokia-sros-yang-extensions     { prefix "sros-ext"; }
    import nokia-types-igp                { prefix "types-igp"; }
    import nokia-types-ospf               { prefix "types-ospf"; }
    import nokia-types-router             { prefix "types-router"; }
    import nokia-types-sros               { prefix "types-sros"; }

    sros-ext:sros-major-release "rel23";
    organization "Nokia";
    contact
        "Nokia SR OS Support
         Web: <http://www.nokia.com>";
    description
        "Nokia YANG Data model with operational state for router ospf protocol attributes on SR OS based routers.

         Copyright 2016 Nokia. All rights reserved. Reproduction of this document
         is authorized on the condition that the foregoing copyright notice is included.

         This nokia-state-router-ospf3 YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-01-04";

    grouping state-router-ospf3 {
        ///nokia-state/state/router/ospf3
        list ospf3 {
            key "ospf-instance";
            description "Enter the ospf3 list instance";

            ///nokia-state/state/router/ospf3/ospf-instance
            leaf ospf-instance {
                type uint32 {
                    range "0..31|64..95";
                }
                description "Value for the integrated OSPF instance";
            }

            ///nokia-state/state/router/ospf3/oper-state
            leaf oper-state {
                type types-sros:oper-state;
                description
                    "the value of oper-state indicates the current operating state of this
                     instance of OSPF in this router.";
            }

            ///nokia-state/state/router/ospf3/last-disabled-reason
            leaf last-disabled-reason {
                type string {
                    length "0..20";
                }
                description "Reason why the disabled state was entered the last time.";
            }

            ///nokia-state/state/router/ospf3/oper-router-id
            leaf oper-router-id {
                type types-sros:ipv4-address;
                description
                    "the value of oper-router-id indicates the 32-bit integer used to uniquely
                     identify the router in the autonomous system. the default OSPF instance
                     will use the value specified by router-id or the one derived from the
                     IP layer. For the non-default instances of OSPF, this is the same value as
                     router-id, which must be specified before the OSPF instance can become
                     operational.";
            }

            ///nokia-state/state/router/ospf3/area-border-router
            leaf area-border-router {
                type boolean;
                description "This indicates whether this router is an area border router.";
            }

            ///nokia-state/state/router/ospf3/as-border-router
            leaf as-border-router {
                type boolean;
                description "This indicates whether this router is an AS border router.";
            }

            ///nokia-state/state/router/ospf3/backbone-router
            leaf backbone-router {
                type boolean;
                description "This indicates whether or not this router is configured as an OSPF back bone router.";
            }

            ///nokia-state/state/router/ospf3/overload-state
            leaf overload-state {
                type enumeration {
                    enum overload                       { value 1; }
                    enum no-overload                    { value 2; }
                }
                description "the value of overload-oper-state indicates whether or not the OSPF application is presently in overload state or not.";
            }

            ///nokia-state/state/router/ospf3/overload-rem-interval
            leaf overload-rem-interval {
                type int32 {
                    range "0..65535";
                }
                units "seconds";
                description "the value of overload-rem-interval indicates the time for which the system will be in overload state if OSPF is in overload state. the value of 0 implies that the system is indefinitely in overload state.";
            }

            ///nokia-state/state/router/ospf3/last-overload-entered-time
            leaf last-overload-entered-time {
                type yang:date-and-time;
                description "the value of last-overload-entrd-time indicates the time at which the system last went into overload state.";
            }

            ///nokia-state/state/router/ospf3/last-overload-exit-time
            leaf last-overload-exit-time {
                type yang:date-and-time;
                description "the value of last-overload-exit-time indicates the time at which the system last came out of overload state.";
            }

            ///nokia-state/state/router/ospf3/last-overload-enter-code
            leaf last-overload-enter-code {
                type enumeration {
                    enum none                           { value 1; }
                    enum spf-failed                     { value 2; }
                    enum boot-overload                  { value 3; }
                    enum manual-overload                { value 4; }
                    enum sfm-overload                   { value 5; }
                    enum fib-add-fail                   { value 6; }
                    enum rtm-add-fail                   { value 7; }
                    enum rtr-adv-lsa-limit              { value 8; }
                }
                description "the value of last-overload-enter-code indicates the condition which caused OSPF to get into overload.";
            }

            ///nokia-state/state/router/ospf3/last-overload-exit-code
            leaf last-overload-exit-code {
                type enumeration {
                    enum none                           { value 1; }
                    enum bgp-sig-recv                   { value 2; }
                    enum timer-expired                  { value 3; }
                    enum manual-exit                    { value 4; }
                    enum sfm-overload-done              { value 5; }
                }
                description "the value of last-overload-exit-code indicates the reason why OSPF came out of overload state the last time, since reset.";
            }

            ///nokia-state/state/router/ospf3/overflow
            leaf overflow {
                type boolean;
                description
                    "The value of overflow indicates the current overflow state (true/false).
                     This overflow state occurs when the number of non-default AS-external-LS-as
                     entries exceed the link-state database capability.";
            }

            ///nokia-state/state/router/ospf3/last-overflow-entered-time
            leaf last-overflow-entered-time {
                type yang:date-and-time;
                description "The value of last-overflow-entered-time indicates the value of sys-up-time the last time we entered overflow state. this overflow state occurs when the number of non-default AS-external-LS-as entries exceed the link-state database capability.";
            }

            ///nokia-state/state/router/ospf3/last-overflow-exit-time
            leaf last-overflow-exit-time {
                type yang:date-and-time;
                description "the value of last-overflow-exit-time indicates the value of sys-up-time the last time we exited overflow state. this overflow state occurs when the number of non-default AS-external-LS-as entries exceed the link-state database capability.";
            }

            ///nokia-state/state/router/ospf3/stub-router-support
            leaf stub-router-support {
                type boolean;
                description "the value of stub-router-support indicates the router's support for stub router functionality.";
            }

            ///nokia-state/state/router/ospf3/opaque-lsa-support
            leaf opaque-lsa-support {
                type boolean;
                description "the value of opaque-lsa-support indicates the router's support for opaque LSA types. this object is valid only when version is 'version2'.";
            }

            ///nokia-state/state/router/ospf3/last-enabled-time
            leaf last-enabled-time {
                type yang:date-and-time;
                description "the value of last-enabled-time indicates the value of sys-up-time when admin-state was last set to 'enabled'. when admin-state is set to 'disabled', the OSPF counters are stopped when admin-state is reset to 'enabled', the counters are reset to zero.";
            }

            ///nokia-state/state/router/ospf3/routes-submitted
            leaf routes-submitted {
                type yang:gauge32;
                description "the value of routes-submitted indicates the number of routes submitted to the route table manager (RTM) by this instance of OSPF.";
            }

            ///nokia-state/state/router/ospf3/total-exported-routes
            leaf total-exported-routes {
                type yang:gauge32;
                description "the value of total-exported-routes indicates the total number of routes exported into OSPF from the route table manager when an export policy is configured. value of total-exported-routes would be 0 when no export policy is configured.";
            }

            ///nokia-state/state/router/ospf3/ldp-over-rsvp-status
            leaf ldp-over-rsvp-status {
                type enumeration {
                    enum enabled                        { value 1; }
                    enum disabled                       { value 2; }
                }
                description "the value of ldp-over-rsvp-status indicates whether LDP-over-RSVP feature is enabled or disabled for a specific OSPF instance.";
            }

            ///nokia-state/state/router/ospf3/rsvp-shortcut-status
            leaf rsvp-shortcut-status {
                type boolean;
                description "the value of rsvp-shortcut-status indicates whether RSVP-TE shortcut for resolving IGP routes has been enabled or disabled for OSPF.";
            }

            ///nokia-state/state/router/ospf3/advertise-tunl-link-status
            leaf advertise-tunl-link-status {
                type boolean;
                description "the value of advertise-tunl-link-status indicates whether advertisement of LSP shortcuts into IGP has been enabled or disabled for OSPF.";
            }

            ///nokia-state/state/router/ospf3/ovld-lsa-limit-rem-interval
            leaf ovld-lsa-limit-rem-interval {
                type int32 {
                    range "0..65535";
                }
                units "seconds";
                description "the value of ovld-lsa-limit-rem-interval indicates the remaining time in seconds for which the system will be in overload state due to advertising router LSA limit exceeded. the value of 0 implies that the system is either not in overload or indefinitely in overload state.";
            }

            ///nokia-state/state/router/ospf3/db-asn
            leaf db-asn {
                type inet:as-number;
                description "the value of the object db-asn indicates the autonomous system number the IGP is using during its database export. the value from TIMETRA-VRTR-MIB::v-rtr-AS4byte at the moment database-export is enabled is used as AS number. the used AS number gets updated when the value from admin-state changes from disabled (2) to enabled (1) or when the value from database-export changes from disabled(2) to enabled(1).";
            }

            ///nokia-state/state/router/ospf3/export-limit
            container export-limit {
                description "Enable the export-limit context";

                ///nokia-state/state/router/ospf3/export-limit/state
                leaf state {
                    type enumeration {
                        enum below-limits                   { value 1; }
                        enum log-level-reached              { value 2; }
                        enum limit-reached                  { value 3; }
                    }
                    description "the value of export-limit-state indicates the current state of the export of routes into OSPF.";
                }

            } // container export-limit

            ///nokia-state/state/router/ospf3/rtr-adv-lsa-limit
            container rtr-adv-lsa-limit {
                description "Enable the rtr-adv-lsa-limit context";

                ///nokia-state/state/router/ospf3/rtr-adv-lsa-limit/state
                leaf state {
                    type enumeration {
                        enum below-limits                   { value 1; }
                        enum warning-threshold-exceeded     { value 2; }
                        enum max-lsa-count-exceeded         { value 3; }
                    }
                    description "the value of rtr-adv-lsa-limit-state indicates the current state according to config in rtr-adv-lsa-limit.";
                }

                ///nokia-state/state/router/ospf3/rtr-adv-lsa-limit/adv-router-id
                leaf adv-router-id {
                    type types-sros:ipv4-address;
                    description "the identity of the router that is advertising too many LSAs.";
                }

            } // container rtr-adv-lsa-limit

            ///nokia-state/state/router/ospf3/spf
            container spf {
                description "Enter the spf context";

                ///nokia-state/state/router/ospf3/spf/max-spf-run-interval
                leaf max-spf-run-interval {
                    type int32 {
                        range "0..2147483647";
                    }
                    units "centiseconds";
                    description "the value of max-spf-run-interval indicates the maximum time, in hundredths of seconds, used to perform a total SPF calculation.";
                }

                ///nokia-state/state/router/ospf3/spf/min-spf-run-interval
                leaf min-spf-run-interval {
                    type int32 {
                        range "0..2147483647";
                    }
                    units "centiseconds";
                    description "the value of min-spf-run-interval indicates the minimum time, in hundredths of seconds, used to perform a total SPF calculation.";
                }

                ///nokia-state/state/router/ospf3/spf/avg-spf-run-interval
                leaf avg-spf-run-interval {
                    type int32 {
                        range "0..2147483647";
                    }
                    units "centiseconds";
                    description "the value of avg-spf-run-interval indicates the average time, in hundredths of seconds, of all the total SPF calculations performed by this OSPF router.";
                }

                ///nokia-state/state/router/ospf3/spf/max-rtm-update-interval
                leaf max-rtm-update-interval {
                    type int32 {
                        range "0..2147483647";
                    }
                    units "centiseconds";
                    description "the value of max-rtm-update-time indicates the maximum time, in hundredths of seconds, used to update RTM.";
                }

                ///nokia-state/state/router/ospf3/spf/min-rtm-update-interval
                leaf min-rtm-update-interval {
                    type int32 {
                        range "0..2147483647";
                    }
                    units "centiseconds";
                    description "the value of min-rtm-update-time indicates the minimum time, in hundredths of seconds, used to update RTM.";
                }

                ///nokia-state/state/router/ospf3/spf/avg-rtm-update-interval
                leaf avg-rtm-update-interval {
                    type int32 {
                        range "0..2147483647";
                    }
                    units "centiseconds";
                    description "the value of avg-rtm-update-time indicates the average time, in hundredths of seconds, used to update RTM.";
                }

                ///nokia-state/state/router/ospf3/spf/max-lfa-spf-interval
                leaf max-lfa-spf-interval {
                    type int32 {
                        range "0..2147483647";
                    }
                    units "centiseconds";
                    description "the value of max-lfa-spf-interval indicates the maximum time, in hundredths of seconds, used to run LFA SPF.";
                }

                ///nokia-state/state/router/ospf3/spf/min-lfa-spf-interval
                leaf min-lfa-spf-interval {
                    type int32 {
                        range "0..2147483647";
                    }
                    units "centiseconds";
                    description "the value of min-lfa-spf-interval indicates the minimum time, in hundredths of seconds, used to run LFA SPF.";
                }

                ///nokia-state/state/router/ospf3/spf/avg-lfa-spf-interval
                leaf avg-lfa-spf-interval {
                    type int32 {
                        range "0..2147483647";
                    }
                    units "centiseconds";
                    description "the value of avg-lfa-spf-interval indicates the average time, in hundredths of seconds, used to run LFA SPF.";
                }

                ///nokia-state/state/router/ospf3/spf/last-full-spf
                container last-full-spf {
                    description "Enter the last-full-spf context";

                    ///nokia-state/state/router/ospf3/spf/last-full-spf/run-time
                    leaf run-time {
                        type yang:date-and-time;
                        description "the value of last-full-spf-run-time indicates the time at which the system last performed a full dijkstra (SPF) run.";
                    }

                    ///nokia-state/state/router/ospf3/spf/last-full-spf/total-time
                    leaf total-time {
                        type int32 {
                            range "0..2147483647";
                        }
                        units "centiseconds";
                        description "Time it toook, in hundredths of seconds, to complete the last SPF run completely.";
                    }

                    ///nokia-state/state/router/ospf3/spf/last-full-spf/intra-spf-time
                    leaf intra-spf-time {
                        type int32 {
                            range "0..2147483647";
                        }
                        units "centiseconds";
                        description "Time it toook, in hundredths of seconds, to complete the intra-area SPF calculations.";
                    }

                    ///nokia-state/state/router/ospf3/spf/last-full-spf/inter-spf-time
                    leaf inter-spf-time {
                        type int32 {
                            range "0..2147483647";
                        }
                        units "centiseconds";
                        description "Time it toook, in hundredths of seconds, to complete the inter-area SPF calculations.";
                    }

                    ///nokia-state/state/router/ospf3/spf/last-full-spf/extern-spf-time
                    leaf extern-spf-time {
                        type int32 {
                            range "0..2147483647";
                        }
                        units "centiseconds";
                        description "Time it toook, in hundredths of seconds, to complete the external LSA calculations.";
                    }

                    ///nokia-state/state/router/ospf3/spf/last-full-spf/rtm-update-time
                    leaf rtm-update-time {
                        type int32 {
                            range "0..2147483647";
                        }
                        units "centiseconds";
                        description "Time it toook, in hundredths of seconds, to complete the RTM updates.";
                    }

                } // container last-full-spf

                ///nokia-state/state/router/ospf3/spf/last-ext-spf
                container last-ext-spf {
                    description "Enter the last-ext-spf context";

                    ///nokia-state/state/router/ospf3/spf/last-ext-spf/run-time
                    leaf run-time {
                        type yang:date-and-time;
                        description "the value of last-ext-spf-run-time indicates the value of sys-up-time when the external OSPF dijkstra (SPF) was last run.";
                    }

                    ///nokia-state/state/router/ospf3/spf/last-ext-spf/interval
                    leaf interval {
                        type int32 {
                            range "0..2147483647";
                        }
                        units "centiseconds";
                        description "the value of ext-spf-run-interval indicates the time, in hundredths of seconds, used to perform the most recent total external (not incremental) SPF calculation.";
                    }

                } // container last-ext-spf

                ///nokia-state/state/router/ospf3/spf/last-lfa-spf
                container last-lfa-spf {
                    description "Enter the last-lfa-spf context";

                    ///nokia-state/state/router/ospf3/spf/last-lfa-spf/run-time
                    leaf run-time {
                        type yang:date-and-time;
                        description "the value of last-lfa-spf-run-time indicates the time at which the system last performed a dijkstra (LFA SPF) run.";
                    }

                    ///nokia-state/state/router/ospf3/spf/last-lfa-spf/interval
                    leaf interval {
                        type int32 {
                            range "0..2147483647";
                        }
                        units "centiseconds";
                        description "the time, in hundredths of seconds, used to perform the last LFA SPF calculation.";
                    }

                } // container last-lfa-spf

            } // container spf

            ///nokia-state/state/router/ospf3/statistics
            container statistics {
                description "Enter the statistics context";

                ///nokia-state/state/router/ospf3/statistics/num-times-in-overload
                leaf num-times-in-overload {
                    type yang:counter32;
                    description "The count of the number of times the system was overloaded.";
                }

                ///nokia-state/state/router/ospf3/statistics/num-times-in-overflow
                leaf num-times-in-overflow {
                    type yang:counter32;
                    description "The count of the number of times the system was in the overflow state.";
                }

                ///nokia-state/state/router/ospf3/statistics/neighbor-count
                leaf neighbor-count {
                    type yang:gauge32;
                    description "The number of OSPF neighbors.";
                }

                ///nokia-state/state/router/ospf3/statistics/virt-nbr-count
                leaf virt-nbr-count {
                    type yang:gauge32;
                    description "The number of OSPF virtual link neighbors.";
                }

                ///nokia-state/state/router/ospf3/statistics/spf
                container spf {
                    description "Enter the spf context";

                    ///nokia-state/state/router/ospf3/statistics/spf/full-spf-runs
                    leaf full-spf-runs {
                        type yang:counter32;
                        description "The total number of times that complete SPF has been run on the router since OSPF was last enabled.";
                    }

                    ///nokia-state/state/router/ospf3/statistics/spf/ext-spf-runs
                    leaf ext-spf-runs {
                        type yang:counter32;
                        description "The total number of times that only the external portion of the SPF has been run since OSPF was last enabled.";
                    }

                    ///nokia-state/state/router/ospf3/statistics/spf/incremental-inter-spf-runs
                    leaf incremental-inter-spf-runs {
                        type yang:counter32;
                        description "The total number of incremental SPF runs triggered by new or updated inter-area prefix or inter-area router LS-as.";
                    }

                    ///nokia-state/state/router/ospf3/statistics/spf/incremental-ext-spf-runs
                    leaf incremental-ext-spf-runs {
                        type yang:counter32;
                        description "The total number of incremental SPF runs triggered by new or updated external LS-as.";
                    }

                    ///nokia-state/state/router/ospf3/statistics/spf/spf-attempts-failed
                    leaf spf-attempts-failed {
                        type yang:counter32;
                        description "The number of times an attempt to run SPF has failed because SPF runs have been stopped as a result of insufficient memory resources.";
                    }

                    ///nokia-state/state/router/ospf3/statistics/spf/route-adds-failed
                    leaf route-adds-failed {
                        type yang:counter32;
                        description "The number of times an attempt to add a route to the route table manager (RTM) failed for this OSPF instance.";
                    }

                    ///nokia-state/state/router/ospf3/statistics/spf/route-dels-failed
                    leaf route-dels-failed {
                        type yang:counter32;
                        description "The number of times an attempt to delete a route from the route table manager (RTM) failed for this instance of OSPF.";
                    }

                    ///nokia-state/state/router/ospf3/statistics/spf/route-mods-failed
                    leaf route-mods-failed {
                        type yang:counter32;
                        description "The number of times an attempt to modify a route in the route table manager (RTM) failed for this instance of OSPF.";
                    }

                    ///nokia-state/state/router/ospf3/statistics/spf/lfa-spf-runs
                    leaf lfa-spf-runs {
                        type yang:counter32;
                        description "The total number of times that complete LFA SPF has been run on the router since OSPF was last enabled.";
                    }

                    ///nokia-state/state/router/ospf3/statistics/spf/rlfa-runs
                    leaf rlfa-runs {
                        type yang:counter32;
                        description "The number of times remote-loopfree-alternate calculations have been made.";
                    }

                    ///nokia-state/state/router/ospf3/statistics/spf/tilfa-runs
                    leaf tilfa-runs {
                        type yang:counter32;
                        description "The number of times remote-loopfree-alternate calculations have been made.";
                    }

                    ///nokia-state/state/router/ospf3/statistics/spf/cspf-requests
                    leaf cspf-requests {
                        type yang:counter32;
                        description "The number of cspf requests made to the OSPF protocol.";
                    }

                    ///nokia-state/state/router/ospf3/statistics/spf/cspf-dropped-requests
                    leaf cspf-dropped-requests {
                        type yang:counter32;
                        description "The number of dropped cspf requests made by the OSPF protocol.";
                    }

                    ///nokia-state/state/router/ospf3/statistics/spf/cspf-paths-found
                    leaf cspf-paths-found {
                        type yang:counter32;
                        description "The number of of paths found for the requests made to OSPF protocol.";
                    }

                    ///nokia-state/state/router/ospf3/statistics/spf/cspf-paths-not-found
                    leaf cspf-paths-not-found {
                        type yang:counter32;
                        description "The number of of paths not found for the requests made to OSPF protocol.";
                    }

                } // container spf

                ///nokia-state/state/router/ospf3/statistics/lsdb
                container lsdb {
                    description "Enter the lsdb context";

                    ///nokia-state/state/router/ospf3/statistics/lsdb/new-lsas-originated
                    leaf new-lsas-originated {
                        type yang:counter32;
                        description "The number of new link-state advertisements that have been originated. This number is incremented each time the router originates a new LSA.";
                    }

                    ///nokia-state/state/router/ospf3/statistics/lsdb/new-lsas-received
                    leaf new-lsas-received {
                        type yang:counter32;
                        description "The number of link-state advertisements received determined to be new instantiations. This number does not include newer instantiations of self-originated link-state advertisements.";
                    }

                    ///nokia-state/state/router/ospf3/statistics/lsdb/as-scope-lsa-count
                    leaf as-scope-lsa-count {
                        type yang:gauge32;
                        description "the value of as-scope-lsa-count indicates the number of AS-scope (e.g. AS-external) link state advertisements in the link-state database.";
                    }

                    ///nokia-state/state/router/ospf3/statistics/lsdb/as-scope-lsa-cksum-sum
                    leaf as-scope-lsa-cksum-sum {
                        type int32;
                        description "the value of as-scope-lsa-cksum-sum indicates the 32-bit unsigned sum of the LS checksums of the AS-scoped link-state advertisements contained in the link-state database. this sum can be used to determine if there has been a change in a router's link-state database, and to compare the link-state database of two routers.";
                    }

                    ///nokia-state/state/router/ospf3/statistics/lsdb/as-scope-unk-lsa-count
                    leaf as-scope-unk-lsa-count {
                        type yang:gauge32;
                        description "the value of as-scope-unk-lsa-count indicates the number of unknown AS-scope (e.g. AS-external) link-state advertisements in the link-state database.";
                    }

                    ///nokia-state/state/router/ospf3/statistics/lsdb/as-scope-unk-lsa-cksum-sum
                    leaf as-scope-unk-lsa-cksum-sum {
                        type int32;
                        description "the value of as-scope-unk-lsa-cksum-sum indicates the 32-bit unsigned sum of the LS checksums of the unknown AS-scoped link-state advertisements contained in the link-state database. this sum can be used to determine if there has been a change in a router's link-state database, and to compare the link-state database of two routers.";
                    }

                    ///nokia-state/state/router/ospf3/statistics/lsdb/extern-lsa-count
                    leaf extern-lsa-count {
                        type yang:gauge32;
                        description "the value of extern-lsa-count indicates the number of external LS-as (LS type 0x4005) in the link-state database";
                    }

                    ///nokia-state/state/router/ospf3/statistics/lsdb/extern-lsa-cksum-sum
                    leaf extern-lsa-cksum-sum {
                        type int32;
                        description "the value of extern-lsa-cksum-sum indicates the 32-bit unsigned sum of the LS checksums of the external link-state advertisements contained in the link-state database. this sum can be used to determine if there has been a change in a router's link state database, and to compare the link-state database of two routers.";
                    }

                    ///nokia-state/state/router/ospf3/statistics/lsdb/as-lsdb-entries
                    leaf as-lsdb-entries {
                        type yang:gauge32;
                        description "The number of row entries in the as-lsdb-table.";
                    }

                    ///nokia-state/state/router/ospf3/statistics/lsdb/area-lsdb-entries
                    leaf area-lsdb-entries {
                        type yang:gauge32;
                        description "The number of row entries in the area-lsdb-table.";
                    }

                    ///nokia-state/state/router/ospf3/statistics/lsdb/link-lsdb-entries
                    leaf link-lsdb-entries {
                        type yang:gauge32;
                        description "The number of row entries in the ng-link-lsdb-table.";
                    }

                } // container lsdb

                ///nokia-state/state/router/ospf3/statistics/sid
                container sid {
                    description "Enter the sid context";

                    ///nokia-state/state/router/ospf3/statistics/sid/srgb-errors
                    leaf srgb-errors {
                        type yang:counter32;
                        description "The total number of errors for SI-ds that are not within the label-range of the router.";
                    }

                    ///nokia-state/state/router/ospf3/statistics/sid/duplicated-errors
                    leaf duplicated-errors {
                        type yang:counter32;
                        description "The total number of errors for SI-ds which are already assigned to another prefix.";
                    }

                } // container sid

                ///nokia-state/state/router/ospf3/statistics/packets
                container packets {
                    description "Enter the packets context";

                    ///nokia-state/state/router/ospf3/statistics/packets/tx-total
                    leaf tx-total {
                        type yang:counter32;
                        description "The total number of OSPF packets transmitted since admin-state was last set to 'enabled'.";
                    }

                    ///nokia-state/state/router/ospf3/statistics/packets/tx-hello
                    leaf tx-hello {
                        type yang:counter32;
                        description "The total number of OSPF hello packets transmitted since admin-state was last set to 'enabled'.";
                    }

                    ///nokia-state/state/router/ospf3/statistics/packets/tx-db-description
                    leaf tx-db-description {
                        type yang:counter32;
                        description "The total number of OSPF database description packets transmitted since admin-state was last set to 'enabled'.";
                    }

                    ///nokia-state/state/router/ospf3/statistics/packets/tx-ls-request
                    leaf tx-ls-request {
                        type yang:counter32;
                        description "The total number of OSPF link state requests (LS-rs)transmitted since admin-state was last set to 'enabled'.";
                    }

                    ///nokia-state/state/router/ospf3/statistics/packets/tx-ls-update
                    leaf tx-ls-update {
                        type yang:counter32;
                        description "The total number of OSPF link state updates (LS-us) transmitted since admin-state was last set to 'enabled'.";
                    }

                    ///nokia-state/state/router/ospf3/statistics/packets/tx-ls-ack
                    leaf tx-ls-ack {
                        type yang:counter32;
                        description "The total number of OSPF link state acknowledgements transmitted since admin-state was last set to 'enabled'.";
                    }

                    ///nokia-state/state/router/ospf3/statistics/packets/rx-total
                    leaf rx-total {
                        type yang:counter32;
                        description "The total number of OSPF packets received since admin-state was last set to 'enabled'.";
                    }

                    ///nokia-state/state/router/ospf3/statistics/packets/rx-hello
                    leaf rx-hello {
                        type yang:counter32;
                        description "The total number of OSPF hello packets received since admin-state was last set to 'enabled'.";
                    }

                    ///nokia-state/state/router/ospf3/statistics/packets/rx-db-description
                    leaf rx-db-description {
                        type yang:counter32;
                        description "The total number of OSPF database description packets received since admin-state was last set to 'enabled'.";
                    }

                    ///nokia-state/state/router/ospf3/statistics/packets/rx-ls-request
                    leaf rx-ls-request {
                        type yang:counter32;
                        description "The total number of link state requests (LS-rs) received since admin-state was last set to 'enabled'.";
                    }

                    ///nokia-state/state/router/ospf3/statistics/packets/rx-ls-update
                    leaf rx-ls-update {
                        type yang:counter32;
                        description "The total number of link state updates (LS-us) received since admin-state was last set to 'enabled'.";
                    }

                    ///nokia-state/state/router/ospf3/statistics/packets/rx-ls-ack
                    leaf rx-ls-ack {
                        type yang:counter32;
                        description "The total number of link state acknowledgements received since admin-state was last set to 'enabled'.";
                    }

                    ///nokia-state/state/router/ospf3/statistics/packets/discarded
                    leaf discarded {
                        type yang:counter32;
                        description "The total number of OSPF packets discarded since admin-state was last set to 'enabled'.";
                    }

                    ///nokia-state/state/router/ospf3/statistics/packets/retransmits
                    leaf retransmits {
                        type yang:counter32;
                        description "The total number of OSPF retransmits since admin-state was last set to 'enabled'.";
                    }

                    ///nokia-state/state/router/ospf3/statistics/packets/tx-failures
                    leaf tx-failures {
                        type yang:counter32;
                        description "The total number of OSPF transmit failures since admin-state was last set to 'enabled'.";
                    }

                    ///nokia-state/state/router/ospf3/statistics/packets/bad-version
                    leaf bad-version {
                        type yang:counter32;
                        description "The total number of OSPF packets received with bad OSPF version numbers since admin-state was last set to 'enabled'.";
                    }

                    ///nokia-state/state/router/ospf3/statistics/packets/bad-network
                    leaf bad-network {
                        type yang:counter32;
                        description "The total number of OSPF packets received with invalid network or mask since admin-state was last set to 'enabled'.";
                    }

                    ///nokia-state/state/router/ospf3/statistics/packets/bad-area
                    leaf bad-area {
                        type yang:counter32;
                        description "The total number of OSPF packets received with an area mismatch since admin-state was last set to 'enabled'.";
                    }

                    ///nokia-state/state/router/ospf3/statistics/packets/bad-dest-address
                    leaf bad-dest-address {
                        type yang:counter32;
                        description "The total number of OSPF packets received with the incorrect IP destination address since admin-state was last set to 'enabled'.";
                    }

                    ///nokia-state/state/router/ospf3/statistics/packets/bad-neighbors
                    leaf bad-neighbors {
                        type yang:counter32;
                        description "The total number of OSPF packets received where the neighbor information does not match the information this router has for the neighbor since admin-state was last set to 'enabled'.";
                    }

                    ///nokia-state/state/router/ospf3/statistics/packets/bad-packet-type
                    leaf bad-packet-type {
                        type yang:counter32;
                        description "The total number of OSPF packets received with an invalid OSPF packet type since admin-state was last set to 'enabled'.";
                    }

                    ///nokia-state/state/router/ospf3/statistics/packets/bad-length
                    leaf bad-length {
                        type yang:counter32;
                        description "The total number of OSPF packets received with a total length not equal to the length given in the packet itself since admin-state was last set to 'enabled'.";
                    }

                    ///nokia-state/state/router/ospf3/statistics/packets/bad-hello-interval
                    leaf bad-hello-interval {
                        type yang:counter32;
                        description "the value of bad-hello-intervals indicates the total number of OSPF packets received where the hello interval given in packet was not equal to that configured on this interface since admin-state was last set to 'enabled'.";
                    }

                    ///nokia-state/state/router/ospf3/statistics/packets/bad-dead-interval
                    leaf bad-dead-interval {
                        type yang:counter32;
                        description "The total number of OSPF packets received where the dead interval given in the packet was not equal to that configured on this interface since admin-state was last set to 'enabled'.";
                    }

                    ///nokia-state/state/router/ospf3/statistics/packets/bad-options
                    leaf bad-options {
                        type yang:counter32;
                        description "The total number of OSPF packets received with an option that does not match those configured for this interface or area since admin-state was last set to 'enabled'.";
                    }

                    ///nokia-state/state/router/ospf3/statistics/packets/rx-bad-checksum
                    leaf rx-bad-checksum {
                        type yang:counter32;
                        description "The count of LS-as received with bad checksums.";
                    }

                    ///nokia-state/state/router/ospf3/statistics/packets/bad-auth-type
                    leaf bad-auth-type {
                        type yang:counter32;
                        description "The total number of OSPF packets received with an invalid authorization type since admin-state was last set to 'enabled'.";
                    }

                    ///nokia-state/state/router/ospf3/statistics/packets/auth-failures
                    leaf auth-failures {
                        type yang:counter32;
                        description "The total number of OSPF packets received with an invalid authorization key since admin-state was last set to 'enabled'.";
                    }

                    ///nokia-state/state/router/ospf3/statistics/packets/bad-virtual-link
                    leaf bad-virtual-link {
                        type yang:counter32;
                        description "The total number of OSPF packets received that are destined to a virtual link that does not exist since admin-state was last set to 'enabled'.";
                    }

                } // container packets

            } // container statistics

            ///nokia-state/state/router/ospf3/segment-routing
            container segment-routing {
                description "Enter the segment-routing context";


            } // container segment-routing

            ///nokia-state/state/router/ospf3/area
            list area {
                key "area-id";
                description "Enter the area list instance";

                ///nokia-state/state/router/ospf3/area/area-id
                leaf area-id {
                    type types-sros:ipv4-address;
                    description "Area-ID attribute";
                }

                ///nokia-state/state/router/ospf3/area/area-bdr-rtr-count
                leaf area-bdr-rtr-count {
                    type yang:gauge32;
                    description "The total number of area border routers reachable within this area.";
                }

                ///nokia-state/state/router/ospf3/area/as-bdr-rtr-count
                leaf as-bdr-rtr-count {
                    type yang:gauge32;
                    description "The total number of autonomous system border routers reachable within this area.";
                }

                ///nokia-state/state/router/ospf3/area/active-interfaces
                leaf active-interfaces {
                    type uint32;
                    description "The number of active interfaces in this area.";
                }

                ///nokia-state/state/router/ospf3/area/interface-count
                leaf interface-count {
                    type uint32;
                    description "The number of interfaces configured in this area.";
                }

                ///nokia-state/state/router/ospf3/area/virtual-link-count
                leaf virtual-link-count {
                    type uint32;
                    description "The total number of virtual links configured through this area.";
                }

                ///nokia-state/state/router/ospf3/area/neighbor-count
                leaf neighbor-count {
                    type yang:gauge32;
                    description "The number of active neighbors in this area.";
                }

                ///nokia-state/state/router/ospf3/area/last-spf-run-time
                leaf last-spf-run-time {
                    type yang:date-and-time;
                    description "The sys-up-time when intra-area SPF was last run on this area.";
                }

                ///nokia-state/state/router/ospf3/area/spf-runs
                leaf spf-runs {
                    type yang:counter32;
                    description "The number of times that the intra-area route table has been calculated using this area's link-state database.";
                }

                ///nokia-state/state/router/ospf3/area/nssa-translator-state
                leaf nssa-translator-state {
                    type enumeration {
                        enum enabled                        { value 1; }
                        enum elected                        { value 2; }
                        enum disabled                       { value 3; }
                    }
                    description "The current NSSA translator state";
                }

                ///nokia-state/state/router/ospf3/area/nssa-translator-events
                leaf nssa-translator-events {
                    type yang:counter32;
                    description "The number of translator state changes that have occurred since the last boot-up.";
                }

                ///nokia-state/state/router/ospf3/area/lsa-totals
                container lsa-totals {
                    description "Enter the lsa-totals context";

                    ///nokia-state/state/router/ospf3/area/lsa-totals/router-lsa
                    leaf router-lsa {
                        type yang:gauge32;
                        description "The number of router LSAs in this area's link-state database.";
                    }

                    ///nokia-state/state/router/ospf3/area/lsa-totals/e-router-lsa
                    leaf e-router-lsa {
                        type yang:gauge32;
                        description "The number of OSPFv3 E-router LSAs in this area's link-state database.";
                    }

                    ///nokia-state/state/router/ospf3/area/lsa-totals/network-lsa
                    leaf network-lsa {
                        type yang:gauge32;
                        description "The number of network LSAs in this area's link-state database.";
                    }

                    ///nokia-state/state/router/ospf3/area/lsa-totals/e-network-lsa
                    leaf e-network-lsa {
                        type yang:gauge32;
                        description "The number of OSPFv3 E-network LSAs in this area's link-state database.";
                    }

                    ///nokia-state/state/router/ospf3/area/lsa-totals/nssa-lsa
                    leaf nssa-lsa {
                        type yang:gauge32;
                        description "The number of NSSA LSAs in this area's link-state database.";
                    }

                    ///nokia-state/state/router/ospf3/area/lsa-totals/e-nssa-lsa
                    leaf e-nssa-lsa {
                        type yang:gauge32;
                        description "The number of OSPFv3 E-NSSA LSAs in this area's link-state database.";
                    }

                    ///nokia-state/state/router/ospf3/area/lsa-totals/inter-area-prefix-lsa
                    leaf inter-area-prefix-lsa {
                        type yang:gauge32;
                        description "The number of OSPFv3 inter-area-prefix LSAs in this area's link-state database.";
                    }

                    ///nokia-state/state/router/ospf3/area/lsa-totals/e-inter-area-prefix-lsa
                    leaf e-inter-area-prefix-lsa {
                        type yang:gauge32;
                        description "The number of OSPFv3 E-inter-area-prefix LSAs in this area's link-state database.";
                    }

                    ///nokia-state/state/router/ospf3/area/lsa-totals/inter-area-router-lsa
                    leaf inter-area-router-lsa {
                        type yang:gauge32;
                        description "The number of OSPFv3 inter-area-router LSAs in this area's link-state database.";
                    }

                    ///nokia-state/state/router/ospf3/area/lsa-totals/e-inter-area-router-lsa
                    leaf e-inter-area-router-lsa {
                        type yang:gauge32;
                        description "The number of OSPFv3 E-inter-area-router LSAs in this area's link-state database.";
                    }

                    ///nokia-state/state/router/ospf3/area/lsa-totals/intra-area-prefix-lsa
                    leaf intra-area-prefix-lsa {
                        type yang:gauge32;
                        description "The number of OSPFv3 intra-area-prefix LSAs in this area's link-state database.";
                    }

                    ///nokia-state/state/router/ospf3/area/lsa-totals/e-intra-area-prefix-lsa
                    leaf e-intra-area-prefix-lsa {
                        type yang:gauge32;
                        description "The number of OSPFv3 E-intra-area-prefix LSAs in this area's link-state database.";
                    }

                    ///nokia-state/state/router/ospf3/area/lsa-totals/router-info-lsa
                    leaf router-info-lsa {
                        type yang:gauge32;
                        description "The number of OSPFv3 router-info LSAs in this area's link-state database.";
                    }

                    ///nokia-state/state/router/ospf3/area/lsa-totals/unknown-lsa
                    leaf unknown-lsa {
                        type yang:gauge32;
                        description "The number of unknown LSA advertisements in this area's link-state database.";
                    }

                    ///nokia-state/state/router/ospf3/area/lsa-totals/total
                    leaf total {
                        type yang:gauge32;
                        description "The number of area scope LSAs within this area.";
                    }

                    ///nokia-state/state/router/ospf3/area/lsa-totals/total-lsa-cksum-sum
                    leaf total-lsa-cksum-sum {
                        type int32;
                        description "The 32-bit unsigned sum of the area scope LSA checksums contained in this area's link-state database. The sum can be used to determine if there has been a change in a router's link-state database, and to compare the link-state database of two routers.";
                    }

                } // container lsa-totals

                ///nokia-state/state/router/ospf3/area/lsa-filter-totals
                container lsa-filter-totals {
                    description "Enter the lsa-filter-totals context";

                    ///nokia-state/state/router/ospf3/area/lsa-filter-totals/export-filtered
                    leaf export-filtered {
                        type yang:gauge32;
                        description "The number of LSAs not sent due to area export policy.";
                    }

                    ///nokia-state/state/router/ospf3/area/lsa-filter-totals/import-filtered
                    leaf import-filtered {
                        type yang:gauge32;
                        description "The number of LSAs not sent due to area import policy.";
                    }

                } // container lsa-filter-totals

                ///nokia-state/state/router/ospf3/area/interface
                list interface {
                    key "interface-name";
                    description "Enter the interface list instance";

                    ///nokia-state/state/router/ospf3/area/interface/interface-name
                    leaf interface-name {
                        type types-sros:interface-name;
                        description "Router interface name";
                    }

                    ///nokia-state/state/router/ospf3/area/interface/type
                    leaf type {
                        type enumeration {
                            enum broadcast                      { value 1; }
                            enum non-broadcast                  { value 2; }
                            enum point-to-point                 { value 3; }
                            enum secondary                      { value 6; }
                            enum p2mp-nbma                      { value 9; }
                        }
                        description "the value of type indicates the operational OSPF interface type.";
                    }

                    ///nokia-state/state/router/ospf3/area/interface/oper-state
                    leaf oper-state {
                        type enumeration {
                            enum down                           { value 1; }
                            enum loopback                       { value 2; }
                            enum waiting                        { value 3; }
                            enum point-to-point                 { value 4; }
                            enum designated-router              { value 5; }
                            enum backup-designated-router       { value 6; }
                            enum other-designated-router        { value 7; }
                        }
                        description "the OSPF interface state.";
                    }

                    ///nokia-state/state/router/ospf3/area/interface/last-enabled-time
                    leaf last-enabled-time {
                        type yang:date-and-time;
                        description "the value of last-enabled-time indicates the sys-up-time value when ospf-if-admin-stat was last set to enabled (1) to run the ospf on this interface.";
                    }

                    ///nokia-state/state/router/ospf3/area/interface/oper-mtu
                    leaf oper-mtu {
                        type int32;
                        description "the value of oper-MTU indicates the operational size of the largest packet which can be sent/received on this OSPF interface, specified in octets. this size DOES include the underlying IP header length, but not the underlying layer headers/trailers.";
                    }

                    ///nokia-state/state/router/ospf3/area/interface/oper-metric
                    leaf oper-metric {
                        type int32 {
                            range "0..65535";
                        }
                        description "the value of metric-value indicates the metric value this interface is using. the default value of the metric is (reference bandwidth / if-speed). the value of the reference bandwidth is configured by the reference-bandwidth object.";
                    }

                    ///nokia-state/state/router/ospf3/area/interface/neighbor-count
                    leaf neighbor-count {
                        type yang:gauge32;
                        description "The total number of OSPF neighbors adjacent on this interface, in a state of INIT or greater, since admin-state was last set to 'enabled'.";
                    }

                    ///nokia-state/state/router/ospf3/area/interface/dr-id
                    leaf dr-id {
                        type types-sros:ipv4-address;
                        description "the value of DR-id indicates the router ID of the designated router.";
                    }

                    ///nokia-state/state/router/ospf3/area/interface/dr-ip-address
                    leaf dr-ip-address {
                        type types-sros:ip-address-with-zone;
                        description "the IP address of the designated router.";
                    }

                    ///nokia-state/state/router/ospf3/area/interface/bdr-id
                    leaf bdr-id {
                        type types-sros:ipv4-address;
                        description "the value of BDR-id indicates the router ID of the backup designated router.";
                    }

                    ///nokia-state/state/router/ospf3/area/interface/bdr-ip-address
                    leaf bdr-ip-address {
                        type types-sros:ip-address-with-zone;
                        description "the IP address of the backup designated router.";
                    }

                    ///nokia-state/state/router/ospf3/area/interface/link-lsa-count
                    leaf link-lsa-count {
                        type yang:gauge32;
                        description "the value of link-lsa-count indicates the total number of link-scope link-state advertisements in this link's link-state database.";
                    }

                    ///nokia-state/state/router/ospf3/area/interface/link-lsa-cksum-sum
                    leaf link-lsa-cksum-sum {
                        type int32;
                        description "the value of link-lsa-cksum-sum indicates the 32-bit unsigned sum of the link-scope link-state advertisements' LS checksums contained in this link's link-state database. the sum can be used to determine if there has been a change in a router's link-state database, and to compare the link state database of two routers.";
                    }

                    ///nokia-state/state/router/ospf3/area/interface/local-ip-address
                    leaf local-ip-address {
                        type types-sros:ip-address-with-zone;
                        description "the value of local-ip-address indicates the IP address of this OSPF interface.";
                    }

                    ///nokia-state/state/router/ospf3/area/interface/te-metric
                    leaf te-metric {
                        type uint32 {
                            range "0..16777215";
                        }
                        description "the value of te-metric indicates the MPLS TE metric configured for this interface. this metric is flooded out in the TE metric sub-tlv in the OSPF TE LS-as. depending on the configuration, either the TE metric value or the native OSPF metric value is used in cspf computations.";
                    }

                    ///nokia-state/state/router/ospf3/area/interface/te-state
                    leaf te-state {
                        type types-sros:oper-state;
                        description "the value of te-state indicates the MPLS interface TE status from OSPF standpoint.";
                    }

                    ///nokia-state/state/router/ospf3/area/interface/admin-group
                    leaf admin-group {
                        type uint32;
                        description "the value of admin-group indicates the bit-map inherited from MPLS interface that identifies the admin groups to which this interface belongs. if bit 'n' is set, then the interface belongs to the admin group with value 'n'.";
                    }

                    ///nokia-state/state/router/ospf3/area/interface/events
                    leaf events {
                        type yang:counter32;
                        description "the value of events indicates the number of times this OSPF interface has changed its state, or an error has occurred.";
                    }

                    ///nokia-state/state/router/ospf3/area/interface/last-event-time
                    leaf last-event-time {
                        type yang:date-and-time;
                        description "the value of last-event-time indicates the value of sys-up-time when an event was last associated with this OSPF interface.";
                    }

                    ///nokia-state/state/router/ospf3/area/interface/ldp-sync
                    container ldp-sync {
                        description "Enter the ldp-sync context";

                        ///nokia-state/state/router/ospf3/area/interface/ldp-sync/ldp-sync-state
                        leaf ldp-sync-state {
                            type types-sros:oper-state;
                            description "the value of ldp-sync-state indicates if IGP-LDP synchronization is enabled on this interface. ldp-sync-state is derived from ldp-sync-admin-state and also whether it was enabled at the IP layer from OSPF standpoint.";
                        }

                        ///nokia-state/state/router/ospf3/area/interface/ldp-sync/ldp-sync-max-metric
                        leaf ldp-sync-max-metric {
                            type boolean;
                            description "the value of ldp-sync-max-metric indicates if OSPF advertised maximum metric value for the interface, depending on whether ldp-sync-state is enabled on this interface.";
                        }

                        ///nokia-state/state/router/ospf3/area/interface/ldp-sync/ldp-sync-timer-state
                        leaf ldp-sync-timer-state {
                            type enumeration {
                                enum wait-for-ldp-adj               { value 1; }
                                enum timer-active                   { value 2; }
                                enum ldp-exchg-done                 { value 3; }
                                enum timer-expired                  { value 4; }
                                enum manual-exit                    { value 5; }
                                enum disabled                       { value 6; }
                            }
                            description "the value of ldp-sync-timer-state indicates the state of the ldp-sync-time-left on this OSPF interface.";
                        }

                        ///nokia-state/state/router/ospf3/area/interface/ldp-sync/ldp-sync-time-left
                        leaf ldp-sync-time-left {
                            type uint32 {
                                range "0|1..1800";
                            }
                            units "seconds";
                            description "the value of ldp-sync-time-left indicates the time left before OSPF reverts back to advertising normal metric for this interface. this is applicable only when ldp-sync-max-metric is 'true'.";
                        }

                    } // container ldp-sync

                    ///nokia-state/state/router/ospf3/area/interface/state-ipv6-authentication
                    container state-ipv6-authentication {
                        description "Enter the state-ipv6-authentication context";

                        ///nokia-state/state/router/ospf3/area/interface/state-ipv6-authentication/oper-inb-sa-name
                        leaf oper-inb-sa-name {
                            type types-sros:named-item-or-empty;
                            description "the value of oper-inb-sa-name indicates the name of the operational inbound manual I-psec security association, used for authenticating inbound ospfv3 traffic.";
                        }

                        ///nokia-state/state/router/ospf3/area/interface/state-ipv6-authentication/oper-inb-sa-name-temp
                        leaf oper-inb-sa-name-temp {
                            type types-sros:named-item-or-empty;
                            description "the value of oper-inb-sa-name-temp indicates the name of a temporary operational inbound manual I-psec security association, used for authenticating inbound ospfv3 traffic. this field can only contain a value when the key-rollover mechanism is ongoing.";
                        }

                        ///nokia-state/state/router/ospf3/area/interface/state-ipv6-authentication/oper-outb-sa-name
                        leaf oper-outb-sa-name {
                            type types-sros:named-item-or-empty;
                            description "the value of oper-outb-sa-name indicates the name of the operational outbound manual I-psec security association, used for authenticating outbound ospfv3 traffic. when the key-rollover mechanism is ongoing, the value can temporarily be different from the value of the outbound-sa-name field.";
                        }

                    } // container state-ipv6-authentication

                    ///nokia-state/state/router/ospf3/area/interface/shared-sid
                    container shared-sid {
                        description "Enter the shared-sid context";

                        ///nokia-state/state/router/ospf3/area/interface/shared-sid/type
                        choice type {
                            ///nokia-state/state/router/ospf3/area/interface/shared-sid/type/label
                            case label {

                                ///nokia-state/state/router/ospf3/area/interface/shared-sid/type/label/label
                                leaf label {
                                    type int64 {
                                        range "1..4294967295";
                                    }
                                    description "Specifies IPvX node SID label for this interface.";
                                }

                            }
                            ///nokia-state/state/router/ospf3/area/interface/shared-sid/type/index
                            case index {

                                ///nokia-state/state/router/ospf3/area/interface/shared-sid/type/index/index
                                leaf index {
                                    type int64 {
                                        range "0..4294967295";
                                    }
                                    description "Specifies IPvX node SID index for this interface.";
                                }

                            }
                        }
                    } // container shared-sid

                    ///nokia-state/state/router/ospf3/area/interface/packets
                    container packets {
                        description "Enter the packets context";

                        ///nokia-state/state/router/ospf3/area/interface/packets/tx-total
                        leaf tx-total {
                            type yang:counter32;
                            description "The total number of OSPF packets transmitted since admin-state was last set to 'enabled'.";
                        }

                        ///nokia-state/state/router/ospf3/area/interface/packets/tx-hello
                        leaf tx-hello {
                            type yang:counter32;
                            description "The total number of OSPF hello packets transmitted since admin-state was last set to 'enabled'.";
                        }

                        ///nokia-state/state/router/ospf3/area/interface/packets/tx-db-description
                        leaf tx-db-description {
                            type yang:counter32;
                            description "The total number of OSPF database description packets transmitted since admin-state was last set to 'enabled'.";
                        }

                        ///nokia-state/state/router/ospf3/area/interface/packets/tx-ls-request
                        leaf tx-ls-request {
                            type yang:counter32;
                            description "The total number of OSPF link state requests (LS-rs)transmitted since admin-state was last set to 'enabled'.";
                        }

                        ///nokia-state/state/router/ospf3/area/interface/packets/tx-ls-update
                        leaf tx-ls-update {
                            type yang:counter32;
                            description "The total number of OSPF link state updates (LS-us) transmitted since admin-state was last set to 'enabled'.";
                        }

                        ///nokia-state/state/router/ospf3/area/interface/packets/tx-ls-ack
                        leaf tx-ls-ack {
                            type yang:counter32;
                            description "The total number of OSPF link state acknowledgements transmitted since admin-state was last set to 'enabled'.";
                        }

                        ///nokia-state/state/router/ospf3/area/interface/packets/rx-total
                        leaf rx-total {
                            type yang:counter32;
                            description "The total number of OSPF packets received since admin-state was last set to 'enabled'.";
                        }

                        ///nokia-state/state/router/ospf3/area/interface/packets/rx-hello
                        leaf rx-hello {
                            type yang:counter32;
                            description "The total number of OSPF hello packets received since admin-state was last set to 'enabled'.";
                        }

                        ///nokia-state/state/router/ospf3/area/interface/packets/rx-db-description
                        leaf rx-db-description {
                            type yang:counter32;
                            description "The total number of OSPF database description packets received since admin-state was last set to 'enabled'.";
                        }

                        ///nokia-state/state/router/ospf3/area/interface/packets/rx-ls-request
                        leaf rx-ls-request {
                            type yang:counter32;
                            description "The total number of link state requests (LS-rs) received since admin-state was last set to 'enabled'.";
                        }

                        ///nokia-state/state/router/ospf3/area/interface/packets/rx-ls-update
                        leaf rx-ls-update {
                            type yang:counter32;
                            description "The total number of link state updates (LS-us) received since admin-state was last set to 'enabled'.";
                        }

                        ///nokia-state/state/router/ospf3/area/interface/packets/rx-ls-ack
                        leaf rx-ls-ack {
                            type yang:counter32;
                            description "The total number of link state acknowledgements received since admin-state was last set to 'enabled'.";
                        }

                        ///nokia-state/state/router/ospf3/area/interface/packets/discarded
                        leaf discarded {
                            type yang:counter32;
                            description "The total number of OSPF packets discarded since admin-state was last set to 'enabled'.";
                        }

                        ///nokia-state/state/router/ospf3/area/interface/packets/retransmits
                        leaf retransmits {
                            type yang:counter32;
                            description "The total number of OSPF retransmits since admin-state was last set to 'enabled'.";
                        }

                        ///nokia-state/state/router/ospf3/area/interface/packets/tx-failures
                        leaf tx-failures {
                            type yang:counter32;
                            description "The total number of OSPF transmit failures since admin-state was last set to 'enabled'.";
                        }

                        ///nokia-state/state/router/ospf3/area/interface/packets/bad-version
                        leaf bad-version {
                            type yang:counter32;
                            description "The total number of OSPF packets received with bad OSPF version numbers since admin-state was last set to 'enabled'.";
                        }

                        ///nokia-state/state/router/ospf3/area/interface/packets/bad-network
                        leaf bad-network {
                            type yang:counter32;
                            description "The total number of OSPF packets received with invalid network or mask since admin-state was last set to 'enabled'.";
                        }

                        ///nokia-state/state/router/ospf3/area/interface/packets/bad-area
                        leaf bad-area {
                            type yang:counter32;
                            description "The total number of OSPF packets received with an area mismatch since admin-state was last set to 'enabled'.";
                        }

                        ///nokia-state/state/router/ospf3/area/interface/packets/bad-dest-address
                        leaf bad-dest-address {
                            type yang:counter32;
                            description "The total number of OSPF packets received with the incorrect IP destination address since admin-state was last set to 'enabled'.";
                        }

                        ///nokia-state/state/router/ospf3/area/interface/packets/bad-neighbors
                        leaf bad-neighbors {
                            type yang:counter32;
                            description "The total number of OSPF packets received where the neighbor information does not match the information this router has for the neighbor since admin-state was last set to 'enabled'.";
                        }

                        ///nokia-state/state/router/ospf3/area/interface/packets/bad-packet-type
                        leaf bad-packet-type {
                            type yang:counter32;
                            description "The total number of OSPF packets received with an invalid OSPF packet type since admin-state was last set to 'enabled'.";
                        }

                        ///nokia-state/state/router/ospf3/area/interface/packets/bad-length
                        leaf bad-length {
                            type yang:counter32;
                            description "The total number of OSPF packets received with a total length not equal to the length given in the packet itself since admin-state was last set to 'enabled'.";
                        }

                        ///nokia-state/state/router/ospf3/area/interface/packets/bad-hello-interval
                        leaf bad-hello-interval {
                            type yang:counter32;
                            description "the value of bad-hello-intervals indicates the total number of OSPF packets received where the hello interval given in packet was not equal to that configured on this interface since admin-state was last set to 'enabled'.";
                        }

                        ///nokia-state/state/router/ospf3/area/interface/packets/bad-dead-interval
                        leaf bad-dead-interval {
                            type yang:counter32;
                            description "The total number of OSPF packets received where the dead interval given in the packet was not equal to that configured on this interface since admin-state was last set to 'enabled'.";
                        }

                        ///nokia-state/state/router/ospf3/area/interface/packets/bad-options
                        leaf bad-options {
                            type yang:counter32;
                            description "The total number of OSPF packets received with an option that does not match those configured for this interface or area since admin-state was last set to 'enabled'.";
                        }

                        ///nokia-state/state/router/ospf3/area/interface/packets/rx-bad-checksum
                        leaf rx-bad-checksum {
                            type yang:counter32;
                            description "The count of LS-as received with bad checksums.";
                        }

                        ///nokia-state/state/router/ospf3/area/interface/packets/bad-auth-type
                        leaf bad-auth-type {
                            type yang:counter32;
                            description "The total number of OSPF packets received with an invalid authorization type since admin-state was last set to 'enabled'.";
                        }

                        ///nokia-state/state/router/ospf3/area/interface/packets/auth-failures
                        leaf auth-failures {
                            type yang:counter32;
                            description "The total number of OSPF packets received with an invalid authorization key since admin-state was last set to 'enabled'.";
                        }

                        ///nokia-state/state/router/ospf3/area/interface/packets/bad-virtual-link
                        leaf bad-virtual-link {
                            type yang:counter32;
                            description "The total number of OSPF packets received that are destined to a virtual link that does not exist since admin-state was last set to 'enabled'.";
                        }

                    } // container packets

                    ///nokia-state/state/router/ospf3/area/interface/last-packet-drop
                    container last-packet-drop {
                        description "Enter the last-packet-drop context";

                        ///nokia-state/state/router/ospf3/area/interface/last-packet-drop/reason
                        leaf reason {
                            type types-ospf:packet-drop-reason;
                            description "The reason for dropping the packet.";
                        }

                        ///nokia-state/state/router/ospf3/area/interface/last-packet-drop/packet-type
                        leaf packet-type {
                            type uint8;
                            description "the OSPF packet type of the dropped packet from the packet header.";
                        }

                        ///nokia-state/state/router/ospf3/area/interface/last-packet-drop/router-id
                        leaf router-id {
                            type types-sros:ipv4-address;
                            description "the OSPF router ID of the dropped packet from the packet header.";
                        }

                        ///nokia-state/state/router/ospf3/area/interface/last-packet-drop/area-id
                        leaf area-id {
                            type types-sros:ipv4-address;
                            description "the OSPF area ID of the dropped packet from the packet header.";
                        }

                        ///nokia-state/state/router/ospf3/area/interface/last-packet-drop/checksum
                        leaf checksum {
                            type uint32;
                            description "the OSPF checksum of the dropped packet from the packet header.";
                        }

                        ///nokia-state/state/router/ospf3/area/interface/last-packet-drop/drop-time
                        leaf drop-time {
                            type yang:date-and-time;
                            description "the time when the drop occured.";
                        }

                    } // container last-packet-drop

                    ///nokia-state/state/router/ospf3/area/interface/neighbor
                    list neighbor {
                        key "address";
                        description "Add a list entry for neighbor";

                        ///nokia-state/state/router/ospf3/area/interface/neighbor/address
                        leaf address {
                            type types-sros:ip-address;
                            description "Neighbor link local address";
                        }

                        ///nokia-state/state/router/ospf3/area/interface/neighbor/priority
                        leaf priority {
                            type int32 {
                                range "0..255";
                            }
                            description
                                "Specifies the priority of this neighbor in the designated router election algorithm.

                                 The value 0 signifies that the neighbor is not eligible to become
                                 the designated router on this particular network.";
                        }

                        ///nokia-state/state/router/ospf3/area/interface/neighbor/router-id
                        leaf router-id {
                            type types-sros:ipv4-address;
                            description
                                "Indicates a 32-bit integer uniquely identifying the neighboring router in the Autonomous System.

                                 A value of 0 is returned until a Hello is received from the configured neighbor.";
                        }

                        ///nokia-state/state/router/ospf3/area/interface/neighbor/oper-state
                        leaf oper-state {
                            type types-ospf:neighbor-oper-state-type;
                            description "Indicates the State of the relationship with this Neighbor.";
                        }

                    } // list neighbor

                    ///nokia-state/state/router/ospf3/area/interface/neighbor-state
                    list neighbor-state {
                        key "router-id";
                        description "Enter the neighbor-state list instance";

                        ///nokia-state/state/router/ospf3/area/interface/neighbor-state/router-id
                        leaf router-id {
                            type types-sros:ipv4-address;
                            description "Router ID of the neighbor.";
                        }

                        ///nokia-state/state/router/ospf3/area/interface/neighbor-state/address
                        leaf address {
                            type types-sros:ip-address-with-zone;
                            description "the value of address indicates the IP address of the neighbor associated with the local link.";
                        }

                        ///nokia-state/state/router/ospf3/area/interface/neighbor-state/priority
                        leaf priority {
                            type int32 {
                                range "0..255";
                            }
                            description
                                "Specifies the priority of this neighbor in the designated router election algorithm.

                                 The value 0 signifies that the neighbor is not eligible to become
                                 the designated router on this particular network.";
                        }

                        ///nokia-state/state/router/ospf3/area/interface/neighbor-state/bfd-tracking
                        leaf bfd-tracking {
                            type boolean;
                            description "the value of bfd-tracking indicates whether a BFD session is being maintained to track the forwarding path to this neighbor or not.";
                        }

                        ///nokia-state/state/router/ospf3/area/interface/neighbor-state/dr-id
                        leaf dr-id {
                            type types-sros:ipv4-address;
                            description "the value of dr-id indicates the DR value advertised in the HELLO packets received from the OSPF neighbor. if it is not a broadcast interface dr-id will be zero.";
                        }

                        ///nokia-state/state/router/ospf3/area/interface/neighbor-state/bdr-id
                        leaf bdr-id {
                            type types-sros:ipv4-address;
                            description "the value of bdr-id indicates the BDR value advertised in the HELLO packets received from the OSPF neighbor. if it is not a broadcast interface bdr-id will be zero.";
                        }

                        ///nokia-state/state/router/ospf3/area/interface/neighbor-state/bfd-strict-state
                        leaf bfd-strict-state {
                            type enumeration {
                                enum disabled                       { value 0; }
                                enum up                             { value 1; }
                                enum blocked                        { value 2; }
                                enum held                           { value 3; }
                            }
                            description "the value of bfd-strict-state indicates the state of the strict-bfd session";
                        }

                        ///nokia-state/state/router/ospf3/area/interface/neighbor-state/group-if-index
                        leaf group-if-index {
                            type int32 {
                                range "1..2147483647";
                            }
                            description "The value of group-if-index indicates the interface ID of the group interface over which the neighbor can be reached.";
                        }

                        ///nokia-state/state/router/ospf3/area/interface/neighbor-state/group-if-oper-mtu
                        leaf group-if-oper-mtu {
                            type int32;
                            description "The value of group-if-oper-mtu indicates the operational size of the largest packet which can be sent/received on the neighbor's group interface, specified in octets. this size DOES include the underlying IP header length, but not the underlying layer headers/trailers.";
                        }

                        ///nokia-state/state/router/ospf3/area/interface/neighbor-state/oper-state
                        leaf oper-state {
                            type enumeration {
                                enum down                           { value 1; }
                                enum attempt                        { value 2; }
                                enum init                           { value 3; }
                                enum two-way                        { value 4; }
                                enum exchange-start                 { value 5; }
                                enum exchange                       { value 6; }
                                enum loading                        { value 7; }
                                enum full                           { value 8; }
                            }
                            description "Indicates the State of the relationship with this Neighbor.";
                        }

                        ///nokia-state/state/router/ospf3/area/interface/neighbor-state/options
                        leaf options {
                            type int32;
                            description "the value of options indicates a bit mask corresponding to the neighbor's options field.";
                        }

                        ///nokia-state/state/router/ospf3/area/interface/neighbor-state/hello-suppressed
                        leaf hello-suppressed {
                            type boolean;
                            description "the value of hello-suppressed indicates whether hellos are being suppressed to the neighbor.";
                        }

                        ///nokia-state/state/router/ospf3/area/interface/neighbor-state/if-id
                        leaf if-id {
                            type int32 {
                                range "0..2147483647";
                            }
                            description "the value of if-id indicates the interface ID that the neighbor advertises in its hello packets on this link, that is, the neighbor's local interface index.";
                        }

                        ///nokia-state/state/router/ospf3/area/interface/neighbor-state/restart-helper-status
                        leaf restart-helper-status {
                            type enumeration {
                                enum not-helping                    { value 1; }
                                enum helping                        { value 2; }
                            }
                            description "the value of restart-helper-status indicates whether the router is acting as a graceful restart helper for the neighbor.";
                        }

                        ///nokia-state/state/router/ospf3/area/interface/neighbor-state/restart-helper-age
                        leaf restart-helper-age {
                            type int32 {
                                range "0..1800";
                            }
                            units "seconds";
                            description "the value of restart-helper-age indicates the remaining time in the current OSPF graceful restart interval, if the router is acting as a restart helper for the neighbor.";
                        }

                        ///nokia-state/state/router/ospf3/area/interface/neighbor-state/restart-helper-exit-rc
                        leaf restart-helper-exit-rc {
                            type enumeration {
                                enum none                           { value 1; }
                                enum in-progress                    { value 2; }
                                enum completed                      { value 3; }
                                enum timed-out                      { value 4; }
                                enum topology-changed               { value 5; }
                                enum bfd-down                       { value 6; }
                            }
                            description "the value of restart-helper-exit-rc indicates the outcome of the last attempt at acting as a graceful restart helper for the neighbor. none no restart has yet been attempted. in-progress A restart attempt is currently underway. completed the last restart completed successfully. timed-out the last restart timed out. topology-changed the last restart was aborted due to a topology change.";
                        }

                        ///nokia-state/state/router/ospf3/area/interface/neighbor-state/last-restart-time
                        leaf last-restart-time {
                            type yang:date-and-time;
                            description "the value of last-restart-time indicates the last time the neighbor attempted restart.";
                        }

                        ///nokia-state/state/router/ospf3/area/interface/neighbor-state/restart-reason
                        leaf restart-reason {
                            type types-ospf:restart-reason-type;
                            description "the value of restart-reason indicates the OSPF neighbor's graceful restart reason.";
                        }

                        ///nokia-state/state/router/ospf3/area/interface/neighbor-state/up-time
                        leaf up-time {
                            type int32 {
                                range "0..2147483647";
                            }
                            units "centiseconds";
                            description "the value of up-time indicates the uninterrupted time, in hundredths of seconds, the adjacency to this neighbour has been up.";
                        }

                        ///nokia-state/state/router/ospf3/area/interface/neighbor-state/last-event
                        leaf last-event {
                            type types-ospf:neighbor-event;
                            description "Indicates the last event as defined in RFC causing an oper-state change for this Neighbor.";
                        }

                        ///nokia-state/state/router/ospf3/area/interface/neighbor-state/last-event-time
                        leaf last-event-time {
                            type yang:date-and-time;
                            description "the value of last-event-time indicates the value of sys-up-time when the last event occurred that affected the adjacency to the neighbour.";
                        }

                        ///nokia-state/state/router/ospf3/area/interface/neighbor-state/dead-time-outstanding
                        leaf dead-time-outstanding {
                            type uint32 {
                                range "0..2147483647";
                            }
                            units "seconds";
                            description "the value of dead-time-outstanding indicates the amount of time in seconds until the dead-router interval expires. normally, this value should not be significantly smaller than the configured dead router interval minus one hello interval.";
                        }

                        ///nokia-state/state/router/ospf3/area/interface/neighbor-state/statistics
                        container statistics {
                            description "Enter the statistics context";

                            ///nokia-state/state/router/ospf3/area/interface/neighbor-state/statistics/events
                            leaf events {
                                type yang:counter32;
                                description "the value of events indicates the number of times this neighbor relationship has changed state, or an error has occurred.";
                            }

                            ///nokia-state/state/router/ospf3/area/interface/neighbor-state/statistics/ls-retrans-q-len
                            leaf ls-retrans-q-len {
                                type yang:gauge32;
                                description "the value of ls-retrans-Q-len indicates the current length of the retransmission queue.";
                            }

                            ///nokia-state/state/router/ospf3/area/interface/neighbor-state/statistics/bad-nbr-states
                            leaf bad-nbr-states {
                                type yang:counter32;
                                description "the value of bad-nbr-states indicates the total number of OSPF packets received when the neighbor state was not expecting to receive this packet type since admin-state was last set to 'enabled'.";
                            }

                            ///nokia-state/state/router/ospf3/area/interface/neighbor-state/statistics/lsa-install-failed
                            leaf lsa-install-failed {
                                type yang:counter32;
                                description "the value of lsa-install-failed indicates the total number of times an LSA could not be installed into the LSDB due to a resource allocation issue since admin-state was last set to 'enabled'.";
                            }

                            ///nokia-state/state/router/ospf3/area/interface/neighbor-state/statistics/bad-seq-nums
                            leaf bad-seq-nums {
                                type yang:counter32;
                                description "the value of bad-seq-nums indicates the total number of times when a database description packet was received with a sequence number mismatch since admin-state was last set to 'enabled'.";
                            }

                            ///nokia-state/state/router/ospf3/area/interface/neighbor-state/statistics/bad-mtu
                            leaf bad-mtu {
                                type yang:counter32;
                                description "the value of bad-MT-us indicates the total number of times when the MTU in a received database description packet was larger than the MTU of the receiving interface since admin-state was last set to 'enabled'.";
                            }

                            ///nokia-state/state/router/ospf3/area/interface/neighbor-state/statistics/bad-packets
                            leaf bad-packets {
                                type yang:counter32;
                                description "the value of bad-packets indicates the total number of times when an LS update was received with an illegal LS type or an option mismatch since admin-state was last set to 'enabled'.";
                            }

                            ///nokia-state/state/router/ospf3/area/interface/neighbor-state/statistics/lsa-not-in-lsdbs
                            leaf lsa-not-in-lsdbs {
                                type yang:counter32;
                                description "the value of lsa-not-in-lsdbs indicates the total number of times when an LS request was received for an LSA not installed in the LSDB of this router since admin-state was last set to 'enabled'.";
                            }

                            ///nokia-state/state/router/ospf3/area/interface/neighbor-state/statistics/option-mismatches
                            leaf option-mismatches {
                                type yang:counter32;
                                description "the value of option-mismatches indicates the total number of times when a LS update was received with an option mismatch since admin-state was last set to 'enabled'.";
                            }

                            ///nokia-state/state/router/ospf3/area/interface/neighbor-state/statistics/duplicates
                            leaf duplicates {
                                type yang:counter32;
                                description "the value of duplicates indicates the total number of times when a duplicate database description packet was received during the exchange state since admin-state was last set to 'enabled'.";
                            }

                            ///nokia-state/state/router/ospf3/area/interface/neighbor-state/statistics/num-restarts
                            leaf num-restarts {
                                type yang:counter32;
                                description "the value of num-restarts indicates the number of times the neighbor has attempted restart.";
                            }

                        } // container statistics

                        ///nokia-state/state/router/ospf3/area/interface/neighbor-state/sr-adjacency
                        container sr-adjacency {
                            description "Enter the sr-adjacency context";

                            ///nokia-state/state/router/ospf3/area/interface/neighbor-state/sr-adjacency/sid-type
                            leaf sid-type {
                                type enumeration {
                                    enum none                           { value 0; }
                                    enum index                          { value 1; }
                                    enum mpls-label                     { value 2; }
                                }
                                description "the value of sid-type indicates how the value of sid-value shall be interpreted.";
                            }

                            ///nokia-state/state/router/ospf3/area/interface/neighbor-state/sr-adjacency/sid-value
                            leaf sid-value {
                                type uint32;
                                description "the value of the object sid-value indicates the IPv4 SID label or index for this adjacency.";
                            }

                            ///nokia-state/state/router/ospf3/area/interface/neighbor-state/sr-adjacency/sid-protected
                            leaf sid-protected {
                                type boolean;
                                description "The value of the object sid-protected indicates the if the SID for this adjacency is eligible for protection.";
                            }

                            ///nokia-state/state/router/ospf3/area/interface/neighbor-state/sr-adjacency/secondary-sid-type
                            leaf secondary-sid-type {
                                type enumeration {
                                    enum none                           { value 0; }
                                    enum index                          { value 1; }
                                    enum mpls-label                     { value 2; }
                                }
                                description "the value of secondary-sid-type indicates how the value of secondary-sid-value shall be interpreted.";
                            }

                            ///nokia-state/state/router/ospf3/area/interface/neighbor-state/sr-adjacency/secondary-sid-value
                            leaf secondary-sid-value {
                                type uint32;
                                description "the value of the object sid-value indicates the secondary SID label or index for this adjacency.";
                            }

                            ///nokia-state/state/router/ospf3/area/interface/neighbor-state/sr-adjacency/secondary-sid-protected
                            leaf secondary-sid-protected {
                                type boolean;
                                description "The value of the object secondary-sid-protected indicates the if the secondary SID for this adjacency is eligible for protection.";
                            }

                            ///nokia-state/state/router/ospf3/area/interface/neighbor-state/sr-adjacency/secondary-sid-mtu
                            leaf secondary-sid-mtu {
                                type uint32;
                                description "The MTU of the link used by this adjacency using the secondary sid.";
                            }

                            ///nokia-state/state/router/ospf3/area/interface/neighbor-state/sr-adjacency/sid-hold-timer
                            leaf sid-hold-timer {
                                type int32 {
                                    range "0..65535";
                                }
                                units "seconds";
                                description "The remaining holding time for this adjacency-sid.";
                            }

                            ///nokia-state/state/router/ospf3/area/interface/neighbor-state/sr-adjacency/pgid
                            leaf pgid {
                                type uint32;
                                description "The value indicates the PGID for this adjacency.";
                            }

                            ///nokia-state/state/router/ospf3/area/interface/neighbor-state/sr-adjacency/mtu
                            leaf mtu {
                                type uint32;
                                description "The MTU of the link used by this adjacency.";
                            }

                            ///nokia-state/state/router/ospf3/area/interface/neighbor-state/sr-adjacency/lfa-nexthop
                            leaf lfa-nexthop {
                                type types-sros:ip-address;
                                description "The IP address associated with the LFA nexthop.";
                            }

                            ///nokia-state/state/router/ospf3/area/interface/neighbor-state/sr-adjacency/lfa-interface
                            leaf lfa-interface {
                                type types-sros:interface-name;
                                description "The value specifies the interface index of the outgoing interface for the adjacency backup.";
                            }

                            ///nokia-state/state/router/ospf3/area/interface/neighbor-state/sr-adjacency/lfa-tunnel-type
                            leaf lfa-tunnel-type {
                                type enumeration {
                                    enum none                           { value 0; }
                                    enum rsvp                           { value 1; }
                                    enum ldp                            { value 2; }
                                }
                                description "Type of tunnel used for LFA";
                            }

                            ///nokia-state/state/router/ospf3/area/interface/neighbor-state/sr-adjacency/lfa-tunnel-id
                            leaf lfa-tunnel-id {
                                type types-sros:tunnel-id;
                            }

                            ///nokia-state/state/router/ospf3/area/interface/neighbor-state/sr-adjacency/lfa-label-stack
                            list lfa-label-stack {
                                key "label-index";
                                description "Enter the lfa-label-stack list instance";

                                ///nokia-state/state/router/ospf3/area/interface/neighbor-state/sr-adjacency/lfa-label-stack/label-index
                                leaf label-index {
                                    type uint32;
                                    description
                                        "An adjacency can have a backup label stack.
                                         Label-index 0 indicates the first label which can be a destination
                                         node-sid , a node-sid towards a P or PQ node or an adj-sid to a
                                         Q node. The last label always indicates the destination label
                                         unless PHP is enabled.";
                                }

                                ///nokia-state/state/router/ospf3/area/interface/neighbor-state/sr-adjacency/lfa-label-stack/label
                                leaf label {
                                    type uint32;
                                    description
                                        "A label from an adjacency backup. The label can be a destination
                                         node-sid, an adj-sid or a node-sid towards a P or PQ node.";
                                }

                            } // list lfa-label-stack

                        } // container sr-adjacency

                    } // list neighbor-state

                    ///nokia-state/state/router/ospf3/area/interface/linkstate-database
                    list linkstate-database {
                        key "ls-type adv-rtr-id ls-id";
                        description "Enter the linkstate-database list instance";

                        ///nokia-state/state/router/ospf3/area/interface/linkstate-database/ls-type
                        leaf ls-type {
                            type uint32;
                            description "Link state type.";
                        }

                        ///nokia-state/state/router/ospf3/area/interface/linkstate-database/adv-rtr-id
                        leaf adv-rtr-id {
                            type types-sros:ipv4-address;
                            description "Router that originated the link state advertisement.";
                        }

                        ///nokia-state/state/router/ospf3/area/interface/linkstate-database/ls-id
                        leaf ls-id {
                            type types-sros:ipv4-address;
                            description "Link state advertisement identity.";
                        }

                        ///nokia-state/state/router/ospf3/area/interface/linkstate-database/sequence-nr
                        leaf sequence-nr {
                            type uint32;
                        }

                        ///nokia-state/state/router/ospf3/area/interface/linkstate-database/age
                        leaf age {
                            type int32;
                        }

                        ///nokia-state/state/router/ospf3/area/interface/linkstate-database/checksum
                        leaf checksum {
                            type uint32;
                        }

                        ///nokia-state/state/router/ospf3/area/interface/linkstate-database/known-type
                        leaf known-type {
                            type boolean;
                        }

                        ///nokia-state/state/router/ospf3/area/interface/linkstate-database/advertisement
                        leaf advertisement {
                            type string {
                                length "1..9778";
                            }
                            description "Contents of the link state advertisement.";
                        }

                    } // list linkstate-database

                    ///nokia-state/state/router/ospf3/area/interface/capabilities
                    list capabilities {
                        key "ls-type adv-rtr-id ls-id";
                        description "Enter the capabilities list instance";

                        ///nokia-state/state/router/ospf3/area/interface/capabilities/ls-type
                        leaf ls-type {
                            type uint32;
                            description "Link state type.";
                        }

                        ///nokia-state/state/router/ospf3/area/interface/capabilities/adv-rtr-id
                        leaf adv-rtr-id {
                            type types-sros:ipv4-address;
                            description "Router that originated the link state advertisement.";
                        }

                        ///nokia-state/state/router/ospf3/area/interface/capabilities/ls-id
                        leaf ls-id {
                            type types-sros:ipv4-address;
                            description "Link state advertisement identity.";
                        }

                        ///nokia-state/state/router/ospf3/area/interface/capabilities/sequence-nr
                        leaf sequence-nr {
                            type uint32;
                        }

                        ///nokia-state/state/router/ospf3/area/interface/capabilities/age
                        leaf age {
                            type int32;
                        }

                        ///nokia-state/state/router/ospf3/area/interface/capabilities/checksum
                        leaf checksum {
                            type uint32;
                        }

                        ///nokia-state/state/router/ospf3/area/interface/capabilities/advertisement
                        leaf advertisement {
                            type string {
                                length "1..9778";
                            }
                            description "Contents of the link state advertisement.";
                        }

                    } // list capabilities

                } // list interface

                ///nokia-state/state/router/ospf3/area/virtual-link
                list virtual-link {
                    key "router-id transit-area";
                    description "Enter the virtual-link list instance";

                    ///nokia-state/state/router/ospf3/area/virtual-link/router-id
                    leaf router-id {
                        type types-sros:ipv4-address;
                        description "Router ID of the virtual link neighbor";
                    }

                    ///nokia-state/state/router/ospf3/area/virtual-link/transit-area
                    leaf transit-area {
                        type leafref {
                            path "../../../area/area-id";
                        }
                        description "Transit area linking backbone and non-connected area";
                    }

                    ///nokia-state/state/router/ospf3/area/virtual-link/oper-state
                    leaf oper-state {
                        type enumeration {
                            enum down                           { value 1; }
                            enum point-to-point                 { value 4; }
                        }
                        description "the value of state indicates the operational state of this virtual interface.";
                    }

                    ///nokia-state/state/router/ospf3/area/virtual-link/last-enabled-time
                    leaf last-enabled-time {
                        type yang:date-and-time;
                        description "the value of last-enabled-time indicates the sys-up-time value when this entry row entry was enabled.";
                    }

                    ///nokia-state/state/router/ospf3/area/virtual-link/cost
                    leaf cost {
                        type int32 {
                            range "0..65535";
                        }
                        description "the value of cost indicates the OSPF virtual interface cost represents the cost to traverse the transit area to the adjacent router. if multiple routes are available the lowest cost link will be used to maintain the adjacency and route traffic across the transit area.";
                    }

                    ///nokia-state/state/router/ospf3/area/virtual-link/link-lsa-count
                    leaf link-lsa-count {
                        type yang:gauge32;
                        description "the value of link-lsa-count indicates the total number of link-scope link-state advertisements in this virtual link's link-state database.";
                    }

                    ///nokia-state/state/router/ospf3/area/virtual-link/link-lsa-cksum-sum
                    leaf link-lsa-cksum-sum {
                        type int32;
                        description "the value of link-lsa-cksum-sum indicates the 32-bit unsigned sum of the link-scope link-state advertisements' LS checksums contained in this virtual link's link-state database. the sum can be used to determine if there has been a change in a router's link-state database, and to compare the link-state database of two routers.";
                    }

                    ///nokia-state/state/router/ospf3/area/virtual-link/link-unk-lsa-count
                    leaf link-unk-lsa-count {
                        type yang:gauge32;
                        description "the value of link-unk-lsa-count indicates the total number of unknown link-scope link-state advertisements in this virtual link's link-state database.";
                    }

                    ///nokia-state/state/router/ospf3/area/virtual-link/link-unk-lsa-cksum-sum
                    leaf link-unk-lsa-cksum-sum {
                        type int32;
                        description "the value of link-unk-lsa-cksum-sum indicates the 32-bit unsigned sum of the unknown link-scope link-state advertisements' LS checksums contained in this virtual link's link-state database. the sum can be used to determine if there has been a change in a router's link state database, and to compare the link-state database of two routers.";
                    }

                    ///nokia-state/state/router/ospf3/area/virtual-link/local-ip-address
                    leaf local-ip-address {
                        type types-sros:ip-address;
                        description "the value of local-ip-address indicates the IP address of the local egress interface that is used to maintain the adjacency to reach this virtual neighbor.";
                    }

                    ///nokia-state/state/router/ospf3/area/virtual-link/events
                    leaf events {
                        type yang:counter32;
                        description "the value of events indicates the number of times this OSPF interface has changed its state, or an error has occurred.";
                    }

                    ///nokia-state/state/router/ospf3/area/virtual-link/last-event-time
                    leaf last-event-time {
                        type yang:date-and-time;
                        description "the value of last-event-time indicates the value of sys-up-time when an event was last associated with this OSPF interface.";
                    }

                    ///nokia-state/state/router/ospf3/area/virtual-link/state-ipv6-authentication
                    container state-ipv6-authentication {
                        description "Enter the state-ipv6-authentication context";

                        ///nokia-state/state/router/ospf3/area/virtual-link/state-ipv6-authentication/oper-inb-sa-name
                        leaf oper-inb-sa-name {
                            type types-sros:named-item-or-empty;
                            description "the value of oper-inb-sa-name indicates the name of the operational inbound manual I-psec security association, used for authenticating inbound ospfv3 traffic.";
                        }

                        ///nokia-state/state/router/ospf3/area/virtual-link/state-ipv6-authentication/oper-inb-sa-name-temp
                        leaf oper-inb-sa-name-temp {
                            type types-sros:named-item-or-empty;
                            description "the value of oper-inb-sa-name-temp indicates the name of a temporary operational inbound manual I-psec security association, used for authenticating inbound ospfv3 traffic. this field can only contain a value when the key-rollover mechanism is ongoing.";
                        }

                        ///nokia-state/state/router/ospf3/area/virtual-link/state-ipv6-authentication/oper-outb-sa-name
                        leaf oper-outb-sa-name {
                            type types-sros:named-item-or-empty;
                            description "the value of oper-outb-sa-name indicates the name of the operational outbound manual I-psec security association, used for authenticating outbound ospfv3 traffic. when the key-rollover mechanism is ongoing, the value can temporarily be different from the value of the outbound-sa-name field.";
                        }

                    } // container state-ipv6-authentication

                    ///nokia-state/state/router/ospf3/area/virtual-link/packets
                    container packets {
                        description "Enter the packets context";

                        ///nokia-state/state/router/ospf3/area/virtual-link/packets/tx-total
                        leaf tx-total {
                            type yang:counter32;
                            description "The total number of OSPF packets transmitted since admin-state was last set to 'enabled'.";
                        }

                        ///nokia-state/state/router/ospf3/area/virtual-link/packets/tx-hello
                        leaf tx-hello {
                            type yang:counter32;
                            description "The total number of OSPF hello packets transmitted since admin-state was last set to 'enabled'.";
                        }

                        ///nokia-state/state/router/ospf3/area/virtual-link/packets/tx-db-description
                        leaf tx-db-description {
                            type yang:counter32;
                            description "The total number of OSPF database description packets transmitted since admin-state was last set to 'enabled'.";
                        }

                        ///nokia-state/state/router/ospf3/area/virtual-link/packets/tx-ls-request
                        leaf tx-ls-request {
                            type yang:counter32;
                            description "The total number of OSPF link state requests (LS-rs)transmitted since admin-state was last set to 'enabled'.";
                        }

                        ///nokia-state/state/router/ospf3/area/virtual-link/packets/tx-ls-update
                        leaf tx-ls-update {
                            type yang:counter32;
                            description "The total number of OSPF link state updates (LS-us) transmitted since admin-state was last set to 'enabled'.";
                        }

                        ///nokia-state/state/router/ospf3/area/virtual-link/packets/tx-ls-ack
                        leaf tx-ls-ack {
                            type yang:counter32;
                            description "The total number of OSPF link state acknowledgements transmitted since admin-state was last set to 'enabled'.";
                        }

                        ///nokia-state/state/router/ospf3/area/virtual-link/packets/rx-total
                        leaf rx-total {
                            type yang:counter32;
                            description "The total number of OSPF packets received since admin-state was last set to 'enabled'.";
                        }

                        ///nokia-state/state/router/ospf3/area/virtual-link/packets/rx-hello
                        leaf rx-hello {
                            type yang:counter32;
                            description "The total number of OSPF hello packets received since admin-state was last set to 'enabled'.";
                        }

                        ///nokia-state/state/router/ospf3/area/virtual-link/packets/rx-db-description
                        leaf rx-db-description {
                            type yang:counter32;
                            description "The total number of OSPF database description packets received since admin-state was last set to 'enabled'.";
                        }

                        ///nokia-state/state/router/ospf3/area/virtual-link/packets/rx-ls-request
                        leaf rx-ls-request {
                            type yang:counter32;
                            description "The total number of link state requests (LS-rs) received since admin-state was last set to 'enabled'.";
                        }

                        ///nokia-state/state/router/ospf3/area/virtual-link/packets/rx-ls-update
                        leaf rx-ls-update {
                            type yang:counter32;
                            description "The total number of link state updates (LS-us) received since admin-state was last set to 'enabled'.";
                        }

                        ///nokia-state/state/router/ospf3/area/virtual-link/packets/rx-ls-ack
                        leaf rx-ls-ack {
                            type yang:counter32;
                            description "The total number of link state acknowledgements received since admin-state was last set to 'enabled'.";
                        }

                        ///nokia-state/state/router/ospf3/area/virtual-link/packets/discarded
                        leaf discarded {
                            type yang:counter32;
                            description "The total number of OSPF packets discarded since admin-state was last set to 'enabled'.";
                        }

                        ///nokia-state/state/router/ospf3/area/virtual-link/packets/retransmits
                        leaf retransmits {
                            type yang:counter32;
                            description "The total number of OSPF retransmits since admin-state was last set to 'enabled'.";
                        }

                        ///nokia-state/state/router/ospf3/area/virtual-link/packets/tx-failures
                        leaf tx-failures {
                            type yang:counter32;
                            description "The total number of OSPF transmit failures since admin-state was last set to 'enabled'.";
                        }

                        ///nokia-state/state/router/ospf3/area/virtual-link/packets/bad-version
                        leaf bad-version {
                            type yang:counter32;
                            description "The total number of OSPF packets received with bad OSPF version numbers since admin-state was last set to 'enabled'.";
                        }

                        ///nokia-state/state/router/ospf3/area/virtual-link/packets/bad-network
                        leaf bad-network {
                            type yang:counter32;
                            description "The total number of OSPF packets received with invalid network or mask since admin-state was last set to 'enabled'.";
                        }

                        ///nokia-state/state/router/ospf3/area/virtual-link/packets/bad-area
                        leaf bad-area {
                            type yang:counter32;
                            description "The total number of OSPF packets received with an area mismatch since admin-state was last set to 'enabled'.";
                        }

                        ///nokia-state/state/router/ospf3/area/virtual-link/packets/bad-dest-address
                        leaf bad-dest-address {
                            type yang:counter32;
                            description "The total number of OSPF packets received with the incorrect IP destination address since admin-state was last set to 'enabled'.";
                        }

                        ///nokia-state/state/router/ospf3/area/virtual-link/packets/bad-neighbors
                        leaf bad-neighbors {
                            type yang:counter32;
                            description "The total number of OSPF packets received where the neighbor information does not match the information this router has for the neighbor since admin-state was last set to 'enabled'.";
                        }

                        ///nokia-state/state/router/ospf3/area/virtual-link/packets/bad-packet-type
                        leaf bad-packet-type {
                            type yang:counter32;
                            description "The total number of OSPF packets received with an invalid OSPF packet type since admin-state was last set to 'enabled'.";
                        }

                        ///nokia-state/state/router/ospf3/area/virtual-link/packets/bad-length
                        leaf bad-length {
                            type yang:counter32;
                            description "The total number of OSPF packets received with a total length not equal to the length given in the packet itself since admin-state was last set to 'enabled'.";
                        }

                        ///nokia-state/state/router/ospf3/area/virtual-link/packets/bad-hello-interval
                        leaf bad-hello-interval {
                            type yang:counter32;
                            description "the value of bad-hello-intervals indicates the total number of OSPF packets received where the hello interval given in packet was not equal to that configured on this interface since admin-state was last set to 'enabled'.";
                        }

                        ///nokia-state/state/router/ospf3/area/virtual-link/packets/bad-dead-interval
                        leaf bad-dead-interval {
                            type yang:counter32;
                            description "The total number of OSPF packets received where the dead interval given in the packet was not equal to that configured on this interface since admin-state was last set to 'enabled'.";
                        }

                        ///nokia-state/state/router/ospf3/area/virtual-link/packets/bad-options
                        leaf bad-options {
                            type yang:counter32;
                            description "The total number of OSPF packets received with an option that does not match those configured for this interface or area since admin-state was last set to 'enabled'.";
                        }

                        ///nokia-state/state/router/ospf3/area/virtual-link/packets/rx-bad-checksum
                        leaf rx-bad-checksum {
                            type yang:counter32;
                            description "The count of LS-as received with bad checksums.";
                        }

                        ///nokia-state/state/router/ospf3/area/virtual-link/packets/bad-auth-type
                        leaf bad-auth-type {
                            type yang:counter32;
                            description "The total number of OSPF packets received with an invalid authorization type since admin-state was last set to 'enabled'.";
                        }

                        ///nokia-state/state/router/ospf3/area/virtual-link/packets/auth-failures
                        leaf auth-failures {
                            type yang:counter32;
                            description "The total number of OSPF packets received with an invalid authorization key since admin-state was last set to 'enabled'.";
                        }

                    } // container packets

                    ///nokia-state/state/router/ospf3/area/virtual-link/last-packet-drop
                    container last-packet-drop {
                        description "Enter the last-packet-drop context";

                        ///nokia-state/state/router/ospf3/area/virtual-link/last-packet-drop/reason
                        leaf reason {
                            type types-ospf:packet-drop-reason;
                            description "The reason for dropping the packet.";
                        }

                        ///nokia-state/state/router/ospf3/area/virtual-link/last-packet-drop/packet-type
                        leaf packet-type {
                            type uint8;
                            description "the OSPF packet type of the dropped packet from the packet header.";
                        }

                        ///nokia-state/state/router/ospf3/area/virtual-link/last-packet-drop/router-id
                        leaf router-id {
                            type types-sros:ipv4-address;
                            description "the OSPF router ID of the dropped packet from the packet header.";
                        }

                        ///nokia-state/state/router/ospf3/area/virtual-link/last-packet-drop/area-id
                        leaf area-id {
                            type types-sros:ipv4-address;
                            description "the OSPF area ID of the dropped packet from the packet header.";
                        }

                        ///nokia-state/state/router/ospf3/area/virtual-link/last-packet-drop/checksum
                        leaf checksum {
                            type uint32;
                            description "the OSPF checksum of the dropped packet from the packet header.";
                        }

                        ///nokia-state/state/router/ospf3/area/virtual-link/last-packet-drop/drop-time
                        leaf drop-time {
                            type yang:date-and-time;
                            description "the time when the drop occured.";
                        }

                    } // container last-packet-drop

                } // list virtual-link

                ///nokia-state/state/router/ospf3/area/linkstate-database
                list linkstate-database {
                    key "ls-type adv-rtr-id ls-id";
                    description "Enter the linkstate-database list instance";

                    ///nokia-state/state/router/ospf3/area/linkstate-database/ls-type
                    leaf ls-type {
                        type uint32;
                        description "Link state type.";
                    }

                    ///nokia-state/state/router/ospf3/area/linkstate-database/adv-rtr-id
                    leaf adv-rtr-id {
                        type types-sros:ipv4-address;
                        description "Router that originated the link state advertisement.";
                    }

                    ///nokia-state/state/router/ospf3/area/linkstate-database/ls-id
                    leaf ls-id {
                        type types-sros:ipv4-address;
                        description "Link state advertisement identity.";
                    }

                    ///nokia-state/state/router/ospf3/area/linkstate-database/sequence-nr
                    leaf sequence-nr {
                        type uint32;
                    }

                    ///nokia-state/state/router/ospf3/area/linkstate-database/age
                    leaf age {
                        type int32;
                    }

                    ///nokia-state/state/router/ospf3/area/linkstate-database/checksum
                    leaf checksum {
                        type uint32;
                    }

                    ///nokia-state/state/router/ospf3/area/linkstate-database/known-type
                    leaf known-type {
                        type boolean;
                    }

                    ///nokia-state/state/router/ospf3/area/linkstate-database/advertisement
                    leaf advertisement {
                        type string {
                            length "1..9778";
                        }
                        description "Contents of the link state advertisement.";
                    }

                    ///nokia-state/state/router/ospf3/area/linkstate-database/import-filtered
                    leaf import-filtered {
                        type boolean;
                    }

                    ///nokia-state/state/router/ospf3/area/linkstate-database/export-filtered
                    leaf export-filtered {
                        type boolean;
                    }

                } // list linkstate-database

                ///nokia-state/state/router/ospf3/area/capabilities
                list capabilities {
                    key "ls-type adv-rtr-id ls-id";
                    description "Enter the capabilities list instance";

                    ///nokia-state/state/router/ospf3/area/capabilities/ls-type
                    leaf ls-type {
                        type uint32;
                        description "Link state type.";
                    }

                    ///nokia-state/state/router/ospf3/area/capabilities/adv-rtr-id
                    leaf adv-rtr-id {
                        type types-sros:ipv4-address;
                        description "Router that originated the link state advertisement.";
                    }

                    ///nokia-state/state/router/ospf3/area/capabilities/ls-id
                    leaf ls-id {
                        type types-sros:ipv4-address;
                        description "Link state advertisement identity.";
                    }

                    ///nokia-state/state/router/ospf3/area/capabilities/sequence-nr
                    leaf sequence-nr {
                        type uint32;
                    }

                    ///nokia-state/state/router/ospf3/area/capabilities/age
                    leaf age {
                        type int32;
                    }

                    ///nokia-state/state/router/ospf3/area/capabilities/checksum
                    leaf checksum {
                        type uint32;
                    }

                    ///nokia-state/state/router/ospf3/area/capabilities/advertisement
                    leaf advertisement {
                        type string {
                            length "1..9778";
                        }
                        description "Contents of the link state advertisement.";
                    }

                } // list capabilities

            } // list area

            ///nokia-state/state/router/ospf3/virtual-neighbor
            list virtual-neighbor {
                key "router-id transit-area";
                description "Enter the virtual-neighbor list instance";

                ///nokia-state/state/router/ospf3/virtual-neighbor/router-id
                leaf router-id {
                    type types-sros:ipv4-address;
                    description "Router identity of the virtual link neighbor";
                }

                ///nokia-state/state/router/ospf3/virtual-neighbor/transit-area
                leaf transit-area {
                    type leafref {
                        path "../../area/area-id";
                    }
                    description "<IPv4-address> | [1..4294967295]";
                }

                ///nokia-state/state/router/ospf3/virtual-neighbor/if-index
                leaf if-index {
                    type int32 {
                        range "1..2147483647";
                    }
                    description "the value of if-index indicates the local interface ID for the virtual link over which the neighbor can be reached.";
                }

                ///nokia-state/state/router/ospf3/virtual-neighbor/address
                leaf address {
                    type types-sros:ip-address;
                    description "the value of address indicates the IP address of the neighbor associated with the local link.";
                }

                ///nokia-state/state/router/ospf3/virtual-neighbor/oper-state
                leaf oper-state {
                    type enumeration {
                        enum down                           { value 1; }
                        enum attempt                        { value 2; }
                        enum init                           { value 3; }
                        enum two-way                        { value 4; }
                        enum exchange-start                 { value 5; }
                        enum exchange                       { value 6; }
                        enum loading                        { value 7; }
                        enum full                           { value 8; }
                    }
                    description "Indicates the State of the relationship with this Neighbor.";
                }

                ///nokia-state/state/router/ospf3/virtual-neighbor/options
                leaf options {
                    type int32;
                    description "the value of options indicates a bit mask corresponding to the neighbor's options field.";
                }

                ///nokia-state/state/router/ospf3/virtual-neighbor/hello-suppressed
                leaf hello-suppressed {
                    type boolean;
                    description "the value of hello-suppressed indicates whether hellos are being suppressed to the neighbor.";
                }

                ///nokia-state/state/router/ospf3/virtual-neighbor/if-id
                leaf if-id {
                    type int32 {
                        range "0..2147483647";
                    }
                    description "the value of if-id indicates the interface ID that the neighbor advertises in its hello packets on this link, that is, the neighbor's local interface index.";
                }

                ///nokia-state/state/router/ospf3/virtual-neighbor/restart-helper-status
                leaf restart-helper-status {
                    type enumeration {
                        enum not-helping                    { value 1; }
                        enum helping                        { value 2; }
                    }
                    description "the value of restart-helper-status indicates whether the router is acting as a graceful restart helper for the neighbor.";
                }

                ///nokia-state/state/router/ospf3/virtual-neighbor/restart-helper-age
                leaf restart-helper-age {
                    type int32 {
                        range "0..1800";
                    }
                    units "seconds";
                    description "the value of restart-helper-age indicates the remaining time in the current OSPF graceful restart interval, if the router is acting as a restart helper for the neighbor.";
                }

                ///nokia-state/state/router/ospf3/virtual-neighbor/restart-helper-exit-rc
                leaf restart-helper-exit-rc {
                    type enumeration {
                        enum none                           { value 1; }
                        enum in-progress                    { value 2; }
                        enum completed                      { value 3; }
                        enum timed-out                      { value 4; }
                        enum topology-changed               { value 5; }
                        enum bfd-down                       { value 6; }
                    }
                    description "the value of restart-helper-exit-rc indicates the outcome of the last attempt at acting as a graceful restart helper for the neighbor. none no restart has yet been attempted. in-progress A restart attempt is currently underway. completed the last restart completed successfully. timed-out the last restart timed out. topology-changed the last restart was aborted due to a topology change.";
                }

                ///nokia-state/state/router/ospf3/virtual-neighbor/last-restart-time
                leaf last-restart-time {
                    type yang:date-and-time;
                    description "the value of last-restart-time indicates the last time the neighbor attempted restart.";
                }

                ///nokia-state/state/router/ospf3/virtual-neighbor/restart-reason
                leaf restart-reason {
                    type types-ospf:restart-reason-type;
                    description "the value of restart-reason indicates the OSPF neighbor's graceful restart reason.";
                }

                ///nokia-state/state/router/ospf3/virtual-neighbor/up-time
                leaf up-time {
                    type int32 {
                        range "0..2147483647";
                    }
                    units "centiseconds";
                    description "the value of up-time indicates the uninterrupted time, in hundredths of seconds, the adjacency to this neighbour has been up.";
                }

                ///nokia-state/state/router/ospf3/virtual-neighbor/last-event
                leaf last-event {
                    type types-ospf:neighbor-event;
                    description "Indicates the last event as defined in RFC causing an oper-state change for this Neighbor.";
                }

                ///nokia-state/state/router/ospf3/virtual-neighbor/last-event-time
                leaf last-event-time {
                    type yang:date-and-time;
                    description "the value of last-event-time indicates the value of sys-up-time when the last event occurred that affected the adjacency to the neighbour.";
                }

                ///nokia-state/state/router/ospf3/virtual-neighbor/dead-time-outstanding
                leaf dead-time-outstanding {
                    type uint32 {
                        range "0..2147483647";
                    }
                    units "seconds";
                    description "the value of dead-time-outstanding indicates the amount of time in seconds until the dead-router interval expires. normally, this value should not be significantly smaller than the configured dead router interval minus one hello interval.";
                }

                ///nokia-state/state/router/ospf3/virtual-neighbor/statistics
                container statistics {
                    description "Enter the statistics context";

                    ///nokia-state/state/router/ospf3/virtual-neighbor/statistics/events
                    leaf events {
                        type yang:counter32;
                        description "the value of events indicates the number of times this neighbor relationship has changed state, or an error has occurred.";
                    }

                    ///nokia-state/state/router/ospf3/virtual-neighbor/statistics/ls-retrans-q-len
                    leaf ls-retrans-q-len {
                        type yang:gauge32;
                        description "the value of ls-retrans-Q-len indicates the current length of the retransmission queue.";
                    }

                    ///nokia-state/state/router/ospf3/virtual-neighbor/statistics/bad-nbr-states
                    leaf bad-nbr-states {
                        type yang:counter32;
                        description "the value of bad-nbr-states indicates the total number of OSPF packets received when the neighbor state was not expecting to receive this packet type since admin-state was last set to 'enabled'.";
                    }

                    ///nokia-state/state/router/ospf3/virtual-neighbor/statistics/lsa-install-failed
                    leaf lsa-install-failed {
                        type yang:counter32;
                        description "the value of lsa-install-failed indicates the total number of times an LSA could not be installed into the LSDB due to a resource allocation issue since admin-state was last set to 'enabled'.";
                    }

                    ///nokia-state/state/router/ospf3/virtual-neighbor/statistics/bad-seq-nums
                    leaf bad-seq-nums {
                        type yang:counter32;
                        description "the value of bad-seq-nums indicates the total number of times when a database description packet was received with a sequence number mismatch since admin-state was last set to 'enabled'.";
                    }

                    ///nokia-state/state/router/ospf3/virtual-neighbor/statistics/bad-mtu
                    leaf bad-mtu {
                        type yang:counter32;
                        description "the value of bad-MT-us indicates the total number of times when the MTU in a received database description packet was larger than the MTU of the receiving interface since admin-state was last set to 'enabled'.";
                    }

                    ///nokia-state/state/router/ospf3/virtual-neighbor/statistics/bad-packets
                    leaf bad-packets {
                        type yang:counter32;
                        description "the value of bad-packets indicates the total number of times when an LS update was received with an illegal LS type or an option mismatch since admin-state was last set to 'enabled'.";
                    }

                    ///nokia-state/state/router/ospf3/virtual-neighbor/statistics/lsa-not-in-lsdbs
                    leaf lsa-not-in-lsdbs {
                        type yang:counter32;
                        description "the value of lsa-not-in-lsdbs indicates the total number of times when an LS request was received for an LSA not installed in the LSDB of this router since admin-state was last set to 'enabled'.";
                    }

                    ///nokia-state/state/router/ospf3/virtual-neighbor/statistics/option-mismatches
                    leaf option-mismatches {
                        type yang:counter32;
                        description "the value of option-mismatches indicates the total number of times when a LS update was received with an option mismatch since admin-state was last set to 'enabled'.";
                    }

                    ///nokia-state/state/router/ospf3/virtual-neighbor/statistics/duplicates
                    leaf duplicates {
                        type yang:counter32;
                        description "the value of duplicates indicates the total number of times when a duplicate database description packet was received during the exchange state since admin-state was last set to 'enabled'.";
                    }

                    ///nokia-state/state/router/ospf3/virtual-neighbor/statistics/num-restarts
                    leaf num-restarts {
                        type yang:counter32;
                        description "the value of num-restarts indicates the number of times the neighbor has attempted restart.";
                    }

                } // container statistics

            } // list virtual-neighbor

            ///nokia-state/state/router/ospf3/prefix-sid
            list prefix-sid {
                key "prefix area-id route-type label advt-router-id";
                description "Enter the prefix-sid list instance";

                ///nokia-state/state/router/ospf3/prefix-sid/prefix
                leaf prefix {
                    type types-sros:ip-prefix;
                    description "The destination prefix";
                }

                ///nokia-state/state/router/ospf3/prefix-sid/area-id
                leaf area-id {
                    type types-sros:ipv4-address;
                    description "The area in which this prefix SID is defined";
                }

                ///nokia-state/state/router/ospf3/prefix-sid/route-type
                leaf route-type {
                    type enumeration {
                        enum unspecified                    { value 0; }
                        enum intra-area                     { value 1; }
                        enum inter-area                     { value 3; }
                        enum external                       { value 5; }
                        enum nssa-external                  { value 7; }
                    }
                    description "The segment routing SID route type";
                }

                ///nokia-state/state/router/ospf3/prefix-sid/label
                leaf label {
                    type uint32;
                    description "The SID label for this prefix.";
                }

                ///nokia-state/state/router/ospf3/prefix-sid/advt-router-id
                leaf advt-router-id {
                    type types-sros:ipv4-address;
                    description "The router that advertised the SID";
                }

                ///nokia-state/state/router/ospf3/prefix-sid/flags
                leaf flags {
                    type bits {
                        bit bit-N                          { position 0; }
                        bit bit-P                          { position 1; }
                        bit bit-M                          { position 2; }
                        bit bit-E                          { position 3; }
                        bit bit-V                          { position 4; }
                        bit bit-L                          { position 5; }
                        bit bit-IA                         { position 6; }
                        bit bit-AT                         { position 7; }
                        bit bit-B                          { position 8; }
                    }
                    description
                        "The value of the object flags indicates the flags of a prefix-SID advertised extended prefix TLV.
                         bit-N (0)  - node-SID flag. the N-flag is set on prefix-SI-ds attached to a router loopback address.
                         bit-P (1)  - no-PHP flag. if set, then the penultimate hop MUST NOT pop the prefix-SID before delivering the packet to the node that advertised the prefix-SID.
                         bit-M (2)  - mapping server flag. if set, the SID is advertised from the segment routing mapping server functionality
                         bit-E (3)  - explicit-null flag. if set, any upstream neighbor of the prefix-SID originator MUST replace the prefix-SID with a prefix-SID having an explicit-NULL value (0 for I-pv4) before forwarding the packet.
                         bit-V (4)  - value flag. if set, then the prefix-SID carries a value (instead of an index).
                         bit-L (5)  - local flag. if set, then the value/index carried by the prefix-SID has local significance.
                         bit-IA (6) - inter area flag.
                         bit-AT (7) - attached flag.
                         bit-B (8)  - backup SID (seamless MPLS)";
                }

                ///nokia-state/state/router/ospf3/prefix-sid/srms
                leaf srms {
                    type boolean;
                    description
                        "The value indicates whether or not the Prefix/SID is advertised by a
                         Segment Routing Mapping Server.";
                }

                ///nokia-state/state/router/ospf3/prefix-sid/srms-selected
                leaf srms-selected {
                    type boolean;
                    description
                        "The value indicates whether or not the prefix SID received in the
                         SRMS TLV is selected to be programmed.

                         When there is however a SID for the same prefix received in a
                         prefix TLV, that prefix SID will be programmed and not the
                         SRMS prefix SID.";
                }

                ///nokia-state/state/router/ospf3/prefix-sid/shared-sid
                leaf shared-sid {
                    type boolean;
                    description
                        "The value indicates wheter or not the prefix SID is a
                         shared node SID that was configured system wide.

                         Can only be true for self-originated prefix-sids.";
                }

            } // list prefix-sid

            ///nokia-state/state/router/ospf3/sid-statistics
            list sid-statistics {
                key "label";
                description "Enter the sid-statistics list instance";

                ///nokia-state/state/router/ospf3/sid-statistics/label
                leaf label {
                    type uint32;
                    description "The value specifies the SID label";
                }

                ///nokia-state/state/router/ospf3/sid-statistics/type
                leaf type {
                    type enumeration {
                        enum node                           { value 0; }
                        enum adjacency                      { value 1; }
                        enum adjacency-set                  { value 2; }
                    }
                    description "The type of SID for which statistics are collected";
                }

                ///nokia-state/state/router/ospf3/sid-statistics/prefix
                leaf prefix {
                    type types-sros:ip-prefix;
                    description "The IP address type";
                }

                ///nokia-state/state/router/ospf3/sid-statistics/adjacency-set
                leaf adjacency-set {
                    type uint32 {
                        range "0..max";
                    }
                    description "When type is adjacency-set then this is the adjacency-set for whcih the sid is used";
                }

                ///nokia-state/state/router/ospf3/sid-statistics/interface
                leaf interface {
                    type types-sros:interface-name;
                    description "When type is adjacency then this is the interface on which the adjacency is formed";
                }

                ///nokia-state/state/router/ospf3/sid-statistics/egress
                container egress {
                    description "Enter the egress context";

                    ///nokia-state/state/router/ospf3/sid-statistics/egress/oper-state
                    leaf oper-state {
                        type enumeration {
                            enum enabled                        { value 1; }
                            enum disabled                       { value 2; }
                            enum no-resource                    { value 3; }
                        }
                        description "The statistics operational state of this SID for this direction";
                    }

                    ///nokia-state/state/router/ospf3/sid-statistics/egress/octets
                    leaf octets {
                        type yang:counter64;
                        description "The number of octets";
                    }

                    ///nokia-state/state/router/ospf3/sid-statistics/egress/packets
                    leaf packets {
                        type yang:counter64;
                        description "The number of packets";
                    }

                } // container egress

                ///nokia-state/state/router/ospf3/sid-statistics/ingress
                container ingress {
                    description "Enter the ingress context";

                    ///nokia-state/state/router/ospf3/sid-statistics/ingress/oper-state
                    leaf oper-state {
                        type enumeration {
                            enum enabled                        { value 1; }
                            enum disabled                       { value 2; }
                            enum no-resource                    { value 3; }
                        }
                        description "The statistics operational state of this SID for this direction";
                    }

                    ///nokia-state/state/router/ospf3/sid-statistics/ingress/octets
                    leaf octets {
                        type yang:counter64;
                        description "The number of octets";
                    }

                    ///nokia-state/state/router/ospf3/sid-statistics/ingress/packets
                    leaf packets {
                        type yang:counter64;
                        description "The number of packets";
                    }

                } // container ingress

            } // list sid-statistics

            ///nokia-state/state/router/ospf3/lfa-coverage
            list lfa-coverage {
                key "area-id";
                description "Enter the lfa-coverage list instance";

                ///nokia-state/state/router/ospf3/lfa-coverage/area-id
                leaf area-id {
                    type types-sros:ipv4-address;
                    description "Area-ID attribute";
                }

                ///nokia-state/state/router/ospf3/lfa-coverage/nodes-covered
                leaf nodes-covered {
                    type yang:gauge32;
                    description "The value of nodes-covered indicates in absolute numbers the number of nodes for which an LFA is found.";
                }

                ///nokia-state/state/router/ospf3/lfa-coverage/nodes-total
                leaf nodes-total {
                    type yang:gauge32;
                    description "The value of total-nodes indicates in absolute numbers the number of nodes eligible for LFA calculation.";
                }

                ///nokia-state/state/router/ospf3/lfa-coverage/nodes-coverage
                leaf nodes-coverage {
                    type yang:gauge32 {
                        range "0..100";
                    }
                    units "percent";
                    description "The value of coverage indicates how much LFA coverage is being obtained for the set of available LFA eligible nodes.";
                }

                ///nokia-state/state/router/ospf3/lfa-coverage/pfx-covered
                leaf pfx-covered {
                    type yang:gauge32;
                    description "The value of pfx-covered indicates in absolute numbers the number of prefixes for which an LFA is found.";
                }

                ///nokia-state/state/router/ospf3/lfa-coverage/pfx-total
                leaf pfx-total {
                    type yang:gauge32;
                    description "The value of total-pfx indicates in absolute numbers the number of prefixes eligible for LFA calculation.";
                }

                ///nokia-state/state/router/ospf3/lfa-coverage/pfx-coverage
                leaf pfx-coverage {
                    type yang:gauge32 {
                        range "0..100";
                    }
                    units "percent";
                    description "The value of pfx-coverage indicates how much LFA prefix coverage is being obtained for the set of available LFA eligible prefixes.";
                }

            } // list lfa-coverage

            ///nokia-state/state/router/ospf3/as-linkstate-database
            list as-linkstate-database {
                key "ls-type adv-rtr-id ls-id";
                description "Enter the as-linkstate-database list instance";

                ///nokia-state/state/router/ospf3/as-linkstate-database/ls-type
                leaf ls-type {
                    type uint32;
                    description "Link state type.";
                }

                ///nokia-state/state/router/ospf3/as-linkstate-database/adv-rtr-id
                leaf adv-rtr-id {
                    type types-sros:ipv4-address;
                    description "Router that originated the link state advertisement.";
                }

                ///nokia-state/state/router/ospf3/as-linkstate-database/ls-id
                leaf ls-id {
                    type types-sros:ipv4-address;
                    description "Link state advertisement identity.";
                }

                ///nokia-state/state/router/ospf3/as-linkstate-database/sequence-nr
                leaf sequence-nr {
                    type uint32;
                }

                ///nokia-state/state/router/ospf3/as-linkstate-database/age
                leaf age {
                    type int32;
                }

                ///nokia-state/state/router/ospf3/as-linkstate-database/checksum
                leaf checksum {
                    type uint32;
                }

                ///nokia-state/state/router/ospf3/as-linkstate-database/known-type
                leaf known-type {
                    type boolean;
                }

                ///nokia-state/state/router/ospf3/as-linkstate-database/advertisement
                leaf advertisement {
                    type string {
                        length "1..9778";
                    }
                    description "Contents of the link state advertisement.";
                }

            } // list as-linkstate-database

            ///nokia-state/state/router/ospf3/as-capabilities
            list as-capabilities {
                key "ls-type adv-rtr-id ls-id";
                description "Enter the as-capabilities list instance";

                ///nokia-state/state/router/ospf3/as-capabilities/ls-type
                leaf ls-type {
                    type uint32;
                    description "Link state type.";
                }

                ///nokia-state/state/router/ospf3/as-capabilities/adv-rtr-id
                leaf adv-rtr-id {
                    type types-sros:ipv4-address;
                    description "Router that originated the link state advertisement.";
                }

                ///nokia-state/state/router/ospf3/as-capabilities/ls-id
                leaf ls-id {
                    type types-sros:ipv4-address;
                    description "Link state advertisement identity.";
                }

                ///nokia-state/state/router/ospf3/as-capabilities/sequence-nr
                leaf sequence-nr {
                    type uint32;
                }

                ///nokia-state/state/router/ospf3/as-capabilities/age
                leaf age {
                    type int32;
                }

                ///nokia-state/state/router/ospf3/as-capabilities/checksum
                leaf checksum {
                    type uint32;
                }

                ///nokia-state/state/router/ospf3/as-capabilities/advertisement
                leaf advertisement {
                    type string {
                        length "1..9778";
                    }
                    description "Contents of the link state advertisement.";
                }

            } // list as-capabilities

            ///nokia-state/state/router/ospf3/route
            list route {
                key "route-type destination area";
                description "Enter the route list instance";

                ///nokia-state/state/router/ospf3/route/route-type
                leaf route-type {
                    type types-ospf:route-type;
                    description "The route type os this route, network or router.";
                }

                ///nokia-state/state/router/ospf3/route/destination
                leaf destination {
                    type types-sros:ip-prefix;
                    description "The value specifies the IP address and mask of the route destination.";
                }

                ///nokia-state/state/router/ospf3/route/area
                leaf area {
                    type types-sros:ipv4-address;
                    description "Area through which the destination is reachable.";
                }

                ///nokia-state/state/router/ospf3/route/path-type
                leaf path-type {
                    type types-ospf:route-path-type;
                    description "Select path type for the destination.";
                }

                ///nokia-state/state/router/ospf3/route/dest-type
                leaf dest-type {
                    type types-ospf:route-dest-type;
                }

                ///nokia-state/state/router/ospf3/route/rtm-status
                leaf rtm-status {
                    type types-ospf:rtm-status;
                    description "Indicates status in RTM.";
                }

                ///nokia-state/state/router/ospf3/route/cost
                leaf cost {
                    type uint32;
                    description "The cost of this route, calculated during SPF.";
                }

                ///nokia-state/state/router/ospf3/route/type2-cost
                leaf type2-cost {
                    type uint32;
                    description "The external type2 cost of this route, calculated during SPF.";
                }

                ///nokia-state/state/router/ospf3/route/sid
                leaf sid {
                    type uint32;
                    description "The sid that corresponds to this destination";
                }

                ///nokia-state/state/router/ospf3/route/sid-flags
                leaf sid-flags {
                    type bits {
                        bit bit-n                          { position 0; }
                        bit bit-p                          { position 1; }
                        bit bit-m                          { position 2; }
                        bit bit-e                          { position 3; }
                        bit bit-v                          { position 4; }
                        bit bit-l                          { position 5; }
                        bit bit-ia                         { position 6; }
                        bit bit-at                         { position 7; }
                        bit bit-b                          { position 8; }
                    }
                    description "The sid flags that corresponds to this destination";
                }

                ///nokia-state/state/router/ospf3/route/next-hop
                list next-hop {
                    key "ecmp-index";
                    description "Enter the next-hop list instance";

                    ///nokia-state/state/router/ospf3/route/next-hop/ecmp-index
                    leaf ecmp-index {
                        type types-router:ip-ecmp;
                        description "ECMP index of this route next-hop.";
                    }

                    ///nokia-state/state/router/ospf3/route/next-hop/type
                    leaf type {
                        type enumeration {
                            enum unknown                        { value 0; }
                            enum direct                         { value 1; }
                            enum rsvp                           { value 2; }
                            enum srte                           { value 3; }
                            enum shortcut                       { value 4; }
                            enum blackhole                      { value 5; }
                            enum unnumbered                     { value 6; }
                            enum ip                             { value 7; }
                        }
                        description "Indicates the next hop type";
                    }

                    ///nokia-state/state/router/ospf3/route/next-hop/ip-address
                    leaf ip-address {
                        type types-sros:ip-address;
                        description "The value specifies the IP address of the next hop for this route";
                    }

                    ///nokia-state/state/router/ospf3/route/next-hop/interface
                    leaf interface {
                        type types-sros:interface-name;
                        description "The value specifies the interface of the next hop for this route";
                    }

                    ///nokia-state/state/router/ospf3/route/next-hop/tunnel-id
                    leaf tunnel-id {
                        type uint32;
                        description "The tunnel-id given to this tunnelled next hop";
                    }

                    ///nokia-state/state/router/ospf3/route/next-hop/area
                    leaf area {
                        type types-sros:ipv4-address;
                        description "The value specifies the area the shortest path was found in";
                    }

                    ///nokia-state/state/router/ospf3/route/next-hop/rtm-status
                    leaf rtm-status {
                        type enumeration {
                            enum success                        { value 0; }
                            enum discarded                      { value 1; }
                        }
                        description "Indicates the next hop status in RTM";
                    }

                    ///nokia-state/state/router/ospf3/route/next-hop/weight
                    container weight {
                        description "Enter the weight context";

                        ///nokia-state/state/router/ospf3/route/next-hop/weight/configured
                        leaf configured {
                            type uint32;
                            description "The weight given to this next hop";
                        }

                        ///nokia-state/state/router/ospf3/route/next-hop/weight/normalised
                        leaf normalised {
                            type uint32;
                            description "The normalised weight of this next hop for this route";
                        }

                    } // container weight

                } // list next-hop

            } // list route

            ///nokia-state/state/router/ospf3/hostname
            list hostname {
                key "router-id";
                description "Enter the hostname list instance";

                ///nokia-state/state/router/ospf3/hostname/router-id
                leaf router-id {
                    type types-igp:router-id;
                    description "Specifies the router-id for which we map the hostname";
                }

                ///nokia-state/state/router/ospf3/hostname/name
                leaf name {
                    type types-sros:display-string;
                    description "The value indicates the mapping hostname for the corresponding router-id";
                }

            } // list hostname

        } // list ospf3

    } // grouping state-router-ospf3

}
