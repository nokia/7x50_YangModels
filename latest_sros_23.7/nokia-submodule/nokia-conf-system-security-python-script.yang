submodule nokia-conf-system-security-python-script {

    yang-version "1.1";

    belongs-to nokia-conf { prefix "conf"; }

    import nokia-sros-yang-extensions     { prefix "sros-ext"; }

    include nokia-conf-groups;
    include nokia-conf-system;
    include nokia-conf-system-security;
    include nokia-conf-system-security-user-parameters;

    sros-ext:sros-major-release "rel23";
    organization "Nokia";
    contact
        "Nokia SR OS Support
         Web: <http://www.nokia.com>";
    description
        "Nokia YANG Data model to configure system security python script parameters on SR OS based routers.

         Copyright 2016 Nokia. All rights reserved. Reproduction of this document
         is authorized on the condition that the foregoing copyright notice is included.

         This nokia-conf-system-security-python-script YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-05-11";

    grouping conf-system-security-python-script {
        ///nokia-conf/configure/system/security/python-script
        container python-script {
            description "Enable the python-script context";

            ///nokia-conf/configure/system/security/python-script/apply-groups
            leaf-list apply-groups {
                type leafref {
                    path "../../../../groups/group/name";
                }
                max-elements 8;
                ordered-by user;
                description "Apply a configuration group at this level";
            }

            ///nokia-conf/configure/system/security/python-script/apply-groups-exclude
            leaf-list apply-groups-exclude {
                type leafref {
                    path "../../../../groups/group/name";
                }
                max-elements 8;
                ordered-by user;
                description "Exclude a configuration group at this level";
            }

            ///nokia-conf/configure/system/security/python-script/authorization
            container authorization {
                description "Enter the authorization context";

                ///nokia-conf/configure/system/security/python-script/authorization/cron
                container cron {
                    description "Enter the cron context";

                    ///nokia-conf/configure/system/security/python-script/authorization/cron/cli-user
                    leaf cli-user {
                        type leafref {
                            path "../../../../user-params/local-user/user/user-name";
                        }
                        description "User profile name when executing a Python application";
                    }

                } // container cron

                ///nokia-conf/configure/system/security/python-script/authorization/event-handler
                container event-handler {
                    description "Enter the event-handler context";

                    ///nokia-conf/configure/system/security/python-script/authorization/event-handler/cli-user
                    leaf cli-user {
                        type leafref {
                            path "../../../../user-params/local-user/user/user-name";
                        }
                        description "User profile name when executing a Python application";
                    }

                } // container event-handler

            } // container authorization

        } // container python-script

    } // grouping conf-system-security-python-script

}
