submodule nokia-state-python {

    yang-version "1.1";

    belongs-to nokia-state { prefix "state"; }

    import ietf-yang-types                { prefix "yang"; }
    import nokia-sros-yang-extensions     { prefix "sros-ext"; }
    import nokia-types-esa                { prefix "types-esa"; }
    import nokia-types-isa                { prefix "types-isa"; }
    import nokia-types-sros               { prefix "types-sros"; }

    sros-ext:sros-major-release "rel23";
    organization "Nokia";
    contact
        "Nokia SR OS Support
         Web: <http://www.nokia.com>";
    description
        "Nokia YANG Data model with operational state for Python scripts on SR OS based routers.

         Copyright 2016 Nokia. All rights reserved. Reproduction of this document
         is authorized on the condition that the foregoing copyright notice is included.

         This nokia-state-python YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-11-18";

    grouping state-python {
        ///nokia-state/state/python
        container python {
            description "Enable the python context";

            ///nokia-state/state/python/running-interpreters
            leaf running-interpreters {
                type uint32;
                description "The number of currently running interpreters";
            }

            ///nokia-state/state/python/python-script
            list python-script {
                key "name";
                description "Enter the python-script list instance";

                ///nokia-state/state/python/python-script/name
                leaf name {
                    type types-sros:named-item;
                    description "Python script policy name";
                }

                ///nokia-state/state/python/python-script/oper-state
                leaf oper-state {
                    type types-sros:oper-state;
                    description "the operational state of the Python script.";
                }

                ///nokia-state/state/python/python-script/oper-state-distributed
                leaf oper-state-distributed {
                    type types-sros:oper-state;
                    description "the operational state of the distributed deployment of the Python script.";
                }

                ///nokia-state/state/python/python-script/code-size
                leaf code-size {
                    type uint32;
                    units "bytes";
                    description "the bytecode size of the Python script.";
                }

                ///nokia-state/state/python/python-script/active-url
                leaf active-url {
                    type enumeration {
                        enum none                           { value 0; }
                        enum primary                        { value 1; }
                        enum secondary                      { value 2; }
                        enum tertiary                       { value 3; }
                    }
                    description
                        "which URL the script has been loaded.

                         A value of 'primary (1)' indicates the URL in primary-url
                         has been used.
                         A value of 'secondary (2)' indicates the URL in
                         secondary-url has been used.
                         A value of 'tertiary (3)' indicates the URL in tertiary-url
                         has been used.

                         A value of 'none (0)' indicates no script has been
                         loaded.";
                }

                ///nokia-state/state/python/python-script/reload-action
                leaf reload-action {
                    type types-sros:action-type;
                    description
                        "whether to reload the Python script file specified by this
                         Python script.

                         When SET to the value of 'do-action' the system will load
                         and parse the file specified in the primary, secondary or
                         tertiary URL.

                         A request on this object returns 'not-applicable'.";
                }

                ///nokia-state/state/python/python-script/statistics
                list statistics {
                    key "isa-group-id isa";
                    description "Enter the statistics list instance";

                    ///nokia-state/state/python/python-script/statistics/isa-group-id
                    leaf isa-group-id {
                        type uint32 {
                            range "1..4";
                        }
                        description "NAT or WLAN-GW Integrated Service Adaptor (ISA) group ID";
                    }

                    ///nokia-state/state/python/python-script/statistics/isa
                    leaf isa {
                        type types-isa:slot-mda;
                        description "Location of the ISA";
                    }

                    ///nokia-state/state/python/python-script/statistics/success
                    leaf success {
                        type yang:counter32;
                        description "The number of times the Python script ran successfully";
                    }

                    ///nokia-state/state/python/python-script/statistics/failure
                    leaf failure {
                        type yang:counter32;
                        description "The number of times the Python script ran unsuccessfully";
                    }

                    ///nokia-state/state/python/python-script/statistics/timeout
                    leaf timeout {
                        type yang:counter32;
                        description "The number of times the Python script timed out while running";
                    }

                    ///nokia-state/state/python/python-script/statistics/abort
                    leaf abort {
                        type yang:counter32;
                        description
                            "The number of times the Python script was aborted due to
                             rate limitation while running";
                    }

                } // list statistics

                ///nokia-state/state/python/python-script/esa-vm-statistics
                list esa-vm-statistics {
                    key "isa-group-id esa vm";
                    description "Enter the esa-vm-statistics list instance";

                    ///nokia-state/state/python/python-script/esa-vm-statistics/isa-group-id
                    leaf isa-group-id {
                        type uint32 {
                            range "1..4";
                        }
                        description "NAT or WLAN-GW Integrated Service Adaptor (ISA) group ID";
                    }

                    ///nokia-state/state/python/python-script/esa-vm-statistics/esa
                    leaf esa {
                        type types-esa:esa-id;
                        description "Location of the ESA";
                    }

                    ///nokia-state/state/python/python-script/esa-vm-statistics/vm
                    leaf vm {
                        type types-esa:vm-id;
                        description "Location of the ESA-VM";
                    }

                    ///nokia-state/state/python/python-script/esa-vm-statistics/success
                    leaf success {
                        type yang:counter32;
                        description "The number of times the Python script ran successfully";
                    }

                    ///nokia-state/state/python/python-script/esa-vm-statistics/failure
                    leaf failure {
                        type yang:counter32;
                        description "The number of times the Python script ran unsuccessfully";
                    }

                    ///nokia-state/state/python/python-script/esa-vm-statistics/timeout
                    leaf timeout {
                        type yang:counter32;
                        description "The number of times the Python script timed out while running";
                    }

                    ///nokia-state/state/python/python-script/esa-vm-statistics/abort
                    leaf abort {
                        type yang:counter32;
                        description
                            "The number of times the Python script was aborted due to
                             rate limitation while running";
                    }

                } // list esa-vm-statistics

            } // list python-script

            ///nokia-state/state/python/python-policy
            list python-policy {
                key "name";
                description "Enter the python-policy list instance";

                ///nokia-state/state/python/python-policy/name
                leaf name {
                    type types-sros:named-item;
                    description "Python policy name";
                }

                ///nokia-state/state/python/python-policy/cache
                container cache {
                    description "Enable the cache context";

                    ///nokia-state/state/python/python-policy/cache/number-of-entries
                    leaf number-of-entries {
                        type yang:gauge32;
                        description "Current number of Python cache entries.";
                    }

                } // container cache

            } // list python-policy

            ///nokia-state/state/python/interpreters
            container interpreters {
                description "Enter the interpreters context";

                ///nokia-state/state/python/interpreters/interpreter
                list interpreter {
                    key "name";
                    description "Enter the interpreter list instance";

                    ///nokia-state/state/python/interpreters/interpreter/name
                    leaf name {
                        type string;
                        description "The name of this python-interpreter";
                    }

                    ///nokia-state/state/python/interpreters/interpreter/version
                    leaf version {
                        type enumeration {
                            enum python2                        { value 2; }
                            enum python3                        { value 3; }
                        }
                        description "The python version of this python-interpreter";
                    }

                    ///nokia-state/state/python/interpreters/interpreter/source
                    leaf source {
                        type string;
                        description "The origin of the code that is currently running in this python-interpreter";
                    }

                    ///nokia-state/state/python/interpreters/interpreter/source-type
                    leaf source-type {
                        type enumeration {
                            enum none                           { value 0; }
                            enum script                         { value 1; }
                            enum url                            { value 2; }
                        }
                        description "The type of code that is currently running in this python-interpreter";
                    }

                    ///nokia-state/state/python/interpreters/interpreter/statistics
                    container statistics {
                        description "Enter the statistics context";

                        ///nokia-state/state/python/interpreters/interpreter/statistics/start-time
                        leaf start-time {
                            type yang:date-and-time;
                            description "The time at which this python-interpreter was started";
                        }

                        ///nokia-state/state/python/interpreters/interpreter/statistics/run-time
                        leaf run-time {
                            type types-sros:time-duration;
                            units "seconds";
                            description "The amount of time this python-interpreter has been running for";
                        }

                        ///nokia-state/state/python/interpreters/interpreter/statistics/memory
                        container memory {
                            description "Enter the memory context";

                            ///nokia-state/state/python/interpreters/interpreter/statistics/memory/max-allowed
                            leaf max-allowed {
                                type uint32;
                                units "megabytes";
                                description "The maximum amount of memory this python-interpreter is allowed to allocate";
                            }

                            ///nokia-state/state/python/interpreters/interpreter/statistics/memory/in-use
                            leaf in-use {
                                type uint32;
                                units "megabytes";
                                description "The amount of memory currently allocated by this python-interpreter";
                            }

                        } // container memory

                    } // container statistics

                } // list interpreter

            } // container interpreters

        } // container python

    } // grouping state-python

}
