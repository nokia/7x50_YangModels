submodule nokia-conf-router-isis {

    yang-version "1.1";

    belongs-to nokia-conf { prefix "conf"; }

    import ietf-yang-types                { prefix "yang"; }
    import nokia-sros-yang-extensions     { prefix "sros-ext"; }
    import nokia-types-igp                { prefix "types-igp"; }
    import nokia-types-isis               { prefix "types-isis"; }
    import nokia-types-router             { prefix "types-router"; }
    import nokia-types-sros               { prefix "types-sros"; }

    include nokia-conf-groups;
    include nokia-conf-policy-options;
    include nokia-conf-router;
    include nokia-conf-router-bier;
    include nokia-conf-router-segment-routing;
    include nokia-conf-routing-options;
    include nokia-conf-system;
    include nokia-conf-system-security;

    sros-ext:sros-major-release "rel23";
    organization "Nokia";
    contact
        "Nokia SR OS Support
         Web: <http://www.nokia.com>";
    description
        "Nokia YANG Data model to configure router isis protocol attributes on SR OS based routers.

         Copyright 2016 Nokia. All rights reserved. Reproduction of this document
         is authorized on the condition that the foregoing copyright notice is included.

         This nokia-conf-router-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-01";

    grouping conf-router-isis {
        ///nokia-conf/configure/router/isis
        list isis {
            key "isis-instance";
            description "Enter the isis list instance";

            ///nokia-conf/configure/router/isis/isis-instance
            leaf isis-instance {
                type int32 {
                    range "0..127";
                }
                description "Instance ID for the IS-IS instance";
            }

            ///nokia-conf/configure/router/isis/authentication-keychain
            leaf authentication-keychain {
                type leafref {
                    path "../../../system/security/keychains/keychain/keychain-name";
                }
                description "Keychain used to sign and authenticate";
            }

            ///nokia-conf/configure/router/isis/authentication-key
            leaf authentication-key {
                type types-sros:encrypted-leaf {
                    length "1..366";
                }
                description "Authentication key to verify PDUs sent from neighbors";
            }

            ///nokia-conf/configure/router/isis/authentication-type
            leaf authentication-type {
                type types-isis:auth-type;
                description "Authentication type";
            }

            ///nokia-conf/configure/router/isis/csnp-authentication
            leaf csnp-authentication {
                type boolean;
                default "true";
                description "Authenticate individual IS-IS packets of the CSNP type";
            }

            ///nokia-conf/configure/router/isis/psnp-authentication
            leaf psnp-authentication {
                type boolean;
                default "true";
                description "Authenticate individual IS-IS protocol packets of partial sequence number PDU (PSNP) type";
            }

            ///nokia-conf/configure/router/isis/admin-state
            leaf admin-state {
                type types-sros:admin-state;
                default "disable";
                description "Administrative state of the IS-IS instance";
            }

            ///nokia-conf/configure/router/isis/advertise-passive-only
            leaf advertise-passive-only {
                type boolean;
                default "false";
                description "Advertise prefixes that belong to passive interfaces";
            }

            ///nokia-conf/configure/router/isis/advertise-router-capability
            leaf advertise-router-capability {
                type enumeration {
                    enum area                           { value 2; }
                    enum as                             { value 3; }
                }
                description "Router capabilities advertisement to neighbors";
            }

            ///nokia-conf/configure/router/isis/advertise-tunnel-link
            leaf advertise-tunnel-link {
                type boolean;
                default "false";
                description "Allow use of forwarding adjacency";
            }

            ///nokia-conf/configure/router/isis/all-l1isis
            leaf all-l1isis {
                type yang:mac-address;
                default "01:80:C2:00:00:14";
                description "Destination MAC address for all L1 IS-IS routers";
            }

            ///nokia-conf/configure/router/isis/all-l2isis
            leaf all-l2isis {
                type yang:mac-address;
                default "01:80:C2:00:00:15";
                description "Destination MAC address for all L2 IS-IS routers";
            }

            ///nokia-conf/configure/router/isis/authentication-check
            leaf authentication-check {
                type boolean;
                default "true";
                description "Perform authentication check to reject mismatch PDUs";
            }

            ///nokia-conf/configure/router/isis/default-route-tag
            leaf default-route-tag {
                type uint32 {
                    range "1..max";
                }
                description "Route tag for the default route";
            }

            ///nokia-conf/configure/router/isis/ldp-sync
            leaf ldp-sync {
                type boolean;
                default "true";
                description "Use IGP-LDP synchronization feature on all interfaces participating in IS-IS routing protocol";
            }

            ///nokia-conf/configure/router/isis/hello-authentication
            leaf hello-authentication {
                type boolean;
                default "true";
                description "Authenticate Hello type IS-IS protocol packets";
            }

            ///nokia-conf/configure/router/isis/ignore-attached-bit
            leaf ignore-attached-bit {
                type boolean;
                default "false";
                description "Ignore attached bit on received Layer 1 LSPs";
            }

            ///nokia-conf/configure/router/isis/ignore-lsp-errors
            leaf ignore-lsp-errors {
                type boolean;
                default "false";
                description "Ignore LSP packets with errors";
            }

            ///nokia-conf/configure/router/isis/ignore-narrow-metric
            leaf ignore-narrow-metric {
                type boolean;
                default "false";
                description "Ignore links with narrow metrics";
            }

            ///nokia-conf/configure/router/isis/iid-tlv
            leaf iid-tlv {
                type boolean;
                default "false";
                description "Use IID TLVs with IS-IS multi-instance";
            }

            ///nokia-conf/configure/router/isis/ipv4-multicast-routing
            leaf ipv4-multicast-routing {
                type types-isis:routing-topology;
                default "native";
                description "IS-IS topology for IPv4 multicast routing";
            }

            ///nokia-conf/configure/router/isis/ipv4-routing
            leaf ipv4-routing {
                type boolean;
                default "true";
                description "Support IPv4 routing for IS-IS instance";
            }

            ///nokia-conf/configure/router/isis/ipv6-multicast-routing
            leaf ipv6-multicast-routing {
                type types-isis:routing-topology;
                description "Topology to populate the IPv6 multicast RTM";
            }

            ///nokia-conf/configure/router/isis/ipv6-routing
            leaf ipv6-routing {
                type types-isis:routing-topology;
                default "false";
                description "Routing topology for IPv6";
            }

            ///nokia-conf/configure/router/isis/hello-padding
            leaf hello-padding {
                type types-isis:hello-padding-type;
                description "IS-IS Hello message padding";
            }

            ///nokia-conf/configure/router/isis/ldp-over-rsvp
            leaf ldp-over-rsvp {
                type boolean;
                default "false";
                description "Allow LDP over RSVP processing";
            }

            ///nokia-conf/configure/router/isis/level-capability
            leaf level-capability {
                type types-isis:level;
                description "Routing level for instance";
            }

            ///nokia-conf/configure/router/isis/lsp-lifetime
            leaf lsp-lifetime {
                type uint32 {
                    range "350..65535";
                }
                units "seconds";
                sros-ext:manual-restart-to-modify;
                default "1200";
                description "Amount of time during which an LSP is considered valid";
            }

            ///nokia-conf/configure/router/isis/lsp-minimum-remaining-lifetime
            leaf lsp-minimum-remaining-lifetime {
                type uint32 {
                    range "350..65535";
                }
                units "seconds";
                description "Minimum value for the Remaining Lifetime of an LSP";
            }

            ///nokia-conf/configure/router/isis/lsp-mtu-size
            leaf lsp-mtu-size {
                type types-isis:lsp-buffer-ext-size;
                units "bytes";
                sros-ext:manual-restart-to-modify;
                default "1492";
                description "LSP MTU size";
            }

            ///nokia-conf/configure/router/isis/mru-mismatch-detection
            leaf mru-mismatch-detection {
                type boolean;
                default "false";
                description "Enable detection of MRU mismatch";
            }

            ///nokia-conf/configure/router/isis/overload-export-interlevel
            leaf overload-export-interlevel {
                type boolean;
                default "false";
                description "Advertise the inter-level routes when router is overloaded";
            }

            ///nokia-conf/configure/router/isis/overload-export-external
            leaf overload-export-external {
                type boolean;
                default "false";
                description "Advertise the external routes when router is in overloaded";
            }

            ///nokia-conf/configure/router/isis/poi-tlv
            leaf poi-tlv {
                type boolean;
                default "false";
                description "Purge Originator Identification TLV";
            }

            ///nokia-conf/configure/router/isis/prefix-attributes-tlv
            leaf prefix-attributes-tlv {
                type boolean;
                default "false";
                description "Use IS-IS Prefix Attributes TLV to exchange extended IPv4 and IPv6 reachability information";
            }

            ///nokia-conf/configure/router/isis/reference-bandwidth
            leaf reference-bandwidth {
                type types-sros:reference-bandwidth-ext;
                units "kilobps";
                description "Reference bandwidth for bandwidth relative costing";
            }

            ///nokia-conf/configure/router/isis/router-id
            leaf router-id {
                type types-igp:router-id;
                sros-ext:auto-restart-to-modify;
                description "Unique router ID for the ISIS instance";
            }

            ///nokia-conf/configure/router/isis/standard-multi-instance
            leaf standard-multi-instance {
                type boolean;
                default "false";
                description "Enable RFC standards compliant multi-instance behavior";
            }

            ///nokia-conf/configure/router/isis/strict-adjacency-check
            leaf strict-adjacency-check {
                type boolean;
                default "false";
                description "Enable strict checking of address families for IS-IS adjacencies";
            }

            ///nokia-conf/configure/router/isis/suppress-attached-bit
            leaf suppress-attached-bit {
                type boolean;
                default "false";
                description "Allow IS-IS to suppress setting attached bit on LSPs";
            }

            ///nokia-conf/configure/router/isis/system-id
            leaf system-id {
                type types-igp:system-id;
                sros-ext:auto-restart-to-modify;
                sros-ext:manual-restart-to-modify;
                description "System ID";
            }

            ///nokia-conf/configure/router/isis/traffic-engineering
            leaf traffic-engineering {
                type boolean;
                default "false";
                description "Enable traffic engineering for the router";
            }

            ///nokia-conf/configure/router/isis/export-policy
            leaf-list export-policy {
                type leafref {
                    path "../../../policy-options/policy-statement/name";
                }
                max-elements 5;
                ordered-by user;
                description "Export policies that determine exported routes";
            }

            ///nokia-conf/configure/router/isis/import-policy
            leaf-list import-policy {
                type leafref {
                    path "../../../policy-options/policy-statement/name";
                }
                max-elements 5;
                ordered-by user;
                description "Import policy names for routes from IGP to route table";
            }

            ///nokia-conf/configure/router/isis/area-address
            leaf-list area-address {
                type types-isis:area-address;
                max-elements 3;
                description "Area address portion of the NSAP address";
            }

            ///nokia-conf/configure/router/isis/apply-groups
            leaf-list apply-groups {
                type leafref {
                    path "../../../groups/group/name";
                }
                max-elements 8;
                ordered-by user;
                description "Apply a configuration group at this level";
            }

            ///nokia-conf/configure/router/isis/apply-groups-exclude
            leaf-list apply-groups-exclude {
                type leafref {
                    path "../../../groups/group/name";
                }
                max-elements 8;
                ordered-by user;
                description "Exclude a configuration group at this level";
            }

            ///nokia-conf/configure/router/isis/export-limit
            container export-limit {
                presence "Enable the export-limit context";
                description "Enable the export-limit context";

                ///nokia-conf/configure/router/isis/export-limit/number
                leaf number {
                    type uint32 {
                        range "1..max";
                    }
                    mandatory true;
                    description "Maximum routes or prefixes exported from route table";
                }

                ///nokia-conf/configure/router/isis/export-limit/log-percent
                leaf log-percent {
                    type uint32 {
                        range "1..100";
                    }
                    description "Export limit before warning and SNMP notification sent";
                }

            } // container export-limit

            ///nokia-conf/configure/router/isis/graceful-restart
            container graceful-restart {
                presence "Enable the graceful-restart context";
                description "Enable the graceful-restart context";

                ///nokia-conf/configure/router/isis/graceful-restart/helper-mode
                leaf helper-mode {
                    type boolean;
                    default "true";
                    description "Enable the Graceful Restart helper for IS-IS";
                }

            } // container graceful-restart

            ///nokia-conf/configure/router/isis/entropy-label
            container entropy-label {
                description "Enter the entropy-label context";

                ///nokia-conf/configure/router/isis/entropy-label/override-tunnel-elc
                leaf override-tunnel-elc {
                    type boolean;
                    default "false";
                    description "Enable override of received ELC advertisements";
                }

            } // container entropy-label

            ///nokia-conf/configure/router/isis/multi-topology
            container multi-topology {
                presence "Enable the multi-topology context";
                description "Enable the multi-topology context";

                ///nokia-conf/configure/router/isis/multi-topology/ipv6-unicast
                leaf ipv6-unicast {
                    type boolean;
                    default "false";
                    description "Support multi-topology TLVs";
                }

                ///nokia-conf/configure/router/isis/multi-topology/ipv4-multicast
                leaf ipv4-multicast {
                    type boolean;
                    default "false";
                    description "Support IPv4 topology (MT3)";
                }

                ///nokia-conf/configure/router/isis/multi-topology/ipv6-multicast
                leaf ipv6-multicast {
                    type boolean;
                    default "false";
                    description "Support IPv6 topology (MT4)";
                }

            } // container multi-topology

            ///nokia-conf/configure/router/isis/multicast-import
            container multicast-import {
                description "Enter the multicast-import context";

                ///nokia-conf/configure/router/isis/multicast-import/ipv4
                leaf ipv4 {
                    type boolean;
                    default "false";
                    description "Submit IPv4 routes into the multicast RPF of the RTM";
                }

                ///nokia-conf/configure/router/isis/multicast-import/ipv6
                leaf ipv6 {
                    type boolean;
                    default "false";
                    description "Submit IPv6 routes into the multicast RPF of the RTM";
                }

            } // container multicast-import

            ///nokia-conf/configure/router/isis/overload
            container overload {
                presence "Enable the overload context";
                description "Enable the overload context";

                ///nokia-conf/configure/router/isis/overload/max-metric
                leaf max-metric {
                    type boolean;
                    default "false";
                    description "Advertise transit links with maximum metric instead of setting overload bit";
                }

            } // container overload

            ///nokia-conf/configure/router/isis/overload-on-boot
            container overload-on-boot {
                presence "Enable the overload-on-boot context";
                description "Enable the overload-on-boot context";

                ///nokia-conf/configure/router/isis/overload-on-boot/timeout
                leaf timeout {
                    type uint32 {
                        range "60..1800";
                    }
                    units "seconds";
                    description "Time during which the router operates in overload state after reboot";
                }

                ///nokia-conf/configure/router/isis/overload-on-boot/max-metric
                leaf max-metric {
                    type boolean;
                    default "false";
                    description "Advertise transit links with maximum metric instead of setting overload bit";
                }

            } // container overload-on-boot

            ///nokia-conf/configure/router/isis/overload-fib-error-notify-only
            container overload-fib-error-notify-only {
                presence "Enable the overload-fib-error-notify-only context";
                description "Enable the overload-fib-error-notify-only context";

                ///nokia-conf/configure/router/isis/overload-fib-error-notify-only/retry
                leaf retry {
                    type uint32 {
                        range "10..1800";
                    }
                    units "seconds";
                    default "10";
                    description "Time to retry programming failed entries in the FIB";
                }

            } // container overload-fib-error-notify-only

            ///nokia-conf/configure/router/isis/prefix-limit
            container prefix-limit {
                presence "Enable the prefix-limit context";
                description "Enable the prefix-limit context";

                ///nokia-conf/configure/router/isis/prefix-limit/limit
                leaf limit {
                    type uint32 {
                        range "1..max";
                    }
                    mandatory true;
                    description "Maximum number of prefixes for IS-IS instance";
                }

                ///nokia-conf/configure/router/isis/prefix-limit/log-only
                leaf log-only {
                    type boolean;
                    default "false";
                    description "Send warning message when the prefix limit is reached";
                }

                ///nokia-conf/configure/router/isis/prefix-limit/warning-threshold
                leaf warning-threshold {
                    type uint32 {
                        range "0..100";
                    }
                    units "percent";
                    default "0";
                    description "Threshold value to trigger a warning message to be sent";
                }

                ///nokia-conf/configure/router/isis/prefix-limit/overload-timeout
                leaf overload-timeout {
                    type types-igp:overload-timeout;
                    default "forever";
                    description "Time in overload state when prefix limit is reached";
                }

            } // container prefix-limit

            ///nokia-conf/configure/router/isis/lsp-refresh
            container lsp-refresh {
                description "Enter the lsp-refresh context";

                ///nokia-conf/configure/router/isis/lsp-refresh/interval
                leaf interval {
                    type uint32 {
                        range "150..65535";
                    }
                    units "seconds";
                    default "600";
                    description "Refresh timer interval";
                }

                ///nokia-conf/configure/router/isis/lsp-refresh/half-lifetime
                leaf half-lifetime {
                    type boolean;
                    default "true";
                    description "Set the refresh interval to always be half the LSP lifetime";
                }

            } // container lsp-refresh

            ///nokia-conf/configure/router/isis/rib-priority
            container rib-priority {
                description "Enter the rib-priority context";

                ///nokia-conf/configure/router/isis/rib-priority/high
                container high {
                    description "Enter the high context";

                    ///nokia-conf/configure/router/isis/rib-priority/high/type
                    choice type {
                        ///nokia-conf/configure/router/isis/rib-priority/high/type/prefix-list
                        case prefix-list {

                            ///nokia-conf/configure/router/isis/rib-priority/high/type/prefix-list/prefix-list
                            leaf prefix-list {
                                type leafref {
                                    path "../../../../../policy-options/prefix-list/name";
                                }
                                description "List used to select routes processed at higher priority through OSPF route calculation process";
                            }

                        }
                        ///nokia-conf/configure/router/isis/rib-priority/high/type/tag
                        case tag {

                            ///nokia-conf/configure/router/isis/rib-priority/high/type/tag/tag
                            leaf tag {
                                type uint32 {
                                    range "1..max";
                                }
                                description "Tag value that is used to match IS-IS routes";
                            }

                        }
                    }
                } // container high

            } // container rib-priority

            ///nokia-conf/configure/router/isis/timers
            container timers {
                description "Enter the timers context";

                ///nokia-conf/configure/router/isis/timers/spf-wait
                container spf-wait {
                    description "Enter the spf-wait context";

                    ///nokia-conf/configure/router/isis/timers/spf-wait/spf-max-wait
                    leaf spf-max-wait {
                        type uint32 {
                            range "10..120000";
                        }
                        units "milliseconds";
                        default "10000";
                        description "Maximum interval amid two consecutive SPF calculations";
                    }

                    ///nokia-conf/configure/router/isis/timers/spf-wait/spf-initial-wait
                    leaf spf-initial-wait {
                        type uint32 {
                            range "10..100000";
                        }
                        units "milliseconds";
                        default "1000";
                        description "Initial SPF calculation delay after topology change";
                    }

                    ///nokia-conf/configure/router/isis/timers/spf-wait/spf-second-wait
                    leaf spf-second-wait {
                        type uint32 {
                            range "10..100000";
                        }
                        units "milliseconds";
                        default "1000";
                        description "Hold time between first and second SPF calculations";
                    }

                } // container spf-wait

                ///nokia-conf/configure/router/isis/timers/lsp-wait
                container lsp-wait {
                    description "Enter the lsp-wait context";

                    ///nokia-conf/configure/router/isis/timers/lsp-wait/lsp-max-wait
                    leaf lsp-max-wait {
                        type uint32 {
                            range "10..120000";
                        }
                        units "milliseconds";
                        default "5000";
                        description "Maximum time between two consecutive LSP occurrences";
                    }

                    ///nokia-conf/configure/router/isis/timers/lsp-wait/lsp-initial-wait
                    leaf lsp-initial-wait {
                        type uint32 {
                            range "10..100000";
                        }
                        units "milliseconds";
                        default "10";
                        description "Initial LSP generation delay";
                    }

                    ///nokia-conf/configure/router/isis/timers/lsp-wait/lsp-second-wait
                    leaf lsp-second-wait {
                        type uint32 {
                            range "10..100000";
                        }
                        units "milliseconds";
                        default "1000";
                        description "Delay between first and second LSP generation";
                    }

                } // container lsp-wait

            } // container timers

            ///nokia-conf/configure/router/isis/unicast-import
            container unicast-import {
                description "Enter the unicast-import context";

                ///nokia-conf/configure/router/isis/unicast-import/ipv4
                leaf ipv4 {
                    type boolean;
                    default "true";
                    description "Submit IPv4 routes into unicast RTM";
                }

                ///nokia-conf/configure/router/isis/unicast-import/ipv6
                leaf ipv6 {
                    type boolean;
                    default "true";
                    description "Submit IPv6 routes into unicast RTM";
                }

            } // container unicast-import

            ///nokia-conf/configure/router/isis/loopfree-alternate
            container loopfree-alternate {
                presence "Enable the loopfree-alternate context";
                description "Enable the loopfree-alternate context";

                ///nokia-conf/configure/router/isis/loopfree-alternate/augment-route-table
                leaf augment-route-table {
                    type boolean;
                    default "false";
                    description "Attach remote LFA information to RTM entries";
                }

                ///nokia-conf/configure/router/isis/loopfree-alternate/exclude
                container exclude {
                    description "Enter the exclude context";

                    ///nokia-conf/configure/router/isis/loopfree-alternate/exclude/prefix-policy
                    leaf-list prefix-policy {
                        type leafref {
                            path "../../../../../policy-options/policy-statement/name";
                        }
                        max-elements 5;
                        ordered-by user;
                        description "Policy to exclude prefixes from LFA SPF calculation";
                    }

                } // container exclude

                ///nokia-conf/configure/router/isis/loopfree-alternate/multi-homed-prefix
                container multi-homed-prefix {
                    presence "Enable the multi-homed-prefix context";
                    description "Enable the multi-homed-prefix context";

                    ///nokia-conf/configure/router/isis/loopfree-alternate/multi-homed-prefix/preference
                    leaf preference {
                        type enumeration {
                            enum none                           { value 0; }
                            enum all                            { value 1; }
                        }
                        default "none";
                        description "Multihomed prefix LFA backup path preference";
                    }

                } // container multi-homed-prefix

                ///nokia-conf/configure/router/isis/loopfree-alternate/remote-lfa
                container remote-lfa {
                    presence "Enable the remote-lfa context";
                    description "Enable the remote-lfa context";

                    ///nokia-conf/configure/router/isis/loopfree-alternate/remote-lfa/max-pq-cost
                    leaf max-pq-cost {
                        type uint32;
                        default "4261412864";
                        description "Maximum cost of destination node during reverse SPF calculation";
                    }

                    ///nokia-conf/configure/router/isis/loopfree-alternate/remote-lfa/node-protect
                    container node-protect {
                        presence "Enable the node-protect context";
                        description "Enable the node-protect context";

                        ///nokia-conf/configure/router/isis/loopfree-alternate/remote-lfa/node-protect/max-pq-nodes
                        leaf max-pq-nodes {
                            type uint32 {
                                range "1..32";
                            }
                            default "16";
                            description "Maximum number of PQ nodes found in the LFA SPFs";
                        }

                    } // container node-protect

                } // container remote-lfa

                ///nokia-conf/configure/router/isis/loopfree-alternate/ti-lfa
                container ti-lfa {
                    presence "Enable the ti-lfa context";
                    description "Enable the ti-lfa context";

                    ///nokia-conf/configure/router/isis/loopfree-alternate/ti-lfa/max-sr-frr-labels
                    leaf max-sr-frr-labels {
                        type uint32 {
                            range "0..3";
                        }
                        default "2";
                        description "Maximum number of labels the TI-LFA backup path can use";
                    }

                    ///nokia-conf/configure/router/isis/loopfree-alternate/ti-lfa/max-srv6-frr-sids
                    leaf max-srv6-frr-sids {
                        type uint32 {
                            range "0..3";
                        }
                        default "1";
                        description "Maximum number of SIDs the TI-LFA backup path can use";
                    }

                    ///nokia-conf/configure/router/isis/loopfree-alternate/ti-lfa/node-protect
                    container node-protect {
                        presence "Enable the node-protect context";
                        description "Enable the node-protect context";

                    } // container node-protect

                } // container ti-lfa

            } // container loopfree-alternate

            ///nokia-conf/configure/router/isis/database-export
            container database-export {
                presence "Enable the database-export context";
                description "Enable the database-export context";

                ///nokia-conf/configure/router/isis/database-export/igp-identifier
                leaf igp-identifier {
                    type uint64;
                    description "Unique ID of the IGP instance in the BGP-LS NLRI";
                }

                ///nokia-conf/configure/router/isis/database-export/bgp-ls-identifier
                container bgp-ls-identifier {
                    presence "Enable the bgp-ls-identifier context";
                    description "Enable the bgp-ls-identifier context";

                    ///nokia-conf/configure/router/isis/database-export/bgp-ls-identifier/value
                    leaf value {
                        type uint32;
                        default "0";
                        description "BGP-LS identifier sent in the BGP-LS NLRI";
                    }

                } // container bgp-ls-identifier

            } // container database-export

            ///nokia-conf/configure/router/isis/flexible-algorithms
            container flexible-algorithms {
                description "Enter the flexible-algorithms context";

                ///nokia-conf/configure/router/isis/flexible-algorithms/admin-state
                leaf admin-state {
                    type types-sros:admin-state;
                    default "disable";
                    description "Administrative state of flexible algorithm support";
                }

                ///nokia-conf/configure/router/isis/flexible-algorithms/advertise-admin-group
                leaf advertise-admin-group {
                    type enumeration {
                        enum prefer-ag                      { value 1; }
                        enum eag-only                       { value 2; }
                        enum ag-eag                         { value 3; }
                    }
                    default "prefer-ag";
                    description "Administrative group TLV to advertise";
                }

                ///nokia-conf/configure/router/isis/flexible-algorithms/flex-algo
                list flex-algo {
                    key "flex-algo-id";
                    max-elements 7;
                    description "Enter the flex-algo list instance";

                    ///nokia-conf/configure/router/isis/flexible-algorithms/flex-algo/flex-algo-id
                    leaf flex-algo-id {
                        type uint32 {
                            range "128..255";
                        }
                        description "Flexible algorithm ID";
                    }

                    ///nokia-conf/configure/router/isis/flexible-algorithms/flex-algo/participate
                    leaf participate {
                        type boolean;
                        default "false";
                        description "Allow participation in the Flexible Algorithm";
                    }

                    ///nokia-conf/configure/router/isis/flexible-algorithms/flex-algo/advertise
                    leaf advertise {
                        type leafref {
                            path "../../../../../routing-options/flexible-algorithm-definitions/flex-algo/flex-algo-name";
                        }
                        description "Flexible Algorithm Definition advertisement";
                    }

                    ///nokia-conf/configure/router/isis/flexible-algorithms/flex-algo/apply-groups
                    leaf-list apply-groups {
                        type leafref {
                            path "../../../../../groups/group/name";
                        }
                        max-elements 8;
                        ordered-by user;
                        description "Apply a configuration group at this level";
                    }

                    ///nokia-conf/configure/router/isis/flexible-algorithms/flex-algo/apply-groups-exclude
                    leaf-list apply-groups-exclude {
                        type leafref {
                            path "../../../../../groups/group/name";
                        }
                        max-elements 8;
                        ordered-by user;
                        description "Exclude a configuration group at this level";
                    }

                    ///nokia-conf/configure/router/isis/flexible-algorithms/flex-algo/loopfree-alternate
                    container loopfree-alternate {
                        presence "Enable the loopfree-alternate context";
                        description "Enable the loopfree-alternate context";

                    } // container loopfree-alternate

                    ///nokia-conf/configure/router/isis/flexible-algorithms/flex-algo/micro-loop-avoidance
                    container micro-loop-avoidance {
                        presence "Enable the micro-loop-avoidance context";
                        description "Enable the micro-loop-avoidance context";

                    } // container micro-loop-avoidance

                } // list flex-algo

            } // container flexible-algorithms

            ///nokia-conf/configure/router/isis/traffic-engineering-options
            container traffic-engineering-options {
                description "Enter the traffic-engineering-options context";

                ///nokia-conf/configure/router/isis/traffic-engineering-options/advertise-delay
                leaf advertise-delay {
                    type boolean;
                    default "false";
                    description "Enable the advertisement of link delay for TE";
                }

                ///nokia-conf/configure/router/isis/traffic-engineering-options/ipv6
                leaf ipv6 {
                    type boolean;
                    default "false";
                    description "Advertise IS-IS IPv6 Traffic Engineering";
                }

                ///nokia-conf/configure/router/isis/traffic-engineering-options/application-link-attributes
                container application-link-attributes {
                    presence "Enable the application-link-attributes context";
                    description "Enable the application-link-attributes context";

                    ///nokia-conf/configure/router/isis/traffic-engineering-options/application-link-attributes/legacy
                    leaf legacy {
                        type boolean;
                        default "false";
                        description "Advertise legacy TE attributes";
                    }

                } // container application-link-attributes

            } // container traffic-engineering-options

            ///nokia-conf/configure/router/isis/segment-routing
            container segment-routing {
                description "Enable the segment-routing context";

                ///nokia-conf/configure/router/isis/segment-routing/admin-state
                leaf admin-state {
                    type types-sros:admin-state;
                    default "disable";
                    description "Administrative state of segment routing";
                }

                ///nokia-conf/configure/router/isis/segment-routing/adj-sid-hold
                leaf adj-sid-hold {
                    type types-igp:adj-sid-hold-ext-type;
                    units "seconds";
                    default "15";
                    description "Adjacency SID hold time";
                }

                ///nokia-conf/configure/router/isis/segment-routing/class-forwarding
                leaf class-forwarding {
                    type boolean;
                    default "false";
                    description "Allow CBF with ECMP over RSVP-TE LSPs as IGP shortcuts";
                }

                ///nokia-conf/configure/router/isis/segment-routing/entropy-label
                leaf entropy-label {
                    type boolean;
                    description "Enable processing of received ELC signaled in the IGP";
                }

                ///nokia-conf/configure/router/isis/segment-routing/export-tunnel-table
                leaf export-tunnel-table {
                    type enumeration {
                        enum ldp                            { value 1; }
                    }
                    description "Tunnel table export policies to export tunneled routes";
                }

                ///nokia-conf/configure/router/isis/segment-routing/srlb
                leaf srlb {
                    type leafref {
                        path "../../../mpls-labels/reserved-label-block/label-block-name";
                    }
                    description "Segment routing local block";
                }

                ///nokia-conf/configure/router/isis/segment-routing/tunnel-mtu
                leaf tunnel-mtu {
                    type types-router:ip-mtu-ext;
                    description "Tunnel MTU size";
                }

                ///nokia-conf/configure/router/isis/segment-routing/tunnel-table-pref
                leaf tunnel-table-pref {
                    type uint32 {
                        range "1..255";
                    }
                    default "11";
                    description "Preference of SR tunnels created by the IGP instance";
                }

                ///nokia-conf/configure/router/isis/segment-routing/apply-groups
                leaf-list apply-groups {
                    type leafref {
                        path "../../../../groups/group/name";
                    }
                    max-elements 8;
                    ordered-by user;
                    description "Apply a configuration group at this level";
                }

                ///nokia-conf/configure/router/isis/segment-routing/apply-groups-exclude
                leaf-list apply-groups-exclude {
                    type leafref {
                        path "../../../../groups/group/name";
                    }
                    max-elements 8;
                    ordered-by user;
                    description "Exclude a configuration group at this level";
                }

                ///nokia-conf/configure/router/isis/segment-routing/adjacency-sid
                container adjacency-sid {
                    description "Enter the adjacency-sid context";

                    ///nokia-conf/configure/router/isis/segment-routing/adjacency-sid/allocate-dual-sids
                    leaf allocate-dual-sids {
                        type boolean;
                        default "false";
                        description "Allocate dual adjacency SIDs per interface";
                    }

                } // container adjacency-sid

                ///nokia-conf/configure/router/isis/segment-routing/micro-loop-avoidance
                container micro-loop-avoidance {
                    presence "Enable the micro-loop-avoidance context";
                    description "Enable the micro-loop-avoidance context";

                    ///nokia-conf/configure/router/isis/segment-routing/micro-loop-avoidance/fib-delay
                    leaf fib-delay {
                        type uint32 {
                            range "1..300";
                        }
                        units "deciseconds";
                        default "15";
                        description "FIB delay before programming new primary next-hops";
                    }

                } // container micro-loop-avoidance

                ///nokia-conf/configure/router/isis/segment-routing/prefix-sid-range
                container prefix-sid-range {
                    presence "Enable the prefix-sid-range context";
                    description "Enable the prefix-sid-range context";

                    ///nokia-conf/configure/router/isis/segment-routing/prefix-sid-range/type
                    choice type {
                        ///nokia-conf/configure/router/isis/segment-routing/prefix-sid-range/type/global
                        case global {

                            ///nokia-conf/configure/router/isis/segment-routing/prefix-sid-range/type/global/global
                            leaf global {
                                type empty;
                                description "BGP global SR range allocation";
                            }

                        }
                        ///nokia-conf/configure/router/isis/segment-routing/prefix-sid-range/type/local
                        case local {

                            ///nokia-conf/configure/router/isis/segment-routing/prefix-sid-range/type/local/start-label
                            leaf start-label {
                                type uint32 {
                                    range "0..524287";
                                }
                                sros-ext:auto-restart-to-modify;
                                default "0";
                                description "Lower bound value for the local label offset";
                            }

                            ///nokia-conf/configure/router/isis/segment-routing/prefix-sid-range/type/local/max-index
                            leaf max-index {
                                type uint32 {
                                    range "0..524287";
                                }
                                sros-ext:auto-restart-to-modify;
                                default "1";
                                description "Upper bound value for the local SID index";
                            }

                        }
                    }
                } // container prefix-sid-range

                ///nokia-conf/configure/router/isis/segment-routing/maximum-sid-depth
                container maximum-sid-depth {
                    description "Enter the maximum-sid-depth context";

                    ///nokia-conf/configure/router/isis/segment-routing/maximum-sid-depth/override-bmi
                    leaf override-bmi {
                        type int32 {
                            range "0..12";
                        }
                        description "Value to override the announced node MSD-BMI value";
                    }

                    ///nokia-conf/configure/router/isis/segment-routing/maximum-sid-depth/override-erld
                    leaf override-erld {
                        type int32 {
                            range "0..15";
                        }
                        description "Value to override the announced node MSD-ERLD value";
                    }

                } // container maximum-sid-depth

                ///nokia-conf/configure/router/isis/segment-routing/adjacency-set
                list adjacency-set {
                    key "id";
                    description "Enter the adjacency-set list instance";

                    ///nokia-conf/configure/router/isis/segment-routing/adjacency-set/id
                    leaf id {
                        type uint32 {
                            range "1..max";
                        }
                        description "Identifier for specified adjacency set";
                    }

                    ///nokia-conf/configure/router/isis/segment-routing/adjacency-set/family
                    leaf family {
                        type types-sros:adjacency-set-family-type;
                        default "ipv4";
                        description "Address family for the adjacency set";
                    }

                    ///nokia-conf/configure/router/isis/segment-routing/adjacency-set/parallel
                    leaf parallel {
                        type boolean;
                        default "true";
                        description "Require all members of the adjacency set to terminate on the same neighboring node";
                    }

                    ///nokia-conf/configure/router/isis/segment-routing/adjacency-set/advertise
                    leaf advertise {
                        type boolean;
                        default "true";
                        description "Advertise the adjacency set when all links terminate on the same neighboring node";
                    }

                    ///nokia-conf/configure/router/isis/segment-routing/adjacency-set/apply-groups
                    leaf-list apply-groups {
                        type leafref {
                            path "../../../../../groups/group/name";
                        }
                        max-elements 8;
                        ordered-by user;
                        description "Apply a configuration group at this level";
                    }

                    ///nokia-conf/configure/router/isis/segment-routing/adjacency-set/apply-groups-exclude
                    leaf-list apply-groups-exclude {
                        type leafref {
                            path "../../../../../groups/group/name";
                        }
                        max-elements 8;
                        ordered-by user;
                        description "Exclude a configuration group at this level";
                    }

                    ///nokia-conf/configure/router/isis/segment-routing/adjacency-set/sid
                    container sid {
                        presence "Enable the sid context";
                        description "Enable the sid context";

                        ///nokia-conf/configure/router/isis/segment-routing/adjacency-set/sid/type
                        choice type {
                            ///nokia-conf/configure/router/isis/segment-routing/adjacency-set/sid/type/label
                            case label {

                                ///nokia-conf/configure/router/isis/segment-routing/adjacency-set/sid/type/label/label
                                leaf label {
                                    type int64 {
                                        range "1..1048575";
                                    }
                                    description "Adjacency SID label";
                                }

                            }
                        }
                    } // container sid

                } // list adjacency-set

                ///nokia-conf/configure/router/isis/segment-routing/egress-statistics
                container egress-statistics {
                    description "Enter the egress-statistics context";

                    ///nokia-conf/configure/router/isis/segment-routing/egress-statistics/adj-set
                    leaf adj-set {
                        type boolean;
                        default "false";
                        description "Enable the allocation of statistics on adjacency sets";
                    }

                    ///nokia-conf/configure/router/isis/segment-routing/egress-statistics/adj-sid
                    leaf adj-sid {
                        type boolean;
                        default "false";
                        description "Enable the allocation of statistics on adjacency SIDs";
                    }

                    ///nokia-conf/configure/router/isis/segment-routing/egress-statistics/node-sid
                    leaf node-sid {
                        type boolean;
                        default "false";
                        description "Enable the allocation of statistics on node SIDs";
                    }

                } // container egress-statistics

                ///nokia-conf/configure/router/isis/segment-routing/ingress-statistics
                container ingress-statistics {
                    description "Enter the ingress-statistics context";

                    ///nokia-conf/configure/router/isis/segment-routing/ingress-statistics/adj-set
                    leaf adj-set {
                        type boolean;
                        default "false";
                        description "Enable the allocation of statistics on adjacency sets";
                    }

                    ///nokia-conf/configure/router/isis/segment-routing/ingress-statistics/adj-sid
                    leaf adj-sid {
                        type boolean;
                        default "false";
                        description "Enable the allocation of statistics on adjacency SIDs";
                    }

                    ///nokia-conf/configure/router/isis/segment-routing/ingress-statistics/node-sid
                    leaf node-sid {
                        type boolean;
                        default "false";
                        description "Enable the allocation of statistics on node SIDs";
                    }

                } // container ingress-statistics

                ///nokia-conf/configure/router/isis/segment-routing/mapping-server
                container mapping-server {
                    description "Enter the mapping-server context";

                    ///nokia-conf/configure/router/isis/segment-routing/mapping-server/admin-state
                    leaf admin-state {
                        type types-sros:admin-state;
                        default "disable";
                        description "Administrative state of the IS-IS mapping server";
                    }

                    ///nokia-conf/configure/router/isis/segment-routing/mapping-server/node-sid-map
                    list node-sid-map {
                        key "sid-index";
                        description "Enter the node-sid-map list instance";

                        ///nokia-conf/configure/router/isis/segment-routing/mapping-server/node-sid-map/sid-index
                        leaf sid-index {
                            type uint32;
                            description "SID index of a mapping server Prefix-SID";
                        }

                        ///nokia-conf/configure/router/isis/segment-routing/mapping-server/node-sid-map/ip-prefix
                        leaf ip-prefix {
                            type types-sros:ipv4-unicast-prefix;
                            mandatory true;
                            description "Prefix of a mapping server Prefix-SID";
                        }

                        ///nokia-conf/configure/router/isis/segment-routing/mapping-server/node-sid-map/range
                        leaf range {
                            type uint32 {
                                range "0..65535";
                            }
                            default "1";
                            description "Range of addresses and their associated prefix SIDs";
                        }

                        ///nokia-conf/configure/router/isis/segment-routing/mapping-server/node-sid-map/level-capability
                        leaf level-capability {
                            type types-isis:level;
                            description "Flags to assign in SID Label Binding TLV advertised by Segment Routing Mapping Server";
                        }

                        ///nokia-conf/configure/router/isis/segment-routing/mapping-server/node-sid-map/clear-n-flag
                        leaf clear-n-flag {
                            type boolean;
                            default "false";
                            description "Clear the node-sid flag (N-flag)";
                        }

                        ///nokia-conf/configure/router/isis/segment-routing/mapping-server/node-sid-map/apply-groups
                        leaf-list apply-groups {
                            type leafref {
                                path "../../../../../../groups/group/name";
                            }
                            max-elements 8;
                            ordered-by user;
                            description "Apply a configuration group at this level";
                        }

                        ///nokia-conf/configure/router/isis/segment-routing/mapping-server/node-sid-map/apply-groups-exclude
                        leaf-list apply-groups-exclude {
                            type leafref {
                                path "../../../../../../groups/group/name";
                            }
                            max-elements 8;
                            ordered-by user;
                            description "Exclude a configuration group at this level";
                        }

                        ///nokia-conf/configure/router/isis/segment-routing/mapping-server/node-sid-map/set-flags
                        container set-flags {
                            description "Enter the set-flags context";

                            ///nokia-conf/configure/router/isis/segment-routing/mapping-server/node-sid-map/set-flags/bit-s
                            leaf bit-s {
                                type boolean;
                                default "false";
                                description "SID Label Binding TLV to be flooded across the entire routing domain";
                            }

                        } // container set-flags

                    } // list node-sid-map

                } // container mapping-server

            } // container segment-routing

            ///nokia-conf/configure/router/isis/segment-routing-v6
            container segment-routing-v6 {
                description "Enter the segment-routing-v6 context";

                ///nokia-conf/configure/router/isis/segment-routing-v6/admin-state
                leaf admin-state {
                    type types-sros:admin-state;
                    default "disable";
                    description "Administrative state of segment routing SRv6";
                }

                ///nokia-conf/configure/router/isis/segment-routing-v6/adj-sid-hold
                leaf adj-sid-hold {
                    type types-igp:adj-sid-hold-ext-type;
                    units "seconds";
                    default "15";
                    description "Adjacency SID hold time";
                }

                ///nokia-conf/configure/router/isis/segment-routing-v6/apply-groups
                leaf-list apply-groups {
                    type leafref {
                        path "../../../../groups/group/name";
                    }
                    max-elements 8;
                    ordered-by user;
                    description "Apply a configuration group at this level";
                }

                ///nokia-conf/configure/router/isis/segment-routing-v6/apply-groups-exclude
                leaf-list apply-groups-exclude {
                    type leafref {
                        path "../../../../groups/group/name";
                    }
                    max-elements 8;
                    ordered-by user;
                    description "Exclude a configuration group at this level";
                }

                ///nokia-conf/configure/router/isis/segment-routing-v6/locator
                list locator {
                    key "locator-name";
                    max-elements 8;
                    description "Enter the locator list instance";

                    ///nokia-conf/configure/router/isis/segment-routing-v6/locator/locator-name
                    leaf locator-name {
                        type leafref {
                            path "../../../../segment-routing/segment-routing-v6/locator/locator-name";
                        }
                        description "Locator name";
                    }

                    ///nokia-conf/configure/router/isis/segment-routing-v6/locator/level-capability
                    leaf level-capability {
                        type types-isis:level;
                        description "IS-IS routing level capability";
                    }

                    ///nokia-conf/configure/router/isis/segment-routing-v6/locator/tag
                    leaf tag {
                        type uint32 {
                            range "1..max";
                        }
                        description "Route tag to advertise in the locator";
                    }

                    ///nokia-conf/configure/router/isis/segment-routing-v6/locator/apply-groups
                    leaf-list apply-groups {
                        type leafref {
                            path "../../../../../groups/group/name";
                        }
                        max-elements 8;
                        ordered-by user;
                        description "Apply a configuration group at this level";
                    }

                    ///nokia-conf/configure/router/isis/segment-routing-v6/locator/apply-groups-exclude
                    leaf-list apply-groups-exclude {
                        type leafref {
                            path "../../../../../groups/group/name";
                        }
                        max-elements 8;
                        ordered-by user;
                        description "Exclude a configuration group at this level";
                    }

                    ///nokia-conf/configure/router/isis/segment-routing-v6/locator/multi-topology
                    container multi-topology {
                        description "Enter the multi-topology context";

                        ///nokia-conf/configure/router/isis/segment-routing-v6/locator/multi-topology/mt0
                        leaf mt0 {
                            type boolean;
                            default "true";
                            description "Support standard topology (MT0)";
                        }

                        ///nokia-conf/configure/router/isis/segment-routing-v6/locator/multi-topology/mt2
                        leaf mt2 {
                            type boolean;
                            default "false";
                            description "Support IPv6 routing topology (MT2)";
                        }

                    } // container multi-topology

                    ///nokia-conf/configure/router/isis/segment-routing-v6/locator/level
                    list level {
                        key "level-number";
                        max-elements 2;
                        description "Enter the level list instance";

                        ///nokia-conf/configure/router/isis/segment-routing-v6/locator/level/level-number
                        leaf level-number {
                            type enumeration {
                                enum 1                              { value 1; }
                                enum 2                              { value 2; }
                            }
                            description "ISIS protocol level number";
                        }

                        ///nokia-conf/configure/router/isis/segment-routing-v6/locator/level/metric
                        leaf metric {
                            type types-isis:metric;
                            description "IS-IS metric to advertise in the locator level list";
                        }

                        ///nokia-conf/configure/router/isis/segment-routing-v6/locator/level/apply-groups
                        leaf-list apply-groups {
                            type leafref {
                                path "../../../../../../groups/group/name";
                            }
                            max-elements 8;
                            ordered-by user;
                            description "Apply a configuration group at this level";
                        }

                        ///nokia-conf/configure/router/isis/segment-routing-v6/locator/level/apply-groups-exclude
                        leaf-list apply-groups-exclude {
                            type leafref {
                                path "../../../../../../groups/group/name";
                            }
                            max-elements 8;
                            ordered-by user;
                            description "Exclude a configuration group at this level";
                        }

                    } // list level

                } // list locator

                ///nokia-conf/configure/router/isis/segment-routing-v6/micro-segment-locator
                list micro-segment-locator {
                    key "locator-name";
                    max-elements 8;
                    description "Enter the micro-segment-locator list instance";

                    ///nokia-conf/configure/router/isis/segment-routing-v6/micro-segment-locator/locator-name
                    leaf locator-name {
                        type leafref {
                            path "../../../../../router/segment-routing/segment-routing-v6/micro-segment-locator/locator-name";
                        }
                        description "Micro-segment SRv6 locator name";
                    }

                    ///nokia-conf/configure/router/isis/segment-routing-v6/micro-segment-locator/level-capability
                    leaf level-capability {
                        type types-isis:level;
                        description "IS-IS routing level capability";
                    }

                    ///nokia-conf/configure/router/isis/segment-routing-v6/micro-segment-locator/tag
                    leaf tag {
                        type uint32 {
                            range "1..max";
                        }
                        description "Route tag to advertise in the locator";
                    }

                    ///nokia-conf/configure/router/isis/segment-routing-v6/micro-segment-locator/apply-groups
                    leaf-list apply-groups {
                        type leafref {
                            path "../../../../../groups/group/name";
                        }
                        max-elements 8;
                        ordered-by user;
                        description "Apply a configuration group at this level";
                    }

                    ///nokia-conf/configure/router/isis/segment-routing-v6/micro-segment-locator/apply-groups-exclude
                    leaf-list apply-groups-exclude {
                        type leafref {
                            path "../../../../../groups/group/name";
                        }
                        max-elements 8;
                        ordered-by user;
                        description "Exclude a configuration group at this level";
                    }

                    ///nokia-conf/configure/router/isis/segment-routing-v6/micro-segment-locator/multi-topology
                    container multi-topology {
                        description "Enter the multi-topology context";

                        ///nokia-conf/configure/router/isis/segment-routing-v6/micro-segment-locator/multi-topology/mt0
                        leaf mt0 {
                            type boolean;
                            default "true";
                            description "Support standard topology (MT0)";
                        }

                        ///nokia-conf/configure/router/isis/segment-routing-v6/micro-segment-locator/multi-topology/mt2
                        leaf mt2 {
                            type boolean;
                            default "false";
                            description "Support IPv6 routing topology (MT2)";
                        }

                    } // container multi-topology

                    ///nokia-conf/configure/router/isis/segment-routing-v6/micro-segment-locator/level
                    list level {
                        key "level-number";
                        max-elements 2;
                        description "Enter the level list instance";

                        ///nokia-conf/configure/router/isis/segment-routing-v6/micro-segment-locator/level/level-number
                        leaf level-number {
                            type enumeration {
                                enum 1                              { value 1; }
                                enum 2                              { value 2; }
                            }
                            description "ISIS protocol level number";
                        }

                        ///nokia-conf/configure/router/isis/segment-routing-v6/micro-segment-locator/level/metric
                        leaf metric {
                            type types-isis:metric;
                            description "IS-IS metric to advertise in the locator level list";
                        }

                        ///nokia-conf/configure/router/isis/segment-routing-v6/micro-segment-locator/level/apply-groups
                        leaf-list apply-groups {
                            type leafref {
                                path "../../../../../../groups/group/name";
                            }
                            max-elements 8;
                            ordered-by user;
                            description "Apply a configuration group at this level";
                        }

                        ///nokia-conf/configure/router/isis/segment-routing-v6/micro-segment-locator/level/apply-groups-exclude
                        leaf-list apply-groups-exclude {
                            type leafref {
                                path "../../../../../../groups/group/name";
                            }
                            max-elements 8;
                            ordered-by user;
                            description "Exclude a configuration group at this level";
                        }

                    } // list level

                } // list micro-segment-locator

            } // container segment-routing-v6

            ///nokia-conf/configure/router/isis/igp-shortcut
            container igp-shortcut {
                description "Enable the igp-shortcut context";

                ///nokia-conf/configure/router/isis/igp-shortcut/admin-state
                leaf admin-state {
                    type types-sros:admin-state;
                    default "disable";
                    description "Administrative state of RSVP-TE or SR-TE shortcut";
                }

                ///nokia-conf/configure/router/isis/igp-shortcut/allow-sr-over-srte
                leaf allow-sr-over-srte {
                    type boolean;
                    sros-ext:auto-restart-to-modify;
                    default "false";
                    description "Enable SR over SR-TE LSPs";
                }

                ///nokia-conf/configure/router/isis/igp-shortcut/apply-groups
                leaf-list apply-groups {
                    type leafref {
                        path "../../../../groups/group/name";
                    }
                    max-elements 8;
                    ordered-by user;
                    sros-ext:auto-restart-to-modify;
                    description "Apply a configuration group at this level";
                }

                ///nokia-conf/configure/router/isis/igp-shortcut/apply-groups-exclude
                leaf-list apply-groups-exclude {
                    type leafref {
                        path "../../../../groups/group/name";
                    }
                    max-elements 8;
                    ordered-by user;
                    sros-ext:auto-restart-to-modify;
                    description "Exclude a configuration group at this level";
                }

                ///nokia-conf/configure/router/isis/igp-shortcut/tunnel-next-hop
                container tunnel-next-hop {
                    sros-ext:auto-restart-to-modify;
                    description "Enter the tunnel-next-hop context";

                    ///nokia-conf/configure/router/isis/igp-shortcut/tunnel-next-hop/family
                    list family {
                        key "family-type";
                        description "Enter the family list instance";

                        ///nokia-conf/configure/router/isis/igp-shortcut/tunnel-next-hop/family/family-type
                        leaf family-type {
                            type types-isis:tunnel-next-hop-family-type;
                            description "Address family type for tunnel next hop";
                        }

                        ///nokia-conf/configure/router/isis/igp-shortcut/tunnel-next-hop/family/resolution
                        leaf resolution {
                            type types-sros:resolution-type;
                            description "Resolution mode for IGP shortcut tunnels";
                        }

                        ///nokia-conf/configure/router/isis/igp-shortcut/tunnel-next-hop/family/apply-groups
                        leaf-list apply-groups {
                            type leafref {
                                path "../../../../../../groups/group/name";
                            }
                            max-elements 8;
                            ordered-by user;
                            description "Apply a configuration group at this level";
                        }

                        ///nokia-conf/configure/router/isis/igp-shortcut/tunnel-next-hop/family/apply-groups-exclude
                        leaf-list apply-groups-exclude {
                            type leafref {
                                path "../../../../../../groups/group/name";
                            }
                            max-elements 8;
                            ordered-by user;
                            description "Exclude a configuration group at this level";
                        }

                        ///nokia-conf/configure/router/isis/igp-shortcut/tunnel-next-hop/family/resolution-filter
                        container resolution-filter {
                            description "Enter the resolution-filter context";

                            ///nokia-conf/configure/router/isis/igp-shortcut/tunnel-next-hop/family/resolution-filter/rsvp
                            leaf rsvp {
                                type boolean;
                                default "false";
                                description "Use RSVP tunneling for next-hop resolution";
                            }

                            ///nokia-conf/configure/router/isis/igp-shortcut/tunnel-next-hop/family/resolution-filter/sr-te
                            leaf sr-te {
                                type boolean;
                                default "false";
                                description "Use SR-TE tunneling for next-hop resolution";
                            }

                        } // container resolution-filter

                    } // list family

                } // container tunnel-next-hop

            } // container igp-shortcut

            ///nokia-conf/configure/router/isis/interface
            list interface {
                key "interface-name";
                description "Enter the interface list instance";

                ///nokia-conf/configure/router/isis/interface/interface-name
                leaf interface-name {
                    type types-sros:interface-name;
                    description "Router interface name";
                }

                ///nokia-conf/configure/router/isis/interface/admin-state
                leaf admin-state {
                    type types-sros:admin-state;
                    default "enable";
                    description "Administrative state of the IS-IS interface";
                }

                ///nokia-conf/configure/router/isis/interface/hello-authentication-key
                leaf hello-authentication-key {
                    type types-sros:encrypted-leaf {
                        length "1..366";
                    }
                    description "Authentication key or hash string for Hello PDUs";
                }

                ///nokia-conf/configure/router/isis/interface/hello-authentication-keychain
                leaf hello-authentication-keychain {
                    type leafref {
                        path "../../../../system/security/keychains/keychain/keychain-name";
                    }
                    description "Authentication keychain to use for the session";
                }

                ///nokia-conf/configure/router/isis/interface/hello-authentication-type
                leaf hello-authentication-type {
                    type types-isis:auth-type;
                    description "Hello authentication type";
                }

                ///nokia-conf/configure/router/isis/interface/hello-padding
                leaf hello-padding {
                    type types-isis:hello-padding-type;
                    description "Padding on IS-IS Hello packets";
                }

                ///nokia-conf/configure/router/isis/interface/passive
                leaf passive {
                    type boolean;
                    default "false";
                    description "Passive interface";
                }

                ///nokia-conf/configure/router/isis/interface/csnp-interval
                leaf csnp-interval {
                    type uint32 {
                        range "1..65535";
                    }
                    units "seconds";
                    default "10";
                    description "Time interval between successive CSN PDUs sent";
                }

                ///nokia-conf/configure/router/isis/interface/default-instance
                leaf default-instance {
                    type boolean;
                    default "false";
                    description "Allow non-MI capable router to establish an adjacency";
                }

                ///nokia-conf/configure/router/isis/interface/hello-authentication
                leaf hello-authentication {
                    type boolean;
                    default "true";
                    description "Authenticate Hello type IS-IS protocol packets";
                }

                ///nokia-conf/configure/router/isis/interface/interface-type
                leaf interface-type {
                    type types-isis:interface-type;
                    description "Interface type to broadcast, point-to-point, or to be default";
                }

                ///nokia-conf/configure/router/isis/interface/ipv4-multicast
                leaf ipv4-multicast {
                    type boolean;
                    default "true";
                    description "Enable IPv4 multicast routing for the interface";
                }

                ///nokia-conf/configure/router/isis/interface/ipv6-multicast
                leaf ipv6-multicast {
                    type boolean;
                    default "true";
                    description "Enable IPv6 multicast routing for the interface";
                }

                ///nokia-conf/configure/router/isis/interface/ipv6-unicast
                leaf ipv6-unicast {
                    type boolean;
                    default "true";
                    description "Enable IPv6 unicast routing for the interface";
                }

                ///nokia-conf/configure/router/isis/interface/level-capability
                leaf level-capability {
                    type types-isis:level;
                    description "IS-IS levels for this interface";
                }

                ///nokia-conf/configure/router/isis/interface/load-balancing-weight
                leaf load-balancing-weight {
                    type uint32;
                    description "Load balancing weight";
                }

                ///nokia-conf/configure/router/isis/interface/lsp-pacing-interval
                leaf lsp-pacing-interval {
                    type uint32 {
                        range "0..65535";
                    }
                    units "milliseconds";
                    default "100";
                    description "Interval for sending LSPs from interface";
                }

                ///nokia-conf/configure/router/isis/interface/retransmit-interval
                leaf retransmit-interval {
                    type uint32 {
                        range "1..65535";
                    }
                    units "seconds";
                    default "5";
                    description "Minimum time between LSP PDU retransmissions on point-to-point interface";
                }

                ///nokia-conf/configure/router/isis/interface/sid-protection
                leaf sid-protection {
                    type boolean;
                    default "true";
                    description "Allow adjacency SID protection by LFA and remote LFA";
                }

                ///nokia-conf/configure/router/isis/interface/tag
                leaf tag {
                    type uint32 {
                        range "1..max";
                    }
                    description "Route tag for IP address of interface";
                }

                ///nokia-conf/configure/router/isis/interface/apply-groups
                leaf-list apply-groups {
                    type leafref {
                        path "../../../../groups/group/name";
                    }
                    max-elements 8;
                    ordered-by user;
                    description "Apply a configuration group at this level";
                }

                ///nokia-conf/configure/router/isis/interface/apply-groups-exclude
                leaf-list apply-groups-exclude {
                    type leafref {
                        path "../../../../groups/group/name";
                    }
                    max-elements 8;
                    ordered-by user;
                    description "Exclude a configuration group at this level";
                }

                ///nokia-conf/configure/router/isis/interface/ipv4-adjacency-sid
                container ipv4-adjacency-sid {
                    presence "Enable the ipv4-adjacency-sid context";
                    description "Enable the ipv4-adjacency-sid context";

                    ///nokia-conf/configure/router/isis/interface/ipv4-adjacency-sid/type
                    choice type {
                        ///nokia-conf/configure/router/isis/interface/ipv4-adjacency-sid/type/label
                        case label {

                            ///nokia-conf/configure/router/isis/interface/ipv4-adjacency-sid/type/label/label
                            leaf label {
                                type int64 {
                                    range "1..1048575";
                                }
                                description "Adjacency SID label";
                            }

                        }
                    }
                } // container ipv4-adjacency-sid

                ///nokia-conf/configure/router/isis/interface/ipv6-adjacency-sid
                container ipv6-adjacency-sid {
                    presence "Enable the ipv6-adjacency-sid context";
                    description "Enable the ipv6-adjacency-sid context";

                    ///nokia-conf/configure/router/isis/interface/ipv6-adjacency-sid/type
                    choice type {
                        ///nokia-conf/configure/router/isis/interface/ipv6-adjacency-sid/type/label
                        case label {

                            ///nokia-conf/configure/router/isis/interface/ipv6-adjacency-sid/type/label/label
                            leaf label {
                                type int64 {
                                    range "1..1048575";
                                }
                                description "Adjacency SID label";
                            }

                        }
                    }
                } // container ipv6-adjacency-sid

                ///nokia-conf/configure/router/isis/interface/loopfree-alternate
                container loopfree-alternate {
                    description "Enter the loopfree-alternate context";

                    ///nokia-conf/configure/router/isis/interface/loopfree-alternate/exclude
                    leaf exclude {
                        type boolean;
                        default "false";
                        description "Enable/disable Loopfree Alternative at interface level.";
                    }

                    ///nokia-conf/configure/router/isis/interface/loopfree-alternate/policy-map
                    container policy-map {
                        presence "Enable the policy-map context";
                        description "Enable the policy-map context";

                        ///nokia-conf/configure/router/isis/interface/loopfree-alternate/policy-map/route-nh-template
                        leaf route-nh-template {
                            type leafref {
                                path "../../../../../../routing-options/route-next-hop-policy/template/template-name";
                            }
                            mandatory true;
                            description "Route next hop policy template name";
                        }

                    } // container policy-map

                } // container loopfree-alternate

                ///nokia-conf/configure/router/isis/interface/mesh-group
                container mesh-group {
                    presence "Enable the mesh-group context";
                    description "Enable the mesh-group context";

                    ///nokia-conf/configure/router/isis/interface/mesh-group/type
                    choice type {
                        ///nokia-conf/configure/router/isis/interface/mesh-group/type/value
                        case value {

                            ///nokia-conf/configure/router/isis/interface/mesh-group/type/value/value
                            leaf value {
                                type int32 {
                                    range "1..2000000000";
                                }
                                description "Mesh group for the interface";
                            }

                        }
                        ///nokia-conf/configure/router/isis/interface/mesh-group/type/blocked
                        case blocked {

                            ///nokia-conf/configure/router/isis/interface/mesh-group/type/blocked/blocked
                            leaf blocked {
                                type empty;
                                description "Prevent the interface from flooding LSPs";
                            }

                        }
                    }
                } // container mesh-group

                ///nokia-conf/configure/router/isis/interface/bfd-liveness
                container bfd-liveness {
                    description "Enter the bfd-liveness context";

                    ///nokia-conf/configure/router/isis/interface/bfd-liveness/ipv4
                    container ipv4 {
                        presence "Enable the ipv4 context";
                        description "Enable the ipv4 context";

                        ///nokia-conf/configure/router/isis/interface/bfd-liveness/ipv4/include-bfd-tlv
                        leaf include-bfd-tlv {
                            type boolean;
                            default "false";
                            description "Enable IS-IS BFD TLVs on the interface";
                        }

                    } // container ipv4

                    ///nokia-conf/configure/router/isis/interface/bfd-liveness/ipv6
                    container ipv6 {
                        presence "Enable the ipv6 context";
                        description "Enable the ipv6 context";

                        ///nokia-conf/configure/router/isis/interface/bfd-liveness/ipv6/include-bfd-tlv
                        leaf include-bfd-tlv {
                            type boolean;
                            default "false";
                            description "Enable IS-IS BFD TLVs on the interface";
                        }

                    } // container ipv6

                } // container bfd-liveness

                ///nokia-conf/configure/router/isis/interface/ipv4-node-sid
                container ipv4-node-sid {
                    presence "Enable the ipv4-node-sid context";
                    description "Enable the ipv4-node-sid context";

                    ///nokia-conf/configure/router/isis/interface/ipv4-node-sid/clear-n-flag
                    leaf clear-n-flag {
                        type boolean;
                        default "false";
                        description "Clear the node-sid flag (N-flag)";
                    }

                    ///nokia-conf/configure/router/isis/interface/ipv4-node-sid/type
                    choice type {
                        ///nokia-conf/configure/router/isis/interface/ipv4-node-sid/type/label
                        case label {

                            ///nokia-conf/configure/router/isis/interface/ipv4-node-sid/type/label/label
                            leaf label {
                                type int64 {
                                    range "1..4294967295";
                                }
                                description "Label value for the node SID";
                            }

                        }
                        ///nokia-conf/configure/router/isis/interface/ipv4-node-sid/type/index
                        case index {

                            ///nokia-conf/configure/router/isis/interface/ipv4-node-sid/type/index/index
                            leaf index {
                                type int64 {
                                    range "0..4294967295";
                                }
                                description "Node SID index for this interface";
                            }

                        }
                    }
                } // container ipv4-node-sid

                ///nokia-conf/configure/router/isis/interface/ipv6-node-sid
                container ipv6-node-sid {
                    presence "Enable the ipv6-node-sid context";
                    description "Enable the ipv6-node-sid context";

                    ///nokia-conf/configure/router/isis/interface/ipv6-node-sid/clear-n-flag
                    leaf clear-n-flag {
                        type boolean;
                        default "false";
                        description "Clear the node-sid flag (N-flag)";
                    }

                    ///nokia-conf/configure/router/isis/interface/ipv6-node-sid/type
                    choice type {
                        ///nokia-conf/configure/router/isis/interface/ipv6-node-sid/type/label
                        case label {

                            ///nokia-conf/configure/router/isis/interface/ipv6-node-sid/type/label/label
                            leaf label {
                                type int64 {
                                    range "1..4294967295";
                                }
                                description "Label value for the node SID";
                            }

                        }
                        ///nokia-conf/configure/router/isis/interface/ipv6-node-sid/type/index
                        case index {

                            ///nokia-conf/configure/router/isis/interface/ipv6-node-sid/type/index/index
                            leaf index {
                                type int64 {
                                    range "0..4294967295";
                                }
                                description "Node SID index for this interface";
                            }

                        }
                    }
                } // container ipv6-node-sid

                ///nokia-conf/configure/router/isis/interface/adjacency-set
                list adjacency-set {
                    key "id";
                    description "Add a list entry for adjacency-set";

                    ///nokia-conf/configure/router/isis/interface/adjacency-set/id
                    leaf id {
                        type leafref {
                            path "../../../segment-routing/adjacency-set/id";
                        }
                        description "Adjacency set ID";
                    }

                } // list adjacency-set

                ///nokia-conf/configure/router/isis/interface/flex-algo
                list flex-algo {
                    key "flex-algo-id";
                    max-elements 7;
                    description "Enter the flex-algo list instance";

                    ///nokia-conf/configure/router/isis/interface/flex-algo/flex-algo-id
                    leaf flex-algo-id {
                        type uint32 {
                            range "128..255";
                        }
                        description "Flexible algorithm ID";
                    }

                    ///nokia-conf/configure/router/isis/interface/flex-algo/apply-groups
                    leaf-list apply-groups {
                        type leafref {
                            path "../../../../../groups/group/name";
                        }
                        max-elements 8;
                        ordered-by user;
                        description "Apply a configuration group at this level";
                    }

                    ///nokia-conf/configure/router/isis/interface/flex-algo/apply-groups-exclude
                    leaf-list apply-groups-exclude {
                        type leafref {
                            path "../../../../../groups/group/name";
                        }
                        max-elements 8;
                        ordered-by user;
                        description "Exclude a configuration group at this level";
                    }

                    ///nokia-conf/configure/router/isis/interface/flex-algo/ipv4-node-sid
                    container ipv4-node-sid {
                        presence "Enable the ipv4-node-sid context";
                        description "Enable the ipv4-node-sid context";

                        ///nokia-conf/configure/router/isis/interface/flex-algo/ipv4-node-sid/type
                        choice type {
                            ///nokia-conf/configure/router/isis/interface/flex-algo/ipv4-node-sid/type/label
                            case label {

                                ///nokia-conf/configure/router/isis/interface/flex-algo/ipv4-node-sid/type/label/label
                                leaf label {
                                    type int64 {
                                        range "1..4294967295";
                                    }
                                    description "Label value for the node SID";
                                }

                            }
                            ///nokia-conf/configure/router/isis/interface/flex-algo/ipv4-node-sid/type/index
                            case index {

                                ///nokia-conf/configure/router/isis/interface/flex-algo/ipv4-node-sid/type/index/index
                                leaf index {
                                    type int64 {
                                        range "0..4294967295";
                                    }
                                    description "Node SID index for this interface";
                                }

                            }
                        }
                    } // container ipv4-node-sid

                    ///nokia-conf/configure/router/isis/interface/flex-algo/ipv6-node-sid
                    container ipv6-node-sid {
                        presence "Enable the ipv6-node-sid context";
                        description "Enable the ipv6-node-sid context";

                        ///nokia-conf/configure/router/isis/interface/flex-algo/ipv6-node-sid/type
                        choice type {
                            ///nokia-conf/configure/router/isis/interface/flex-algo/ipv6-node-sid/type/label
                            case label {

                                ///nokia-conf/configure/router/isis/interface/flex-algo/ipv6-node-sid/type/label/label
                                leaf label {
                                    type int64 {
                                        range "1..4294967295";
                                    }
                                    description "Label value for the node SID";
                                }

                            }
                            ///nokia-conf/configure/router/isis/interface/flex-algo/ipv6-node-sid/type/index
                            case index {

                                ///nokia-conf/configure/router/isis/interface/flex-algo/ipv6-node-sid/type/index/index
                                leaf index {
                                    type int64 {
                                        range "0..4294967295";
                                    }
                                    description "Node SID index for this interface";
                                }

                            }
                        }
                    } // container ipv6-node-sid

                } // list flex-algo

                ///nokia-conf/configure/router/isis/interface/level
                list level {
                    key "level-number";
                    max-elements 2;
                    description "Enter the level list instance";

                    ///nokia-conf/configure/router/isis/interface/level/level-number
                    leaf level-number {
                        type enumeration {
                            enum 1                              { value 1; }
                            enum 2                              { value 2; }
                        }
                        description "ISIS protocol level number";
                    }

                    ///nokia-conf/configure/router/isis/interface/level/hello-authentication-key
                    leaf hello-authentication-key {
                        type types-sros:encrypted-leaf {
                            length "1..366";
                        }
                        description "Authentication key for Hello PDUs";
                    }

                    ///nokia-conf/configure/router/isis/interface/level/hello-authentication-keychain
                    leaf hello-authentication-keychain {
                        type leafref {
                            path "../../../../../system/security/keychains/keychain/keychain-name";
                        }
                        description "Authentication keychain to use for the session";
                    }

                    ///nokia-conf/configure/router/isis/interface/level/hello-authentication-type
                    leaf hello-authentication-type {
                        type types-isis:auth-type;
                        description "Hello authentication enabled on the context";
                    }

                    ///nokia-conf/configure/router/isis/interface/level/hello-padding
                    leaf hello-padding {
                        type types-isis:hello-padding-type;
                        description "Padding on IS-IS Hello packets";
                    }

                    ///nokia-conf/configure/router/isis/interface/level/passive
                    leaf passive {
                        type boolean;
                        default "false";
                        description "Passive interface";
                    }

                    ///nokia-conf/configure/router/isis/interface/level/hello-interval
                    leaf hello-interval {
                        type uint32 {
                            range "1..20000";
                        }
                        units "seconds";
                        default "9";
                        description "Interval between Hello messages sent on this level";
                    }

                    ///nokia-conf/configure/router/isis/interface/level/hello-multiplier
                    leaf hello-multiplier {
                        type int32 {
                            range "2..100";
                        }
                        default "3";
                        description "Hello messages missed from neighbor before router declares adjacency down";
                    }

                    ///nokia-conf/configure/router/isis/interface/level/ipv4-multicast-metric
                    leaf ipv4-multicast-metric {
                        type types-isis:metric;
                        description "IS-IS interface metric applied for IPv4 multicast";
                    }

                    ///nokia-conf/configure/router/isis/interface/level/ipv6-multicast-metric
                    leaf ipv6-multicast-metric {
                        type types-isis:metric;
                        description "IS-IS interface metric applied for IPv6 multicast";
                    }

                    ///nokia-conf/configure/router/isis/interface/level/ipv6-unicast-metric
                    leaf ipv6-unicast-metric {
                        type types-isis:metric;
                        description "IS-IS interface metric applied for IPv6 unicast";
                    }

                    ///nokia-conf/configure/router/isis/interface/level/metric
                    leaf metric {
                        type types-isis:metric;
                        description "IS-IS interface metric applied for IPv4 unicast";
                    }

                    ///nokia-conf/configure/router/isis/interface/level/priority
                    leaf priority {
                        type uint32 {
                            range "0..127";
                        }
                        default "64";
                        description "Router to become the designated router on a multi-access network";
                    }

                    ///nokia-conf/configure/router/isis/interface/level/sd-offset
                    leaf sd-offset {
                        type types-isis:metric;
                        description "Value of the signal degrade offset";
                    }

                    ///nokia-conf/configure/router/isis/interface/level/sf-offset
                    leaf sf-offset {
                        type types-isis:metric;
                        description "Value of the signal fail offset";
                    }

                    ///nokia-conf/configure/router/isis/interface/level/apply-groups
                    leaf-list apply-groups {
                        type leafref {
                            path "../../../../../groups/group/name";
                        }
                        max-elements 8;
                        ordered-by user;
                        description "Apply a configuration group at this level";
                    }

                    ///nokia-conf/configure/router/isis/interface/level/apply-groups-exclude
                    leaf-list apply-groups-exclude {
                        type leafref {
                            path "../../../../../groups/group/name";
                        }
                        max-elements 8;
                        ordered-by user;
                        description "Exclude a configuration group at this level";
                    }

                } // list level

            } // list interface

            ///nokia-conf/configure/router/isis/level
            list level {
                key "level-number";
                max-elements 2;
                description "Enter the level list instance";

                ///nokia-conf/configure/router/isis/level/level-number
                leaf level-number {
                    type enumeration {
                        enum 1                              { value 1; }
                        enum 2                              { value 2; }
                    }
                    description "ISIS protocol level number";
                }

                ///nokia-conf/configure/router/isis/level/authentication-keychain
                leaf authentication-keychain {
                    type leafref {
                        path "../../../../system/security/keychains/keychain/keychain-name";
                    }
                    description "Keychain used to sign and authenticate";
                }

                ///nokia-conf/configure/router/isis/level/authentication-key
                leaf authentication-key {
                    type types-sros:encrypted-leaf {
                        length "1..366";
                    }
                    description "Authentication key to verify PDUs sent on the interface";
                }

                ///nokia-conf/configure/router/isis/level/authentication-type
                leaf authentication-type {
                    type types-isis:auth-type;
                    description "Authentication type to be used";
                }

                ///nokia-conf/configure/router/isis/level/csnp-authentication
                leaf csnp-authentication {
                    type boolean;
                    default "true";
                    description "Enable authentication of CSNP IS-IS protocol packets";
                }

                ///nokia-conf/configure/router/isis/level/psnp-authentication
                leaf psnp-authentication {
                    type boolean;
                    default "true";
                    description "Enable authentication on PSNP IS-IS protocol packets";
                }

                ///nokia-conf/configure/router/isis/level/advertise-router-capability
                leaf advertise-router-capability {
                    type boolean;
                    default "true";
                    description "Allow router advertisement capabilities";
                }

                ///nokia-conf/configure/router/isis/level/database-export-exclude
                leaf database-export-exclude {
                    type boolean;
                    default "false";
                    description "Exclude IGP link-state information of a specific IS-IS level from being exported into extended TE-DB";
                }

                ///nokia-conf/configure/router/isis/level/default-ipv4-multicast-metric
                leaf default-ipv4-multicast-metric {
                    type types-isis:metric;
                    default "10";
                    description "Default metric for IPv4 unicast";
                }

                ///nokia-conf/configure/router/isis/level/default-ipv6-multicast-metric
                leaf default-ipv6-multicast-metric {
                    type types-isis:metric;
                    default "10";
                    description "Default metric for IPv6 unicast";
                }

                ///nokia-conf/configure/router/isis/level/default-ipv6-unicast-metric
                leaf default-ipv6-unicast-metric {
                    type types-isis:metric;
                    default "10";
                    description "Default metric for IPv6 unicast";
                }

                ///nokia-conf/configure/router/isis/level/default-metric
                leaf default-metric {
                    type types-isis:metric;
                    default "10";
                    description "Default metric";
                }

                ///nokia-conf/configure/router/isis/level/external-preference
                leaf external-preference {
                    type uint32 {
                        range "1..255";
                    }
                    description "External route preference for IS-IS level";
                }

                ///nokia-conf/configure/router/isis/level/hello-authentication
                leaf hello-authentication {
                    type boolean;
                    default "true";
                    description "Authenticate Hello type IS-IS protocol packets";
                }

                ///nokia-conf/configure/router/isis/level/hello-padding
                leaf hello-padding {
                    type types-isis:hello-padding-type;
                    description "Padding on IS-IS Hello packets";
                }

                ///nokia-conf/configure/router/isis/level/loopfree-alternate-exclude
                leaf loopfree-alternate-exclude {
                    type boolean;
                    default "false";
                    description "Exclude interface participating in specific IS-IS level in SPF LFA computation";
                }

                ///nokia-conf/configure/router/isis/level/lsp-mtu-size
                leaf lsp-mtu-size {
                    type types-isis:lsp-buffer-ext-size;
                    units "bytes";
                    sros-ext:manual-restart-to-modify;
                    default "1492";
                    description "LSP MTU size";
                }

                ///nokia-conf/configure/router/isis/level/preference
                leaf preference {
                    type uint32 {
                        range "1..255";
                    }
                    description "External route preference at level";
                }

                ///nokia-conf/configure/router/isis/level/wide-metrics-only
                leaf wide-metrics-only {
                    type boolean;
                    default "false";
                    description "Use wide metrics advertisements in the LSPs";
                }

                ///nokia-conf/configure/router/isis/level/apply-groups
                leaf-list apply-groups {
                    type leafref {
                        path "../../../../groups/group/name";
                    }
                    max-elements 8;
                    ordered-by user;
                    description "Apply a configuration group at this level";
                }

                ///nokia-conf/configure/router/isis/level/apply-groups-exclude
                leaf-list apply-groups-exclude {
                    type leafref {
                        path "../../../../groups/group/name";
                    }
                    max-elements 8;
                    ordered-by user;
                    description "Exclude a configuration group at this level";
                }

                ///nokia-conf/configure/router/isis/level/bier
                container bier {
                    description "Enter the bier context";

                    ///nokia-conf/configure/router/isis/level/bier/admin-state
                    leaf admin-state {
                        type types-sros:admin-state;
                        default "disable";
                        description "Administrative state of BIER";
                    }

                    ///nokia-conf/configure/router/isis/level/bier/template
                    leaf template {
                        type leafref {
                            path "../../../../bier/template/template-name";
                        }
                        description "BIER template name";
                    }

                } // container bier

            } // list level

            ///nokia-conf/configure/router/isis/link-group
            list link-group {
                key "link-group-name";
                description "Enter the link-group list instance";

                ///nokia-conf/configure/router/isis/link-group/link-group-name
                leaf link-group-name {
                    type types-sros:named-item;
                    description "Link group name for the IS-IS protocol";
                }

                ///nokia-conf/configure/router/isis/link-group/description
                leaf description {
                    type types-sros:very-long-description;
                    description "Text description";
                }

                ///nokia-conf/configure/router/isis/link-group/apply-groups
                leaf-list apply-groups {
                    type leafref {
                        path "../../../../groups/group/name";
                    }
                    max-elements 8;
                    ordered-by user;
                    description "Apply a configuration group at this level";
                }

                ///nokia-conf/configure/router/isis/link-group/apply-groups-exclude
                leaf-list apply-groups-exclude {
                    type leafref {
                        path "../../../../groups/group/name";
                    }
                    max-elements 8;
                    ordered-by user;
                    description "Exclude a configuration group at this level";
                }

                ///nokia-conf/configure/router/isis/link-group/level
                list level {
                    key "level-number";
                    max-elements 2;
                    description "Enter the level list instance";

                    ///nokia-conf/configure/router/isis/link-group/level/level-number
                    leaf level-number {
                        type enumeration {
                            enum 1                              { value 1; }
                            enum 2                              { value 2; }
                        }
                        description "ISIS protocol level number";
                    }

                    ///nokia-conf/configure/router/isis/link-group/level/ipv4-multicast-metric-offset
                    leaf ipv4-multicast-metric-offset {
                        type types-isis:metric;
                        description "Offset value for the IPv4 multicast address family";
                    }

                    ///nokia-conf/configure/router/isis/link-group/level/ipv4-unicast-metric-offset
                    leaf ipv4-unicast-metric-offset {
                        type types-isis:metric;
                        description "Offset value for the IPv4 unicast address family";
                    }

                    ///nokia-conf/configure/router/isis/link-group/level/ipv6-multicast-metric-offset
                    leaf ipv6-multicast-metric-offset {
                        type types-isis:metric;
                        description "Offset value for the IPv6 multicast address family";
                    }

                    ///nokia-conf/configure/router/isis/link-group/level/ipv6-unicast-metric-offset
                    leaf ipv6-unicast-metric-offset {
                        type types-isis:metric;
                        description "Offset value for the IPv6 unicast address family";
                    }

                    ///nokia-conf/configure/router/isis/link-group/level/oper-members
                    leaf oper-members {
                        type uint32 {
                            range "1..8";
                        }
                        description "Minimum number of operational links";
                    }

                    ///nokia-conf/configure/router/isis/link-group/level/revert-members
                    leaf revert-members {
                        type uint32 {
                            range "1..8";
                        }
                        description "Minimum number of operational links to return link group to normal state and remove offsets";
                    }

                    ///nokia-conf/configure/router/isis/link-group/level/apply-groups
                    leaf-list apply-groups {
                        type leafref {
                            path "../../../../../groups/group/name";
                        }
                        max-elements 8;
                        ordered-by user;
                        description "Apply a configuration group at this level";
                    }

                    ///nokia-conf/configure/router/isis/link-group/level/apply-groups-exclude
                    leaf-list apply-groups-exclude {
                        type leafref {
                            path "../../../../../groups/group/name";
                        }
                        max-elements 8;
                        ordered-by user;
                        description "Exclude a configuration group at this level";
                    }

                    ///nokia-conf/configure/router/isis/link-group/level/member
                    list member {
                        key "interface-name";
                        max-elements 8;
                        description "Add a list entry for member";

                        ///nokia-conf/configure/router/isis/link-group/level/member/interface-name
                        leaf interface-name {
                            type leafref {
                                path "../../../../interface/interface-name";
                            }
                            description "Router interface name for this link group";
                        }

                    } // list member

                } // list level

            } // list link-group

            ///nokia-conf/configure/router/isis/summary-address
            list summary-address {
                key "ip-prefix";
                description "Enter the summary-address list instance";

                ///nokia-conf/configure/router/isis/summary-address/ip-prefix
                leaf ip-prefix {
                    type types-sros:ip-prefix;
                    description "IP prefix for the summary address";
                }

                ///nokia-conf/configure/router/isis/summary-address/level-capability
                leaf level-capability {
                    type types-isis:level;
                    description "IS-IS level for the summary address";
                }

                ///nokia-conf/configure/router/isis/summary-address/route-tag
                leaf route-tag {
                    type uint32 {
                        range "1..max";
                    }
                    description "Route tag assigned to the summary address";
                }

                ///nokia-conf/configure/router/isis/summary-address/algorithm
                leaf algorithm {
                    type int32 {
                        range "0|128..255";
                    }
                    description "Algorithm topology for the summary address";
                }

                ///nokia-conf/configure/router/isis/summary-address/apply-groups
                leaf-list apply-groups {
                    type leafref {
                        path "../../../../groups/group/name";
                    }
                    max-elements 8;
                    ordered-by user;
                    description "Apply a configuration group at this level";
                }

                ///nokia-conf/configure/router/isis/summary-address/apply-groups-exclude
                leaf-list apply-groups-exclude {
                    type leafref {
                        path "../../../../groups/group/name";
                    }
                    max-elements 8;
                    ordered-by user;
                    description "Exclude a configuration group at this level";
                }

            } // list summary-address

        } // list isis

    } // grouping conf-router-isis

}
